--  The capabilities of SROS product variants are described using
--  tmnx%*V14v0 AGENT-CAPABILITY statements, where % represents a
--  platform name (e.g. 7450).
--
--  The AGENT-CAPABILITY statements must be interpreted using the following
--  agent hierarchy:
--    tmnxSROS*V14v0              - All SROS platforms
--        tmnx7750*V14v0          - 7750 (generic platforms)
--            tmnx7750c12*V14v0    - 7750-c12 platform specific
--            tmnx7750c4*V14v0     - 7750-c4  platform specific
--            tmnx7750SR1*V14v0    - 7750 SR1 platform specific
--            tmnx7750SRa4*V14v0   - 7750 SR-a4 (HSA) platform
--            tmnx7750SRa8*V14v0   - 7750 SR-a8 (HSA) platform
--            tmnx7750SR1e*V14v0   - 7750 SR-1e (HSR) platform
--            tmnx7750SR2e*V14v0   - 7750 SR-2e (HSR) platform
--            tmnx7750SR3e*V14v0   - 7750 SR-3e (HSR) platform
--            tmnx7750MG*V14v0     - 7750 MG platform specific
--        tmnx7450*V14v0          - 7450 (generic platforms)
--            tmnx7450ESS1*V14v0    - 7450 ESS1 platform specific
--            tmnx7450ESS6*V14v0    - 7450 ESS6 platform specific 
--        tmnx7950*V14v0          - 7950 (generic platform)
--        tmnx7710*V14v0          - 7710 (generic platform)
--            tmnx7710c12*V14v0   - 7710-c12 platform specific
--            tmnx7710c4*V14v0    - 7710-c4  platform specific
--
--  For example, if a tmnx7750c12*V14v0 AGENT-CAPABILITY statement does
--  not exist, the tmnx7750*V14v0 takes effect. If, however, a
--  tmnx7750c12*V14v0 AGENT-CAPABILITY statement does exist, the
--  tmnx7750*V14v0 AGENT-CAPABILITY statement does not apply to the
--  7750-c12 agent.
--
--  When a platform specific AGENT-CAPABILITIES INCLUDES list contains a
--  EXCLUDE group statement, it indicates that the objects in that group are
--  not supported on that specific platform.  E.g.: tmnx7750V14v0
--  EXCLUDEs apsCommandOneToN because apsCommandOneToN is not supported on the
--  7750.
--
--  When a platform specific AGENT-CAPABILITIES statement consists of a
--  commented out SUPPORTS statement with an empty INCLUDES list and no
--  VARIATION statements, it indicates that the feature is not implemented
--  on that specific platform.  An empty INCLUDES list contains no group
--  names and no EXCLUDE statements.  E.g.: tmnx7750c12EthRingV14v0

TIMETRA-CAPABILITY-SROS-V14v0 DEFINITIONS ::= BEGIN

IMPORTS
    MODULE-IDENTITY, OBJECT-IDENTITY,
    enterprises, Integer32, Unsigned32      FROM SNMPv2-SMI

    RowStatus, TimeInterval, StorageType    FROM SNMPv2-TC

    AGENT-CAPABILITIES,
    MODULE-COMPLIANCE                       FROM SNMPv2-CONF

    DisplayString,
    TruthValue                              FROM SNMPv2-TC

    SnmpAdminString                         FROM SNMP-FRAMEWORK-MIB

    InterfaceIndex                          FROM IF-MIB

    DefaultMetric                           FROM ISIS-MIB

    Dot1agCfmIdPermission,
    Dot1agCfmMhfCreation,
    Dot1agCfmPbbComponentIdentifier,
    VlanIdOrNone                            FROM IEEE8021-CFM-MIB

    InetAddress, InetAddressPrefixLength,
    InetAddressType                         FROM INET-ADDRESS-MIB

    OwnerString                             FROM RMON-MIB

    LldpPortIdSubtype                       FROM LLDP-MIB 

    TmnxBsxOperator,
    TmnxBsxActionStatus,
    TmnxBsxAaSubscriberType                 FROM TIMETRA-BSX-NG-MIB

    TmnxSETSRefSource, TmnxSSMQualityLevel,
    TmnxChassisMode, TmnxBITSIfType,
    TmnxChassisIndex                        FROM TIMETRA-CHASSIS-MIB

    TEntryId                                FROM TIMETRA-FILTER-MIB

    TmnxOtuAlarms                           FROM TIMETRA-OTU-MIB

    TmnxL2tpSessionLimit                    FROM TIMETRA-L2TP-MIB

    timetraSROSCapModule,
    tmnxSROSCapability                      FROM TIMETRA-GLOBAL-MIB

    TmnxPtpPriority                         FROM TIMETRA-PTP-MIB

    TmnxEnabledDisabled, TIpProtocol,
    TmnxServId, TNamedItemOrEmpty,
    TmnxSubRadServAlgorithm                 FROM TIMETRA-TC-MIB;

--
-- Capability statements for SROS release 14.0
--
--
timetraSROSV14v0CapModule   MODULE-IDENTITY
    LAST-UPDATED "201611301215Z"
    ORGANIZATION "Nokia"
    CONTACT-INFO
        "Nokia SROS Support
        Web: http://www.nokia.com"
    DESCRIPTION
        "This document is the SNMP MIB module for agent capability clauses
         defined under the Nokia timetra object identifier branch for
         the Nokia SROS release R14.0.  These capability clauses
         specify details about the SNMP agent implementation for this release.

         Copyright 2005-2016 Nokia. All rights reserved.
         Reproduction of this document is authorized on the condition that the
         foregoing copyright notice is included.

         This SNMP MIB module (Specification) embodies Nokia's
         proprietary intellectual property.  Nokia retains all title
         and ownership in the Specification, including any revisions.

         Nokia grants all interested parties a non-exclusive license to
         use and distribute an unmodified copy of this Specification in
         connection with management of Nokia products, and without fee,
         provided this copyright notice and license appear on all copies.

         This Specification is supplied as is, and Nokia makes no
         warranty, either express or implied, as to the use, operation,
         condition, or performance of the Specification."
--
--  Revision History
--
    REVISION        "201611301215Z"
    DESCRIPTION     "Rev 0.0                30 Nov 2016 12:15
        This is the initial version of the TIMETRA-CAPABILITY-SROS-V14v0
         mib for Nokia SROS series Release 14.0."
        ::= { timetraSROSCapModule 14 }



--
--  Parent-tree for Nokia SROS SNMP agent capability objects
--
--  tmnxSROSCapability      OBJECT IDENTIFIER ::= { tmnxProductCapability 5 }
    tmnxSROSV14v0          OBJECT IDENTIFIER ::= { tmnxSROSCapability 14 }

-- Supported SROS Agents and capabilities defined by this SNMP MODULE:
tmnxCapsTestObjectV14v0     OBJECT IDENTIFIER ::= { tmnxSROSV14v0 1 }
tmnxSROSAgentCapsV14v0      OBJECT IDENTIFIER ::= { tmnxSROSV14v0 2 }

  tmnxSROSAgentV14v0       OBJECT IDENTIFIER ::= { tmnxSROSAgentCapsV14v0  1 }
-- tmnxSROSBgpV14v0               OBJECT IDENTIFIER ::= { tmnxSROSAgentV14v0   3 }
-- tmnxSROSCflowdV14v0            OBJECT IDENTIFIER ::= { tmnxSROSAgentV14v0   5 }
-- tmnxSROSChassisV14v0           OBJECT IDENTIFIER ::= { tmnxSROSAgentV14v0   6 }
-- tmnxSROSClearV14v0             OBJECT IDENTIFIER ::= { tmnxSROSAgentV14v0   7 }
-- tmnxSROSDs0V14v0               OBJECT IDENTIFIER ::= { tmnxSROSAgentV14v0   8 }
-- tmnxSROSDs1V14v0               OBJECT IDENTIFIER ::= { tmnxSROSAgentV14v0   9 }
-- tmnxSROSDs3V14v0               OBJECT IDENTIFIER ::= { tmnxSROSAgentV14v0  10 }
-- tmnxSROSEtherLikeV14v0         OBJECT IDENTIFIER ::= { tmnxSROSAgentV14v0  11 }
-- tmnxSROSEtherWisV14v0          OBJECT IDENTIFIER ::= { tmnxSROSAgentV14v0  12 }
-- tmnxSROSFilterV14v0            OBJECT IDENTIFIER ::= { tmnxSROSAgentV14v0  13 }
-- tmnxSROSFrameRelayDteV14v0     OBJECT IDENTIFIER ::= { tmnxSROSAgentV14v0  14 }
-- tmnxSROSIeee8021PaeV14v0       OBJECT IDENTIFIER ::= { tmnxSROSAgentV14v0  15 }
-- tmnxSROSInterfaceV14v0         OBJECT IDENTIFIER ::= { tmnxSROSAgentV14v0  16 }
-- tmnxSROSIgmpV14v0              OBJECT IDENTIFIER ::= { tmnxSROSAgentV14v0  18 }
-- tmnxSROSIgmpSnoopingV14v0      OBJECT IDENTIFIER ::= { tmnxSROSAgentV14v0  19 }
-- tmnxSROSIpV14v0                OBJECT IDENTIFIER ::= { tmnxSROSAgentV14v0  20 }
-- tmnxSROSIsisV14v0              OBJECT IDENTIFIER ::= { tmnxSROSAgentV14v0  21 }
-- tmnxSROSLagV14v0               OBJECT IDENTIFIER ::= { tmnxSROSAgentV14v0  22 }
-- tmnxSROSLdpV14v0               OBJECT IDENTIFIER ::= { tmnxSROSAgentV14v0  23 }
-- tmnxSROSLogV14v0               OBJECT IDENTIFIER ::= { tmnxSROSAgentV14v0  24 }
-- tmnxSROSMirrorV14v0            OBJECT IDENTIFIER ::= { tmnxSROSAgentV14v0  25 }
-- tmnxSROSMplsV14v0              OBJECT IDENTIFIER ::= { tmnxSROSAgentV14v0  26 }
-- tmnxSROSOamTestV14v0           OBJECT IDENTIFIER ::= { tmnxSROSAgentV14v0  27 }
-- tmnxSROSOamPmV14v0             OBJECT IDENTIFIER ::= { tmnxSROSAgentV14v0  28 }
-- tmnxSROSOspfV14v0              OBJECT IDENTIFIER ::= { tmnxSROSAgentV14v0  29 }
-- tmnxSROSPimV14v0               OBJECT IDENTIFIER ::= { tmnxSROSAgentV14v0  30 }
-- tmnxSROSPortV14v0              OBJECT IDENTIFIER ::= { tmnxSROSAgentV14v0  31 }
-- tmnxSROSPppV14v0               OBJECT IDENTIFIER ::= { tmnxSROSAgentV14v0  32 }
-- tmnxSROSQosV14v0               OBJECT IDENTIFIER ::= { tmnxSROSAgentV14v0  33 }
-- tmnxSROSRip2V14v0              OBJECT IDENTIFIER ::= { tmnxSROSAgentV14v0  34 }
-- tmnxSROSRmonV14v0              OBJECT IDENTIFIER ::= { tmnxSROSAgentV14v0  35 }
-- tmnxSROSRoutePolicyV14v0       OBJECT IDENTIFIER ::= { tmnxSROSAgentV14v0  36 }
-- tmnxSROSRsvpV14v0              OBJECT IDENTIFIER ::= { tmnxSROSAgentV14v0  37 }
-- tmnxSROSSatelliteV14v0         OBJECT IDENTIFIER ::= { tmnxSROSAgentV14v0  38 }
-- tmnxSROSSecurityV14v0          OBJECT IDENTIFIER ::= { tmnxSROSAgentV14v0  39 }
-- tmnxSROSServicesV14v0          OBJECT IDENTIFIER ::= { tmnxSROSAgentV14v0  40 }
-- tmnxSROSSnmpV14v0              OBJECT IDENTIFIER ::= { tmnxSROSAgentV14v0  41 }
-- tmnxSROSSonetV14v0             OBJECT IDENTIFIER ::= { tmnxSROSAgentV14v0  42 }
-- tmnxSROSSystemV14v0            OBJECT IDENTIFIER ::= { tmnxSROSAgentV14v0  43 }
-- tmnxSROSVrrpV14v0              OBJECT IDENTIFIER ::= { tmnxSROSAgentV14v0  44 }
-- tmnxSROSVrtrV14v0              OBJECT IDENTIFIER ::= { tmnxSROSAgentV14v0  45 }
-- tmnxSROSNtpV14v0               OBJECT IDENTIFIER ::= { tmnxSROSAgentV14v0  46 }
-- tmnxSROSSubscrMgmtV14v0        OBJECT IDENTIFIER ::= { tmnxSROSAgentV14v0  47 }
-- tmnxSROSCronV14v0              OBJECT IDENTIFIER ::= { tmnxSROSAgentV14v0  48 }
-- tmnxSROSSchedulerV14v0         OBJECT IDENTIFIER ::= { tmnxSROSAgentV14v0  49 }
-- tmnxSROSGsmpV14v0              OBJECT IDENTIFIER ::= { tmnxSROSAgentV14v0  50 }
-- tmnxSROSMcRedundancyV14v0      OBJECT IDENTIFIER ::= { tmnxSROSAgentV14v0  51 }
-- tmnxSROSMCastCacV14v0          OBJECT IDENTIFIER ::= { tmnxSROSAgentV14v0  52 }
-- tmnxSROSMsdpV14v0              OBJECT IDENTIFIER ::= { tmnxSROSAgentV14v0  53 }
-- tmnxSROSDot3OamV14v0           OBJECT IDENTIFIER ::= { tmnxSROSAgentV14v0  54 }
-- tmnxSROSMldSnoopingV14v0       OBJECT IDENTIFIER ::= { tmnxSROSAgentV14v0  55 }
-- tmnxSROSDhcpServerV14v0        OBJECT IDENTIFIER ::= { tmnxSROSAgentV14v0  57 }
-- tmnxSROSPppoeV14v0             OBJECT IDENTIFIER ::= { tmnxSROSAgentV14v0  58 }
-- tmnxSROSMldV14v0               OBJECT IDENTIFIER ::= { tmnxSROSAgentV14v0  59 }
-- tmnxSROSDot1agCfmV14v0         OBJECT IDENTIFIER ::= { tmnxSROSAgentV14v0  60 }
-- tmnxSROSMcastPathMgmtV14v0     OBJECT IDENTIFIER ::= { tmnxSROSAgentV14v0  61 }
-- tmnxSROSLocalUserDbV14v0       OBJECT IDENTIFIER ::= { tmnxSROSAgentV14v0  62 }
-- tmnxSROSPimSnoopingV14v0       OBJECT IDENTIFIER ::= { tmnxSROSAgentV14v0  63 }
-- tmnxSROSSapV14v0               OBJECT IDENTIFIER ::= { tmnxSROSAgentV14v0  64 }
-- tmnxSROSSdpV14v0               OBJECT IDENTIFIER ::= { tmnxSROSAgentV14v0  65 }
-- tmnxSROSLldpV14v0              OBJECT IDENTIFIER ::= { tmnxSROSAgentV14v0  67 }
-- tmnxSROSOtuV14v0               OBJECT IDENTIFIER ::= { tmnxSROSAgentV14v0  69 }
-- tmnxSROSEthTunnelV14v0         OBJECT IDENTIFIER ::= { tmnxSROSAgentV14v0  70 }
-- tmnxSROSNatV14v0               OBJECT IDENTIFIER ::= { tmnxSROSAgentV14v0  71 }
-- tmnxSROSVideoV14v0             OBJECT IDENTIFIER ::= { tmnxSROSAgentV14v0  72 }
-- tmnxSROSElmiV14v0              OBJECT IDENTIFIER ::= { tmnxSROSAgentV14v0  73 }
-- tmnxSROSIpsecStaticV14v0       OBJECT IDENTIFIER ::= { tmnxSROSAgentV14v0  74 }
-- tmnxSROSIfGrpHandlerV14v0      OBJECT IDENTIFIER ::= { tmnxSROSAgentV14v0  75 }
-- tmnxSROSEthRingV14v0           OBJECT IDENTIFIER ::= { tmnxSROSAgentV14v0  76 }
-- tmnxSROSDiameterV14v0          OBJECT IDENTIFIER ::= { tmnxSROSAgentV14v0  77 }
-- tmnxSROSTwampV14v0             OBJECT IDENTIFIER ::= { tmnxSROSAgentV14v0  79 }
-- tmnxSROSIpfixV14v0             OBJECT IDENTIFIER ::= { tmnxSROSAgentV14v0  80 }
-- tmnxSROSRadProxV14v0           OBJECT IDENTIFIER ::= { tmnxSROSAgentV14v0  81 }
-- tmnxSROSWppV14v0               OBJECT IDENTIFIER ::= { tmnxSROSAgentV14v0  82 }
-- tmnxSROSDynSrvV14v0            OBJECT IDENTIFIER ::= { tmnxSROSAgentV14v0  85 }
-- tmnxSROSBfdV14v0               OBJECT IDENTIFIER ::= { tmnxSROSAgentV14v0  86 }
-- tmnxSROSPythonV14v0            OBJECT IDENTIFIER ::= { tmnxSROSAgentV14v0  87 }
-- tmnxSROSLdp2V14v0              OBJECT IDENTIFIER ::= { tmnxSROSAgentV14v0  88 }
-- tmnxSROSOpenFlowV14v0          OBJECT IDENTIFIER ::= { tmnxSROSAgentV14v0  89 }
-- tmnxSROSPcepV14v0              OBJECT IDENTIFIER ::= { tmnxSROSAgentV14v0  90 }
-- tmnxSROSRpkiV14v0              OBJECT IDENTIFIER ::= { tmnxSROSAgentV14v0  92 }
-- tmnxSROSLdapV14v0              OBJECT IDENTIFIER ::= { tmnxSROSAgentV14v0  97 }
-- tmnxSROSTlsV14v0               OBJECT IDENTIFIER ::= { tmnxSROSAgentV14v0  98 }
-- tmnxSROSAlarmV14v0             OBJECT IDENTIFIER ::= { tmnxSROSAgentV14v0  99 }
-- tmnxSROSRouteNextHopTemplV14v0 OBJECT IDENTIFIER ::= { tmnxSROSAgentV14v0 100 }

  tmnx7750AgentV14v0       OBJECT IDENTIFIER ::= { tmnxSROSAgentCapsV14v0  2 }
-- tmnx7750ApsV14v0               OBJECT IDENTIFIER ::= { tmnx7750AgentV14v0   1 }
-- tmnx7750AtmV14v0               OBJECT IDENTIFIER ::= { tmnx7750AgentV14v0   2 }
-- tmnx7750ChassisV14v0           OBJECT IDENTIFIER ::= { tmnx7750AgentV14v0   6 }
-- tmnx7750MirrorV14v0            OBJECT IDENTIFIER ::= { tmnx7750AgentV14v0  25 }
-- tmnx7750PortV14v0              OBJECT IDENTIFIER ::= { tmnx7750AgentV14v0  31 }
-- tmnx7750QosV14v0               OBJECT IDENTIFIER ::= { tmnx7750AgentV14v0  33 }
-- tmnx7750ServicesV14v0          OBJECT IDENTIFIER ::= { tmnx7750AgentV14v0  40 }
-- tmnx7750IpSecV14v0             OBJECT IDENTIFIER ::= { tmnx7750AgentV14v0  56 }
-- tmnx7750SdpV14v0               OBJECT IDENTIFIER ::= { tmnx7750AgentV14v0  65 }
-- tmnx7750BsxV14v0               OBJECT IDENTIFIER ::= { tmnx7750AgentV14v0  66 }
-- tmnx7750L2tpV14v0              OBJECT IDENTIFIER ::= { tmnx7750AgentV14v0  68 }
-- tmnx7750ConnProfV14v0          OBJECT IDENTIFIER ::= { tmnx7750AgentV14v0  78 }
-- tmnx7750PtpV14v0               OBJECT IDENTIFIER ::= { tmnx7750AgentV14v0  83 }
-- tmnx7750WlanGwV14v0            OBJECT IDENTIFIER ::= { tmnx7750AgentV14v0  84 }
-- tmnx7750CalltraceV14v0         OBJECT IDENTIFIER ::= { tmnx7750AgentV14v0  94 }

  tmnx7750SR1AgentV14v0    OBJECT IDENTIFIER ::= { tmnxSROSAgentCapsV14v0  3 }
-- tmnx7750SR1AtmV14v0            OBJECT IDENTIFIER ::= { tmnx7750SR1AgentV14v0   2 }
-- tmnx7750SR1FilterV14v0         OBJECT IDENTIFIER ::= { tmnx7750SR1AgentV14v0  13 }
-- tmnx7750SR1LagV14v0            OBJECT IDENTIFIER ::= { tmnx7750SR1AgentV14v0  22 }
-- tmnx7750SR1OamTestV14v0        OBJECT IDENTIFIER ::= { tmnx7750SR1AgentV14v0  27 }
-- tmnx7750SR1OamPmV14v0          OBJECT IDENTIFIER ::= { tmnx7750SR1AgentV14v0  28 }
-- tmnx7750SR1SecurityV14v0       OBJECT IDENTIFIER ::= { tmnx7750SR1AgentV14v0  39 }
-- tmnx7750SR1ServicesV14v0       OBJECT IDENTIFIER ::= { tmnx7750SR1AgentV14v0  40 }
-- tmnx7750SR1SubscrMgmtV14v0     OBJECT IDENTIFIER ::= { tmnx7750SR1AgentV14v0  47 }
-- tmnx7750SR1SdpV14v0            OBJECT IDENTIFIER ::= { tmnx7750SR1AgentV14v0  65 }

  tmnx7750c12AgentV14v0    OBJECT IDENTIFIER ::= { tmnxSROSAgentCapsV14v0  4 }
-- tmnx7750c12ChassisV14v0        OBJECT IDENTIFIER ::= { tmnx7750c12AgentV14v0   6 }
-- tmnx7750c12LagV14v0            OBJECT IDENTIFIER ::= { tmnx7750c12AgentV14v0  22 }
-- tmnx7750c12PortV14v0           OBJECT IDENTIFIER ::= { tmnx7750c12AgentV14v0  31 }
-- tmnx7750c12QosV14v0            OBJECT IDENTIFIER ::= { tmnx7750c12AgentV14v0  33 }
-- tmnx7750c12SecurityV14v0       OBJECT IDENTIFIER ::= { tmnx7750c12AgentV14v0  39 }
-- tmnx7750c12VrtrV14v0           OBJECT IDENTIFIER ::= { tmnx7750c12AgentV14v0  45 }
-- tmnx7750c12SubscrMgmtV14v0     OBJECT IDENTIFIER ::= { tmnx7750c12AgentV14v0  47 }
-- tmnx7750c12McRedundancyV14v0   OBJECT IDENTIFIER ::= { tmnx7750c12AgentV14v0  51 }
-- tmnx7750c12McastPathMgmtV14v0  OBJECT IDENTIFIER ::= { tmnx7750c12AgentV14v0  61 }
-- tmnx7750c12SapV14v0            OBJECT IDENTIFIER ::= { tmnx7750c12AgentV14v0  64 }
-- tmnx7750c12SdpV14v0            OBJECT IDENTIFIER ::= { tmnx7750c12AgentV14v0  65 }
-- tmnx7750c12BsxV14v0            OBJECT IDENTIFIER ::= { tmnx7750c12AgentV14v0  66 }
-- tmnx7750c12L2tpV14v0           OBJECT IDENTIFIER ::= { tmnx7750c12AgentV14v0  68 }
-- tmnx7750c12EthTunnelV14v0      OBJECT IDENTIFIER ::= { tmnx7750c12AgentV14v0  70 }
-- tmnx7750c12NatV14v0            OBJECT IDENTIFIER ::= { tmnx7750c12AgentV14v0  71 }
-- tmnx7750c12VideoV14v0          OBJECT IDENTIFIER ::= { tmnx7750c12AgentV14v0  72 }
-- tmnx7750c12EthRingV14v0        OBJECT IDENTIFIER ::= { tmnx7750c12AgentV14v0  76 }

  tmnx7750c4AgentV14v0     OBJECT IDENTIFIER ::= { tmnxSROSAgentCapsV14v0  5 }
-- tmnx7750c4ChassisV14v0         OBJECT IDENTIFIER ::= { tmnx7750c4AgentV14v0   6 }
-- tmnx7750c4LagV14v0             OBJECT IDENTIFIER ::= { tmnx7750c4AgentV14v0  22 }
-- tmnx7750c4PortV14v0            OBJECT IDENTIFIER ::= { tmnx7750c4AgentV14v0  31 }
-- tmnx7750c4QosV14v0             OBJECT IDENTIFIER ::= { tmnx7750c4AgentV14v0  33 }
-- tmnx7750c4SecurityV14v0        OBJECT IDENTIFIER ::= { tmnx7750c4AgentV14v0  39 }
-- tmnx7750c4VrtrV14v0            OBJECT IDENTIFIER ::= { tmnx7750c4AgentV14v0  45 }
-- tmnx7750c4SubscrMgmtV14v0      OBJECT IDENTIFIER ::= { tmnx7750c4AgentV14v0  47 }
-- tmnx7750c4McRedundancyV14v0    OBJECT IDENTIFIER ::= { tmnx7750c4AgentV14v0  51 }
-- tmnx7750c4McastPathMgmtV14v0   OBJECT IDENTIFIER ::= { tmnx7750c4AgentV14v0  61 }
-- tmnx7750c4SapV14v0             OBJECT IDENTIFIER ::= { tmnx7750c4AgentV14v0  64 }
-- tmnx7750c4SdpV14v0             OBJECT IDENTIFIER ::= { tmnx7750c4AgentV14v0  65 }
-- tmnx7750c4BsxV14v0             OBJECT IDENTIFIER ::= { tmnx7750c4AgentV14v0  66 }
-- tmnx7750c4L2tpV14v0            OBJECT IDENTIFIER ::= { tmnx7750c4AgentV14v0  68 }
-- tmnx7750c4EthTunnelV14v0       OBJECT IDENTIFIER ::= { tmnx7750c4AgentV14v0  70 }
-- tmnx7750c4NatV14v0             OBJECT IDENTIFIER ::= { tmnx7750c4AgentV14v0  71 }
-- tmnx7750c4VideoV14v0           OBJECT IDENTIFIER ::= { tmnx7750c4AgentV14v0  72 }
-- tmnx7750c4EthRingV14v0         OBJECT IDENTIFIER ::= { tmnx7750c4AgentV14v0  76 }

  tmnx7750SR7AgentV14v0    OBJECT IDENTIFIER ::= { tmnxSROSAgentCapsV14v0  6 }
-- tmnx7750SR7GmplsUniV14v0       OBJECT IDENTIFIER ::= { tmnx7750SR7AgentV14v0  17 }
-- tmnx7750SR7OesV14v0            OBJECT IDENTIFIER ::= { tmnx7750SR7AgentV14v0  93 }
-- tmnx7750SR7PxcV14v0            OBJECT IDENTIFIER ::= { tmnx7750SR7AgentV14v0  95 }

  tmnx7750SR12AgentV14v0   OBJECT IDENTIFIER ::= { tmnxSROSAgentCapsV14v0  7 }
-- tmnx7750SR12GmplsUniV14v0      OBJECT IDENTIFIER ::= { tmnx7750SR12AgentV14v0  17 }
-- tmnx7750SR12OesV14v0           OBJECT IDENTIFIER ::= { tmnx7750SR12AgentV14v0  93 }
-- tmnx7750SR12PxcV14v0           OBJECT IDENTIFIER ::= { tmnx7750SR12AgentV14v0  95 }

  tmnx7750SR12eAgentV14v0  OBJECT IDENTIFIER ::= { tmnxSROSAgentCapsV14v0  8 }
-- tmnx7750SR12eChassisV14v0      OBJECT IDENTIFIER ::= { tmnx7750SR12eAgentV14v0   6 }
-- tmnx7750SR12eGmplsUniV14v0     OBJECT IDENTIFIER ::= { tmnx7750SR12eAgentV14v0  17 }
-- tmnx7750SR12eSflowV14v0        OBJECT IDENTIFIER ::= { tmnx7750SR12eAgentV14v0  91 }
-- tmnx7750SR12eOesV14v0          OBJECT IDENTIFIER ::= { tmnx7750SR12eAgentV14v0  93 }
-- tmnx7750SR12ePxcV14v0          OBJECT IDENTIFIER ::= { tmnx7750SR12eAgentV14v0  95 }

  tmnx7750SRa4AgentV14v0   OBJECT IDENTIFIER ::= { tmnxSROSAgentCapsV14v0  9 }
-- tmnx7750SRa4ChassisV14v0       OBJECT IDENTIFIER ::= { tmnx7750SRa4AgentV14v0   6 }
-- tmnx7750SRa4ServicesV14v0      OBJECT IDENTIFIER ::= { tmnx7750SRa4AgentV14v0  40 }
-- tmnx7750SRa4AlarmInputV14v0    OBJECT IDENTIFIER ::= { tmnx7750SRa4AgentV14v0  96 }

  tmnx7750SRa8AgentV14v0   OBJECT IDENTIFIER ::= { tmnxSROSAgentCapsV14v0 10 }
-- tmnx7750SRa8ChassisV14v0       OBJECT IDENTIFIER ::= { tmnx7750SRa8AgentV14v0   6 }
-- tmnx7750SRa8ServicesV14v0      OBJECT IDENTIFIER ::= { tmnx7750SRa8AgentV14v0  40 }
-- tmnx7750SRa8AlarmInputV14v0    OBJECT IDENTIFIER ::= { tmnx7750SRa8AgentV14v0  96 }

  tmnx7750SR1eAgentV14v0   OBJECT IDENTIFIER ::= { tmnxSROSAgentCapsV14v0 11 }
-- tmnx7750SR1eChassisV14v0       OBJECT IDENTIFIER ::= { tmnx7750SR1eAgentV14v0   6 }
-- tmnx7750SR1eServicesV14v0      OBJECT IDENTIFIER ::= { tmnx7750SR1eAgentV14v0  40 }

  tmnx7750SR2eAgentV14v0   OBJECT IDENTIFIER ::= { tmnxSROSAgentCapsV14v0 12 }
-- tmnx7750SR2eChassisV14v0       OBJECT IDENTIFIER ::= { tmnx7750SR2eAgentV14v0   6 }
-- tmnx7750SR2eServicesV14v0      OBJECT IDENTIFIER ::= { tmnx7750SR2eAgentV14v0  40 }

  tmnx7750SR3eAgentV14v0   OBJECT IDENTIFIER ::= { tmnxSROSAgentCapsV14v0 13 }
-- tmnx7750SR3eChassisV14v0       OBJECT IDENTIFIER ::= { tmnx7750SR3eAgentV14v0   6 }
-- tmnx7750SR3eServicesV14v0      OBJECT IDENTIFIER ::= { tmnx7750SR3eAgentV14v0  40 }

  tmnx7450AgentV14v0       OBJECT IDENTIFIER ::= { tmnxSROSAgentCapsV14v0 14 }
-- tmnx7450ApsV14v0               OBJECT IDENTIFIER ::= { tmnx7450AgentV14v0   1 }
-- tmnx7450AtmV14v0               OBJECT IDENTIFIER ::= { tmnx7450AgentV14v0   2 }
-- tmnx7450BgpV14v0               OBJECT IDENTIFIER ::= { tmnx7450AgentV14v0   3 }
-- tmnx7450ChassisV14v0           OBJECT IDENTIFIER ::= { tmnx7450AgentV14v0   6 }
-- tmnx7450MirrorV14v0            OBJECT IDENTIFIER ::= { tmnx7450AgentV14v0  25 }
-- tmnx7450PortV14v0              OBJECT IDENTIFIER ::= { tmnx7450AgentV14v0  31 }
-- tmnx7450QosV14v0               OBJECT IDENTIFIER ::= { tmnx7450AgentV14v0  33 }
-- tmnx7450SecurityV14v0          OBJECT IDENTIFIER ::= { tmnx7450AgentV14v0  39 }
-- tmnx7450ServicesV14v0          OBJECT IDENTIFIER ::= { tmnx7450AgentV14v0  40 }
-- tmnx7450SubscrMgmtV14v0        OBJECT IDENTIFIER ::= { tmnx7450AgentV14v0  47 }
-- tmnx7450SapV14v0               OBJECT IDENTIFIER ::= { tmnx7450AgentV14v0  64 }
-- tmnx7450SdpV14v0               OBJECT IDENTIFIER ::= { tmnx7450AgentV14v0  65 }
-- tmnx7450BsxV14v0               OBJECT IDENTIFIER ::= { tmnx7450AgentV14v0  66 }
-- tmnx7450L2tpV14v0              OBJECT IDENTIFIER ::= { tmnx7450AgentV14v0  68 }
-- tmnx7450NatV14v0               OBJECT IDENTIFIER ::= { tmnx7450AgentV14v0  71 }
-- tmnx7450ConnProfV14v0          OBJECT IDENTIFIER ::= { tmnx7450AgentV14v0  78 }
-- tmnx7450PtpV14v0               OBJECT IDENTIFIER ::= { tmnx7450AgentV14v0  83 }

  tmnx7450ESS1AgentV14v0   OBJECT IDENTIFIER ::= { tmnxSROSAgentCapsV14v0 15 }
-- tmnx7450ESS1AtmV14v0           OBJECT IDENTIFIER ::= { tmnx7450ESS1AgentV14v0   2 }
-- tmnx7450ESS1FilterV14v0        OBJECT IDENTIFIER ::= { tmnx7450ESS1AgentV14v0  13 }
-- tmnx7450ESS1LagV14v0           OBJECT IDENTIFIER ::= { tmnx7450ESS1AgentV14v0  22 }
-- tmnx7450ESS1OamTestV14v0       OBJECT IDENTIFIER ::= { tmnx7450ESS1AgentV14v0  27 }
-- tmnx7450ESS1OamPmV14v0         OBJECT IDENTIFIER ::= { tmnx7450ESS1AgentV14v0  28 }
-- tmnx7450ESS1SecurityV14v0      OBJECT IDENTIFIER ::= { tmnx7450ESS1AgentV14v0  39 }
-- tmnx7450ESS1ServicesV14v0      OBJECT IDENTIFIER ::= { tmnx7450ESS1AgentV14v0  40 }
-- tmnx7450ESS1SubscrMgmtV14v0    OBJECT IDENTIFIER ::= { tmnx7450ESS1AgentV14v0  47 }
-- tmnx7450ESS1SdpV14v0           OBJECT IDENTIFIER ::= { tmnx7450ESS1AgentV14v0  65 }

  tmnx7450ESS6AgentV14v0   OBJECT IDENTIFIER ::= { tmnxSROSAgentCapsV14v0 16 }
-- tmnx7450ESS6OamTestV14v0       OBJECT IDENTIFIER ::= { tmnx7450ESS6AgentV14v0  27 }
-- tmnx7450ESS6OamPmV14v0         OBJECT IDENTIFIER ::= { tmnx7450ESS6AgentV14v0  28 }

  tmnx7710AgentV14v0       OBJECT IDENTIFIER ::= { tmnxSROSAgentCapsV14v0 17 }
-- tmnx7710ApsV14v0               OBJECT IDENTIFIER ::= { tmnx7710AgentV14v0   1 }
-- tmnx7710AtmV14v0               OBJECT IDENTIFIER ::= { tmnx7710AgentV14v0   2 }
-- tmnx7710ChassisV14v0           OBJECT IDENTIFIER ::= { tmnx7710AgentV14v0   6 }
-- tmnx7710FilterV14v0            OBJECT IDENTIFIER ::= { tmnx7710AgentV14v0  13 }
-- tmnx7710LagV14v0               OBJECT IDENTIFIER ::= { tmnx7710AgentV14v0  22 }
-- tmnx7710LogV14v0               OBJECT IDENTIFIER ::= { tmnx7710AgentV14v0  24 }
-- tmnx7710OamTestV14v0           OBJECT IDENTIFIER ::= { tmnx7710AgentV14v0  27 }
-- tmnx7710OamPmV14v0             OBJECT IDENTIFIER ::= { tmnx7710AgentV14v0  28 }
-- tmnx7710PortV14v0              OBJECT IDENTIFIER ::= { tmnx7710AgentV14v0  31 }
-- tmnx7710QosV14v0               OBJECT IDENTIFIER ::= { tmnx7710AgentV14v0  33 }
-- tmnx7710SecurityV14v0          OBJECT IDENTIFIER ::= { tmnx7710AgentV14v0  39 }
-- tmnx7710ServicesV14v0          OBJECT IDENTIFIER ::= { tmnx7710AgentV14v0  40 }
-- tmnx7710VrtrV14v0              OBJECT IDENTIFIER ::= { tmnx7710AgentV14v0  45 }
-- tmnx7710SubscrMgmtV14v0        OBJECT IDENTIFIER ::= { tmnx7710AgentV14v0  47 }
-- tmnx7710McRedundancyV14v0      OBJECT IDENTIFIER ::= { tmnx7710AgentV14v0  51 }
-- tmnx7710PppoeV14v0             OBJECT IDENTIFIER ::= { tmnx7710AgentV14v0  58 }
-- tmnx7710McastPathMgmtV14v0     OBJECT IDENTIFIER ::= { tmnx7710AgentV14v0  61 }
-- tmnx7710LocalUserDbV14v0       OBJECT IDENTIFIER ::= { tmnx7710AgentV14v0  62 }
-- tmnx7710SapV14v0               OBJECT IDENTIFIER ::= { tmnx7710AgentV14v0  64 }
-- tmnx7710SdpV14v0               OBJECT IDENTIFIER ::= { tmnx7710AgentV14v0  65 }
-- tmnx7710EthTunnelV14v0         OBJECT IDENTIFIER ::= { tmnx7710AgentV14v0  70 }
-- tmnx7710VideoV14v0             OBJECT IDENTIFIER ::= { tmnx7710AgentV14v0  72 }
-- tmnx7710EthRingV14v0           OBJECT IDENTIFIER ::= { tmnx7710AgentV14v0  76 }

  tmnx7710c12AgentV14v0    OBJECT IDENTIFIER ::= { tmnxSROSAgentCapsV14v0 18 }

  tmnx7710c4AgentV14v0     OBJECT IDENTIFIER ::= { tmnxSROSAgentCapsV14v0 19 }

  tmnx7950AgentV14v0       OBJECT IDENTIFIER ::= { tmnxSROSAgentCapsV14v0 20 }
-- tmnx7950ChassisInterconnectV14v0 OBJECT IDENTIFIER ::= { tmnx7950AgentV14v0   4 }
-- tmnx7950CflowdV14v0            OBJECT IDENTIFIER ::= { tmnx7950AgentV14v0   5 }
-- tmnx7950ChassisV14v0           OBJECT IDENTIFIER ::= { tmnx7950AgentV14v0   6 }
-- tmnx7950FilterV14v0            OBJECT IDENTIFIER ::= { tmnx7950AgentV14v0  13 }
-- tmnx7950GmplsUniV14v0          OBJECT IDENTIFIER ::= { tmnx7950AgentV14v0  17 }
-- tmnx7950LogV14v0               OBJECT IDENTIFIER ::= { tmnx7950AgentV14v0  24 }
-- tmnx7950OamTestV14v0           OBJECT IDENTIFIER ::= { tmnx7950AgentV14v0  27 }
-- tmnx7950PortV14v0              OBJECT IDENTIFIER ::= { tmnx7950AgentV14v0  31 }
-- tmnx7950QosV14v0               OBJECT IDENTIFIER ::= { tmnx7950AgentV14v0  33 }
-- tmnx7950Rip2V14v0              OBJECT IDENTIFIER ::= { tmnx7950AgentV14v0  34 }
-- tmnx7950ServicesV14v0          OBJECT IDENTIFIER ::= { tmnx7950AgentV14v0  40 }
-- tmnx7950SonetV14v0             OBJECT IDENTIFIER ::= { tmnx7950AgentV14v0  42 }
-- tmnx7950SystemV14v0            OBJECT IDENTIFIER ::= { tmnx7950AgentV14v0  43 }
-- tmnx7950SubscrMgmtV14v0        OBJECT IDENTIFIER ::= { tmnx7950AgentV14v0  47 }
-- tmnx7950IpSecV14v0             OBJECT IDENTIFIER ::= { tmnx7950AgentV14v0  56 }
-- tmnx7950DhcpServerV14v0        OBJECT IDENTIFIER ::= { tmnx7950AgentV14v0  57 }
-- tmnx7950PppoeV14v0             OBJECT IDENTIFIER ::= { tmnx7950AgentV14v0  58 }
-- tmnx7950LocalUserDbV14v0       OBJECT IDENTIFIER ::= { tmnx7950AgentV14v0  62 }
-- tmnx7950SapV14v0               OBJECT IDENTIFIER ::= { tmnx7950AgentV14v0  64 }
-- tmnx7950SdpV14v0               OBJECT IDENTIFIER ::= { tmnx7950AgentV14v0  65 }
-- tmnx7950NatV14v0               OBJECT IDENTIFIER ::= { tmnx7950AgentV14v0  71 }
-- tmnx7950RadProxV14v0           OBJECT IDENTIFIER ::= { tmnx7950AgentV14v0  81 }
-- tmnx7950WppV14v0               OBJECT IDENTIFIER ::= { tmnx7950AgentV14v0  82 }
-- tmnx7950PtpV14v0               OBJECT IDENTIFIER ::= { tmnx7950AgentV14v0  83 }
-- tmnx7950SflowV14v0             OBJECT IDENTIFIER ::= { tmnx7950AgentV14v0  91 }
-- tmnx7950OesV14v0               OBJECT IDENTIFIER ::= { tmnx7950AgentV14v0  93 }
-- tmnx7950PxcV14v0               OBJECT IDENTIFIER ::= { tmnx7950AgentV14v0  95 }
--
-- SROS ALARM CAPABILITIES
--
tmnxSROSAlarmV14v0                AGENT-CAPABILITIES
    PRODUCT-RELEASE "Nokia SROS"
    STATUS          current
    DESCRIPTION
         "Implementation of alarms for Nokia SROS systems release 14.0."

    SUPPORTS        ALARM-MIB
        INCLUDES {
           alarmActiveGroup,
           alarmActiveStatsGroup,
           alarmClearGroup,
           alarmModelGroup,
           alarmNotificationsGroup
        }

        VARIATION   alarmActiveLogPointer
            DESCRIPTION
                 "alarmActiveLogPointer is not supported on Nokia SROS. The
                  value of alarmActiveLogPointer is always '0.0'."

        VARIATION   alarmActiveSpecificPointer
            DESCRIPTION
                 "alarmActiveSpecificPointer is not supported on Nokia SROS. The
                  value of alarmActiveSpecificPointer is always '0.0'."

        VARIATION   alarmActiveVariableCounter32Val
            ACCESS  not-implemented
            DESCRIPTION
                 "alarmActiveVariableCounter32Val is not implemented on Nokia
                  SROS in release 14.0."

        VARIATION   alarmActiveVariableCounter64Val
            ACCESS  not-implemented
            DESCRIPTION
                 "alarmActiveVariableCounter64Val is not implemented on Nokia
                  SROS in release 14.0."

        VARIATION   alarmActiveVariableID
            ACCESS  not-implemented
            DESCRIPTION
                 "alarmActiveVariableID is not implemented on Nokia SROS in
                  release 14.0."

        VARIATION   alarmActiveVariableInteger32Val
            ACCESS  not-implemented
            DESCRIPTION
                 "alarmActiveVariableInteger32Val is not implemented on Nokia
                  SROS in release 14.0."

        VARIATION   alarmActiveVariableIpAddressVal
            ACCESS  not-implemented
            DESCRIPTION
                 "alarmActiveVariableIpAddressVal is not implemented on Nokia
                  SROS in release 14.0."

        VARIATION   alarmActiveVariableOctetStringVal
            ACCESS  not-implemented
            DESCRIPTION
                 "alarmActiveVariableOctetStringVal is not implemented on Nokia
                  SROS in release 14.0."

        VARIATION   alarmActiveVariableOidVal
            ACCESS  not-implemented
            DESCRIPTION
                 "alarmActiveVariableOidVal is not implemented on Nokia SROS in
                  release 14.0."

        VARIATION   alarmActiveVariableOpaqueVal
            ACCESS  not-implemented
            DESCRIPTION
                 "alarmActiveVariableOpaqueVal is not implemented on Nokia SROS
                  in release 14.0."

        VARIATION   alarmActiveVariableTimeTicksVal
            ACCESS  not-implemented
            DESCRIPTION
                 "alarmActiveVariableTimeTicksVal is not implemented on Nokia
                  SROS in release 14.0."

        VARIATION   alarmActiveVariableUnsigned32Val
            ACCESS  not-implemented
            DESCRIPTION
                 "alarmActiveVariableUnsigned32Val is not implemented on Nokia
                  SROS in release 14.0."

        VARIATION   alarmActiveVariableValueType
            ACCESS  not-implemented
            DESCRIPTION
                 "alarmActiveVariableValueType is not implemented on Nokia SROS
                  in release 14.0."

        VARIATION   alarmActiveVariables
            DESCRIPTION
                 "alarmActiveVariables is not supported on Nokia SROS. The value
                  of alarmActiveVariables is always '0'."

        VARIATION   alarmClearLogIndex
            DESCRIPTION
                 "alarmClearLogIndex is not supported on Nokia SROS. The value
                  of alarmClearLogIndex is always '0'."

        VARIATION   alarmModelRowStatus
            SYNTAX  INTEGER {
                       active               (1)
                    }
            ACCESS  read-only
            DESCRIPTION
                 "alarmModelRowStatus is implemented as read-only. Row entries
                  cannot be created by SNMP SET requests. Alarms are created
                  using the TIMETRA-ALARM-MIB."

        VARIATION   alarmModelSpecificPointer
            DESCRIPTION
                 "alarmModelSpecificPointer is not supported on Nokia SROS. The
                  value of alarmModelSpecificPointer is always '0.0'."

    SUPPORTS        ITU-ALARM-MIB
        INCLUDES {
           ituAlarmStatisticsGroup
        }

    SUPPORTS        TIMETRA-ALARM-MIB
        INCLUDES {
           tmnxAlarmSystemConfigGroup
        }

    ::= { tmnxSROSAgentV14v0  99 }

--
-- 7750SR-a4 ALARM_INPUT CAPABILITIES
--
tmnx7750SRa4AlarmInputV14v0       AGENT-CAPABILITIES
    PRODUCT-RELEASE "Nokia SROS"
    STATUS          current
    DESCRIPTION
         "Implementation of alarm input capabilities for Nokia 7750 SR-a4
          systems release 14.0."

    SUPPORTS        TIMETRA-SAS-ALARM-INPUT-MIB
        INCLUDES {
           tmnxAlarmInputNotificationV2v0Group,
           tmnxAlmInpV2v0NotifyObjsGroup,
           tmnxSASAlarmInputV2v0Group
        }

        VARIATION   tmnxSasAlarmOutputSeverity
            ACCESS  not-implemented
            DESCRIPTION
                 "tmnxSasAlarmOutputSeverity is not implemented on Nokia 7750
                  SR-a4 in release 14.0."

    ::= { tmnx7750SRa4AgentV14v0  96 }

--
-- 7750SR-a8 ALARM_INPUT CAPABILITIES
--
tmnx7750SRa8AlarmInputV14v0       AGENT-CAPABILITIES
    PRODUCT-RELEASE "Nokia SROS"
    STATUS          current
    DESCRIPTION
         "Implementation of alarm input capabilities for Nokia 7750 SR-a8
          systems release 14.0."

    SUPPORTS        TIMETRA-SAS-ALARM-INPUT-MIB
        INCLUDES {
           tmnxAlarmInputNotificationV2v0Group,
           tmnxAlmInpV2v0NotifyObjsGroup,
           tmnxSASAlarmInputV2v0Group
        }

        VARIATION   tmnxSasAlarmOutputSeverity
            ACCESS  not-implemented
            DESCRIPTION
                 "tmnxSasAlarmOutputSeverity is not implemented on Nokia 7750
                  SR-a8 in release 14.0."

    ::= { tmnx7750SRa8AgentV14v0  96 }

--
-- 7750 APS CAPABILITIES
--
tmnx7750ApsV14v0                  AGENT-CAPABILITIES
    PRODUCT-RELEASE "Nokia SROS"
    STATUS          current
    DESCRIPTION
         "Implementation of APS capabilities for Nokia 7750 systems release
          14.0."

    SUPPORTS        APS-MIB
        INCLUDES {
           apsChanGeneral,
-- EXCLUDE apsChanOneToN
           apsCommandOnePlusOne,
-- EXCLUDE apsCommandOneToN
           apsConfigGeneral,
           apsConfigWtr,
           apsEventGroup,
           apsMapGroup,
           apsStatusGeneral,
           apsTotalsGroup
        }

        VARIATION   apsChanConfigIfIndex
            DESCRIPTION
                 "apsChanConfigIfIndex object cannot be set with the interface
                  index of a SONET LTE that is part of a channelized MDA that is
                  not part of the ASAP channelized MDA family (indicated by
                  tmnxMdaTypeName object of the TIMETRA-CHASSIS-MIB). For ASAP
                  MDA family refer to customer documentation for any further
                  restrictions."

        VARIATION   apsChanConfigNumber
            DESCRIPTION
                 "For an Multi-Chassis (MC) APS group (i.e. tApsMcNeighborAddr
                  object of the TIMETRA-APS-MIB is non-zero), an APS Group
                  (indicated by apsChanConfigGroupName object) can have only one
                  channel, i.e. apsChanConfigNumber can be set to either 0
                  (protection-circuit) or 1 (working-circuit) in an APS Group."

        VARIATION   apsChanConfigRowStatus
            DESCRIPTION
                 "For an Multi-Chassis (MC) APS group (i.e. tApsMcNeighborAddr
                  object of the TIMETRA-APS-MIB is non-zero), creation/deletion
                  of a protection circuit entry (i.e. apsChanConfigNumber 0)
                  creates/deletes an apsChanConfigEntry for the working circuit
                  (with 1 as apsChanConfigNumber and an invalid interface index
                  value as apsChanConfigIfIndex), and an apsChanConfigEntry for
                  the protection circuit (with the provided values of
                  apsChanConfigNumber and apsChanConfigIfIndex)."

        VARIATION   apsCommandSwitch
            DESCRIPTION
                 "For an Multi-Chassis (MC) APS group (i.e. tApsMcNeighborAddr
                  object of the TIMETRA-APS-MIB is non-zero), apsCommandSwitch
                  object can be set/read only from the protection router, i.e.
                  MC router having the protection circuit (apsChanConfigNumber
                  is 0). The switch commands can be set only if the MC-APS
                  control link (i.e. tApsMcApsCtlLinkState object of
                  TIMETRA-APS-MIB) is UP. However a switch command can be
                  cleared, i.e. the value 'clear (1)' can be set, irrespective
                  of the MC-APS Control link state.

                  For APS Annex B, the following switch commands must be
                  interpreted as switch requests against the primary or
                  secondary channels instead of the working or protection
                  channels respectively:

                  'forcedSwitchWorkToProtect(4)' 'forcedSwitchProtectToWork(5)'
                  'manualSwitchWorkToProtect(6)' 'manualSwitchProtectToWork(7)'

                  For example, value 'forcedSwitchWorkToProtect(4)' specifies a
                  forced switch of the primary channel to the secondary
                  channel."

        VARIATION   apsConfigDirection
            SYNTAX  INTEGER {
                       unidirectional       (1),
                       bidirectional        (2)
                    }
            DEFVAL  { bidirectional  }
            DESCRIPTION
                 "The default value is bidirectional instead of unidirectional."

        VARIATION   apsConfigEntry
            DESCRIPTION
                 "A Row creation/deletion in the apsConfigTable creates/deletes
                  an entry in the TIMETRA-PORT-MIB::tmnxPortTable for a port of
                  type APS Group."

        VARIATION   apsConfigExtraTraffic
            ACCESS  read-only
            DESCRIPTION
                 "apsConfigExtraTraffic is implemented as read-only on Nokia
                  7750 in release 14.0."

        VARIATION   apsConfigMode
            SYNTAX  INTEGER {
                       onePlusOne           (1),
                    -- oneToN               (2)
                    -- onePlusOneCompatible (3)
                       onePlusOneOptimized  (4)
                    }
            DESCRIPTION
                 "Only 'onePlusOne(1)' and 'onePlusOneOptimized(4)' are
                  supported."

        VARIATION   apsConfigName
            DESCRIPTION
                 "The format of the apsConfigName string must be
                  'aps-<group-id>' where <group-id> is a numerical value from 1
                  to the maximum number of supported APS groups for the chassis
                  type. An attempt to use an apsConfigName index that does not
                  meet this format specification results in a 'noCreation' or
                  'noSuchInstance' error."

        VARIATION   apsConfigRowStatus
            SYNTAX  RowStatus {
                       active               (1),
                    -- notInService         (2)
                    -- notReady             (3)
                       createAndGo          (4),
                    -- createAndWait        (5)
                       destroy              (6)
                    }
            DESCRIPTION
                 "apsConfigRowStatus supports only 'active (1)', 'createAndGo
                  (4)', and 'destroy (6)'."

        VARIATION   apsConfigSdBerThreshold
            ACCESS  not-implemented
            DESCRIPTION
                 "apsConfigSdBerThreshold is not implemented on Nokia 7750 in
                  release 14.0.

                  SD BER threshold of an APS physical port (working/protection
                  channel) can be set using the tmnxSonetBerSdThreshold object
                  of the TIMETRA-PORT-MIB."

        VARIATION   apsConfigSfBerThreshold
            ACCESS  not-implemented
            DESCRIPTION
                 "apsConfigSfBerThreshold is not implemented on Nokia 7750 in
                  release 14.0.

                  SF BER threshold of an APS physical port (working/protection
                  channel) can be set using the tmnxSonetBerSfThreshold object
                  of the TIMETRA-PORT-MIB."

        VARIATION   apsConfigWaitToRestore
            SYNTAX  Integer32 (0..3600)
            DESCRIPTION
                 "The maximum value of apsConfigWaitToRestore has been increased
                  from 720 to 3600 seconds. This is consistent with other Nokia
                  wait-to-restore timer objects.

                  The value of apsConfigWaitToRestore will be set to the
                  default value 300 if the value of apsConfigMode is changed by
                  an operator."

        VARIATION   apsEventSwitchover
            DESCRIPTION
                 "For an Multi-Chassis (MC) APS group (i.e. tApsMcNeighborAddr
                  object of the TIMETRA-APS-MIB is non-zero), apsEventSwitchover
                  notification sent by the protection router, i.e. MC router
                  having the protection circuit (apsChanConfigNumber is 0)
                  should be used to track an APS switchover event."

        VARIATION   apsNotificationEnable
            ACCESS  read-only
            DESCRIPTION
                 "apsNotificationEnable is implemented as read-only on Nokia
                  7750 in release 14.0.

                  The generation of APS notifications is controlled by
                  tmnxEventTable in the TIMETRA-LOG-MIB."

        VARIATION   apsStatusK1K2Rcv
            DESCRIPTION
                 "For SDH framing mode, as defined in G.841, bits 6-8 of K2
                  would be 0 for either (unidirectional or bidirectional)
                  switching mode."

        VARIATION   apsStatusK1K2Trans
            DESCRIPTION
                 "For SDH framing mode, as defined in G.841, bits 6-8 of K2
                  would be set to 0 for either (unidirectional or bidirectional)
                  switching mode."

        VARIATION   apsStatusSwitchedChannel
            DESCRIPTION
                 "For APS Annex B, apsStatusSwitchedChannel is set to the number
                  of the channel that is currently switched to the other
                  channel. The value '0' indicates that no channel is switched.
                  The value '1' indicates that working channel 1 is switched to
                  working channel 2. The value '2' indicates that working
                  channel 2 is switched to working channel 1."

    SUPPORTS        TIMETRA-APS-MIB
        INCLUDES {
           tmnxApsChanStatus,
           tmnxApsConfigGroup,
           tmnxApsConfigV8v0Group,
           tmnxApsGroupCommandV9v0Group,
           tmnxApsMcGroup,
           tmnxApsNotificationsV4v0,
           tmnxApsNotificationsV9v0Group,
           tmnxApsSwitchCommand
        }

        VARIATION   tmnxApsSwitchCommand
            DESCRIPTION
                 "For an Multi-Chassis (MC) APS group (i.e. tApsMcNeighborAddr
                  object of the TIMETRA-APS-MIB is non-zero), the objects of
                  this group can be set/read only from the protection router,
                  i.e. MC router having the protection circuit
                  (apsChanConfigNumber is 0)."

    ::= { tmnx7750AgentV14v0   1 }

--
-- 7450 APS CAPABILITIES
--
tmnx7450ApsV14v0                  AGENT-CAPABILITIES
    PRODUCT-RELEASE "Nokia SROS"
    STATUS          current
    DESCRIPTION
         "Implementation of APS capabilities for Nokia 7450 systems release
          14.0."

    SUPPORTS        APS-MIB
        INCLUDES {
           apsChanGeneral,
-- EXCLUDE apsChanOneToN
           apsCommandOnePlusOne,
-- EXCLUDE apsCommandOneToN
           apsConfigGeneral,
           apsConfigWtr,
           apsEventGroup,
           apsMapGroup,
           apsStatusGeneral,
           apsTotalsGroup
        }

        VARIATION   apsChanConfigIfIndex
            DESCRIPTION
                 "apsChanConfigIfIndex object cannot be set with the interface
                  index of a SONET LTE that is part of a channelized MDA that is
                  not part of the ASAP channelized MDA family (indicated by
                  tmnxMdaTypeName object of the TIMETRA-CHASSIS-MIB). For ASAP
                  MDA family refer to customer documentation for any further
                  restrictions."

        VARIATION   apsChanConfigNumber
            DESCRIPTION
                 "For an Multi-Chassis (MC) APS group (i.e. tApsMcNeighborAddr
                  object of the TIMETRA-APS-MIB is non-zero), an APS Group
                  (indicated by apsChanConfigGroupName object) can have only one
                  channel, i.e. apsChanConfigNumber can be set to either 0
                  (protection-circuit) or 1 (working-circuit) in an APS Group."

        VARIATION   apsChanConfigRowStatus
            DESCRIPTION
                 "For an Multi-Chassis (MC) APS group (i.e. tApsMcNeighborAddr
                  object of the TIMETRA-APS-MIB is non-zero), creation/deletion
                  of a protection circuit entry (i.e. apsChanConfigNumber 0)
                  creates/deletes an apsChanConfigEntry for the working circuit
                  (with 1 as apsChanConfigNumber and an invalid interface index
                  value as apsChanConfigIfIndex), and an apsChanConfigEntry for
                  the protection circuit (with the provided values of
                  apsChanConfigNumber and apsChanConfigIfIndex)."

        VARIATION   apsCommandSwitch
            DESCRIPTION
                 "For an Multi-Chassis (MC) APS group (i.e. tApsMcNeighborAddr
                  object of the TIMETRA-APS-MIB is non-zero), apsCommandSwitch
                  object can be set/read only from the protection router, i.e.
                  MC router having the protection circuit (apsChanConfigNumber
                  is 0). The switch commands can be set only if the MC-APS
                  control link (i.e. tApsMcApsCtlLinkState object of
                  TIMETRA-APS-MIB) is UP. However a switch command can be
                  cleared, i.e. the value 'clear (1)' can be set, irrespective
                  of the MC-APS Control link state.

                  For APS Annex B, the following switch commands must be
                  interpreted as switch requests against the primary or
                  secondary channels instead of the working or protection
                  channels respectively:

                  'forcedSwitchWorkToProtect(4)' 'forcedSwitchProtectToWork(5)'
                  'manualSwitchWorkToProtect(6)' 'manualSwitchProtectToWork(7)'

                  For example, value 'forcedSwitchWorkToProtect(4)' specifies a
                  forced switch of the primary channel to the secondary
                  channel."

        VARIATION   apsConfigDirection
            SYNTAX  INTEGER {
                       unidirectional       (1),
                       bidirectional        (2)
                    }
            DEFVAL  { bidirectional  }
            DESCRIPTION
                 "The default value is bidirectional instead of unidirectional."

        VARIATION   apsConfigEntry
            DESCRIPTION
                 "A Row creation/deletion in the apsConfigTable creates/deletes
                  an entry in the TIMETRA-PORT-MIB::tmnxPortTable for a port of
                  type APS Group."

        VARIATION   apsConfigExtraTraffic
            ACCESS  read-only
            DESCRIPTION
                 "apsConfigExtraTraffic is implemented as read-only on Nokia
                  7450 in release 14.0."

        VARIATION   apsConfigMode
            SYNTAX  INTEGER {
                       onePlusOne           (1),
                    -- oneToN               (2)
                    -- onePlusOneCompatible (3)
                       onePlusOneOptimized  (4)
                    }
            DESCRIPTION
                 "Only 'onePlusOne(1)' and 'onePlusOneOptimized(4)' are
                  supported."

        VARIATION   apsConfigName
            DESCRIPTION
                 "The format of the apsConfigName string must be
                  'aps-<group-id>' where <group-id> is a numerical value from 1
                  to the maximum number of supported APS groups for the chassis
                  type. An attempt to use an apsConfigName index that does not
                  meet this format specification results in a 'noCreation' or
                  'noSuchInstance' error."

        VARIATION   apsConfigRowStatus
            SYNTAX  RowStatus {
                       active               (1),
                    -- notInService         (2)
                    -- notReady             (3)
                       createAndGo          (4),
                    -- createAndWait        (5)
                       destroy              (6)
                    }
            DESCRIPTION
                 "apsConfigRowStatus supports only 'active (1)', 'createAndGo
                  (4)', and 'destroy (6)'."

        VARIATION   apsConfigSdBerThreshold
            ACCESS  not-implemented
            DESCRIPTION
                 "apsConfigSdBerThreshold is not implemented on Nokia 7450 in
                  release 14.0.

                  SD BER threshold of an APS physical port (working/protection
                  channel) can be set using the tmnxSonetBerSdThreshold object
                  of the TIMETRA-PORT-MIB."

        VARIATION   apsConfigSfBerThreshold
            ACCESS  not-implemented
            DESCRIPTION
                 "apsConfigSfBerThreshold is not implemented on Nokia 7450 in
                  release 14.0.

                  SF BER threshold of an APS physical port (working/protection
                  channel) can be set using the tmnxSonetBerSfThreshold object
                  of the TIMETRA-PORT-MIB."

        VARIATION   apsConfigWaitToRestore
            SYNTAX  Integer32 (0..3600)
            DESCRIPTION
                 "The maximum value of apsConfigWaitToRestore has been increased
                  from 720 to 3600 seconds. This is consistent with other Nokia
                  wait-to-restore timer objects.

                  The value of apsConfigWaitToRestore will be set to the
                  default value 300 if the value of apsConfigMode is changed by
                  an operator."

        VARIATION   apsEventSwitchover
            DESCRIPTION
                 "For an Multi-Chassis (MC) APS group (i.e. tApsMcNeighborAddr
                  object of the TIMETRA-APS-MIB is non-zero), apsEventSwitchover
                  notification sent by the protection router, i.e. MC router
                  having the protection circuit (apsChanConfigNumber is 0)
                  should be used to track an APS switchover event."

        VARIATION   apsNotificationEnable
            ACCESS  read-only
            DESCRIPTION
                 "apsNotificationEnable is implemented as read-only on Nokia
                  7450 in release 14.0.

                  The generation of APS notifications is controlled by
                  tmnxEventTable in the TIMETRA-LOG-MIB."

        VARIATION   apsStatusK1K2Rcv
            DESCRIPTION
                 "For SDH framing mode, as defined in G.841, bits 6-8 of K2
                  would be 0 for either (unidirectional or bidirectional)
                  switching mode."

        VARIATION   apsStatusK1K2Trans
            DESCRIPTION
                 "For SDH framing mode, as defined in G.841, bits 6-8 of K2
                  would be set to 0 for either (unidirectional or bidirectional)
                  switching mode."

        VARIATION   apsStatusSwitchedChannel
            DESCRIPTION
                 "For APS Annex B, apsStatusSwitchedChannel is set to the number
                  of the channel that is currently switched to the other
                  channel. The value '0' indicates that no channel is switched.
                  The value '1' indicates that working channel 1 is switched to
                  working channel 2. The value '2' indicates that working
                  channel 2 is switched to working channel 1."

    SUPPORTS        TIMETRA-APS-MIB
        INCLUDES {
           tmnxApsChanStatus,
           tmnxApsConfigGroup,
           tmnxApsConfigV8v0Group,
           tmnxApsGroupCommandV9v0Group,
           tmnxApsMcGroup,
           tmnxApsNotificationsV4v0,
           tmnxApsNotificationsV9v0Group,
           tmnxApsSwitchCommand
        }

        VARIATION   tmnxApsSwitchCommand
            DESCRIPTION
                 "For an Multi-Chassis (MC) APS group (i.e. tApsMcNeighborAddr
                  object of the TIMETRA-APS-MIB is non-zero), the objects of
                  this group can be set/read only from the protection router,
                  i.e. MC router having the protection circuit
                  (apsChanConfigNumber is 0)."

    ::= { tmnx7450AgentV14v0   1 }

--
-- 7710 APS CAPABILITIES
--
tmnx7710ApsV14v0                  AGENT-CAPABILITIES
    PRODUCT-RELEASE "Nokia SROS"
    STATUS          current
    DESCRIPTION
         "Implementation of APS capabilities for Nokia 7710 systems release
          14.0."

    SUPPORTS        APS-MIB
        INCLUDES {
           apsChanGeneral,
-- EXCLUDE apsChanOneToN
           apsCommandOnePlusOne,
-- EXCLUDE apsCommandOneToN
           apsConfigGeneral,
           apsConfigWtr,
           apsEventGroup,
           apsMapGroup,
           apsStatusGeneral,
           apsTotalsGroup
        }

        VARIATION   apsChanConfigIfIndex
            DESCRIPTION
                 "apsChanConfigIfIndex object cannot be set with the interface
                  index of a SONET LTE that is part of a channelized MDA that is
                  not part of the ASAP channelized MDA family (indicated by
                  tmnxMdaTypeName object of the TIMETRA-CHASSIS-MIB). For ASAP
                  MDA family refer to customer documentation for any further
                  restrictions."

        VARIATION   apsChanConfigNumber
            DESCRIPTION
                 "For an Multi-Chassis (MC) APS group (i.e. tApsMcNeighborAddr
                  object of the TIMETRA-APS-MIB is non-zero), an APS Group
                  (indicated by apsChanConfigGroupName object) can have only one
                  channel, i.e. apsChanConfigNumber can be set to either 0
                  (protection-circuit) or 1 (working-circuit) in an APS Group."

        VARIATION   apsChanConfigRowStatus
            DESCRIPTION
                 "For an Multi-Chassis (MC) APS group (i.e. tApsMcNeighborAddr
                  object of the TIMETRA-APS-MIB is non-zero), creation/deletion
                  of a protection circuit entry (i.e. apsChanConfigNumber 0)
                  creates/deletes an apsChanConfigEntry for the working circuit
                  (with 1 as apsChanConfigNumber and an invalid interface index
                  value as apsChanConfigIfIndex), and an apsChanConfigEntry for
                  the protection circuit (with the provided values of
                  apsChanConfigNumber and apsChanConfigIfIndex)."

        VARIATION   apsCommandSwitch
            DESCRIPTION
                 "For an Multi-Chassis (MC) APS group (i.e. tApsMcNeighborAddr
                  object of the TIMETRA-APS-MIB is non-zero), apsCommandSwitch
                  object can be set/read only from the protection router, i.e.
                  MC router having the protection circuit (apsChanConfigNumber
                  is 0). The switch commands can be set only if the MC-APS
                  control link (i.e. tApsMcApsCtlLinkState object of
                  TIMETRA-APS-MIB) is UP. However a switch command can be
                  cleared, i.e. the value 'clear (1)' can be set, irrespective
                  of the MC-APS Control link state.

                  For APS Annex B, the following switch commands must be
                  interpreted as switch requests against the primary or
                  secondary channels instead of the working or protection
                  channels respectively:

                  'forcedSwitchWorkToProtect(4)' 'forcedSwitchProtectToWork(5)'
                  'manualSwitchWorkToProtect(6)' 'manualSwitchProtectToWork(7)'

                  For example, value 'forcedSwitchWorkToProtect(4)' specifies a
                  forced switch of the primary channel to the secondary
                  channel."

        VARIATION   apsConfigDirection
            SYNTAX  INTEGER {
                       unidirectional       (1),
                       bidirectional        (2)
                    }
            DEFVAL  { bidirectional  }
            DESCRIPTION
                 "The default value is bidirectional instead of unidirectional."

        VARIATION   apsConfigEntry
            DESCRIPTION
                 "A Row creation/deletion in the apsConfigTable creates/deletes
                  an entry in the TIMETRA-PORT-MIB::tmnxPortTable for a port of
                  type APS Group."

        VARIATION   apsConfigExtraTraffic
            ACCESS  read-only
            DESCRIPTION
                 "apsConfigExtraTraffic is implemented as read-only on Nokia
                  7710 in release 14.0."

        VARIATION   apsConfigMode
            SYNTAX  INTEGER {
                       onePlusOne           (1),
                    -- oneToN               (2)
                    -- onePlusOneCompatible (3)
                       onePlusOneOptimized  (4)
                    }
            DESCRIPTION
                 "Only 'onePlusOne(1)' and 'onePlusOneOptimized(4)' are
                  supported."

        VARIATION   apsConfigName
            DESCRIPTION
                 "The format of the apsConfigName string must be
                  'aps-<group-id>' where <group-id> is a numerical value from 1
                  to the maximum number of supported APS groups for the chassis
                  type. An attempt to use an apsConfigName index that does not
                  meet this format specification results in a 'noCreation' or
                  'noSuchInstance' error."

        VARIATION   apsConfigRowStatus
            SYNTAX  RowStatus {
                       active               (1),
                    -- notInService         (2)
                    -- notReady             (3)
                       createAndGo          (4),
                    -- createAndWait        (5)
                       destroy              (6)
                    }
            DESCRIPTION
                 "apsConfigRowStatus supports only 'active (1)', 'createAndGo
                  (4)', and 'destroy (6)'."

        VARIATION   apsConfigSdBerThreshold
            ACCESS  not-implemented
            DESCRIPTION
                 "apsConfigSdBerThreshold is not implemented on Nokia 7710 in
                  release 14.0.

                  SD BER threshold of an APS physical port (working/protection
                  channel) can be set using the tmnxSonetBerSdThreshold object
                  of the TIMETRA-PORT-MIB."

        VARIATION   apsConfigSfBerThreshold
            ACCESS  not-implemented
            DESCRIPTION
                 "apsConfigSfBerThreshold is not implemented on Nokia 7710 in
                  release 14.0.

                  SF BER threshold of an APS physical port (working/protection
                  channel) can be set using the tmnxSonetBerSfThreshold object
                  of the TIMETRA-PORT-MIB."

        VARIATION   apsConfigWaitToRestore
            SYNTAX  Integer32 (0..3600)
            DESCRIPTION
                 "The maximum value of apsConfigWaitToRestore has been increased
                  from 720 to 3600 seconds. This is consistent with other Nokia
                  wait-to-restore timer objects.

                  The value of apsConfigWaitToRestore will be set to the
                  default value 300 if the value of apsConfigMode is changed by
                  an operator."

        VARIATION   apsEventSwitchover
            DESCRIPTION
                 "For an Multi-Chassis (MC) APS group (i.e. tApsMcNeighborAddr
                  object of the TIMETRA-APS-MIB is non-zero), apsEventSwitchover
                  notification sent by the protection router, i.e. MC router
                  having the protection circuit (apsChanConfigNumber is 0)
                  should be used to track an APS switchover event."

        VARIATION   apsNotificationEnable
            ACCESS  read-only
            DESCRIPTION
                 "apsNotificationEnable is implemented as read-only on Nokia
                  7710 in release 14.0.

                  The generation of APS notifications is controlled by
                  tmnxEventTable in the TIMETRA-LOG-MIB."

        VARIATION   apsStatusK1K2Rcv
            DESCRIPTION
                 "For SDH framing mode, as defined in G.841, bits 6-8 of K2
                  would be 0 for either (unidirectional or bidirectional)
                  switching mode."

        VARIATION   apsStatusK1K2Trans
            DESCRIPTION
                 "For SDH framing mode, as defined in G.841, bits 6-8 of K2
                  would be set to 0 for either (unidirectional or bidirectional)
                  switching mode."

        VARIATION   apsStatusSwitchedChannel
            DESCRIPTION
                 "For APS Annex B, apsStatusSwitchedChannel is set to the number
                  of the channel that is currently switched to the other
                  channel. The value '0' indicates that no channel is switched.
                  The value '1' indicates that working channel 1 is switched to
                  working channel 2. The value '2' indicates that working
                  channel 2 is switched to working channel 1."

    SUPPORTS        TIMETRA-APS-MIB
        INCLUDES {
           tmnxApsChanStatus,
           tmnxApsConfigGroup,
           tmnxApsConfigV8v0Group,
           tmnxApsGroupCommandV9v0Group,
           tmnxApsMcGroup,
           tmnxApsNotificationsV4v0,
           tmnxApsNotificationsV9v0Group,
           tmnxApsSwitchCommand
        }

        VARIATION   tApsLineSDHoldTime
            ACCESS  not-implemented
            DESCRIPTION
                 "tApsLineSDHoldTime is not implemented on Nokia 7710 in release
                  14.0."

        VARIATION   tApsLineSFHoldTime
            ACCESS  not-implemented
            DESCRIPTION
                 "tApsLineSFHoldTime is not implemented on Nokia 7710 in release
                  14.0."

        VARIATION   tApsProtectionType
            ACCESS  not-implemented
            DESCRIPTION
                 "tApsProtectionType is not implemented on Nokia 7710 in release
                  14.0."

        VARIATION   tApsRdiAlarmGeneration
            ACCESS  not-implemented
            DESCRIPTION
                 "tApsRdiAlarmGeneration is not implemented on Nokia 7710 in
                  release 14.0."

        VARIATION   tmnxApsSwitchCommand
            DESCRIPTION
                 "For an Multi-Chassis (MC) APS group (i.e. tApsMcNeighborAddr
                  object of the TIMETRA-APS-MIB is non-zero), the objects of
                  this group can be set/read only from the protection router,
                  i.e. MC router having the protection circuit
                  (apsChanConfigNumber is 0)."

    ::= { tmnx7710AgentV14v0   1 }

--
-- 7750 ATM CAPABILITIES
--
tmnx7750AtmV14v0                  AGENT-CAPABILITIES
    PRODUCT-RELEASE "Nokia SROS"
    STATUS          current
    DESCRIPTION
         "Implementation of ATM functions for Nokia 7750 systems release 14.0."

    SUPPORTS        ATM-MIB
        INCLUDES {
           aal5VccGroup,
-- EXCLUDE atmInterfaceConfGroup
           atmInterfaceConfGroup2,
-- EXCLUDE atmInterfaceDs3PlcpGroup
           atmInterfaceTCGroup,
-- EXCLUDE atmTrafficDescrGroup
-- EXCLUDE atmTrafficDescrGroup2
-- EXCLUDE atmVcCrossConnectGroup
-- EXCLUDE atmVcPvcCrossConnectGroup
-- EXCLUDE atmVccTerminationGroup
           atmVccTerminationGroup2
-- EXCLUDE atmVclCrossConnectGroup
-- EXCLUDE atmVpCrossConnectGroup
-- EXCLUDE atmVpPvcCrossConnectGroup
-- EXCLUDE atmVpcTerminationGroup
-- EXCLUDE atmVpcTerminationGroup2
-- EXCLUDE atmVplCrossConnectGroup
        }

        VARIATION   atmInterfaceAddressType
            ACCESS  not-implemented
            DESCRIPTION
                 "atmInterfaceAddressType is not implemented on Nokia 7750 in
                  release 14.0.

                  Deprecated object."

        VARIATION   atmInterfaceAdminAddress
            ACCESS  not-implemented
            DESCRIPTION
                 "atmInterfaceAdminAddress is not implemented on Nokia 7750 in
                  release 14.0.

                  Deprecated object."

        VARIATION   atmInterfaceIlmiVci
            ACCESS  read-only
            DESCRIPTION
                 "atmInterfaceIlmiVci is implemented as read-only on Nokia 7750
                  in release 14.0."

        VARIATION   atmInterfaceIlmiVpi
            ACCESS  read-only
            DESCRIPTION
                 "atmInterfaceIlmiVpi is implemented as read-only on Nokia 7750
                  in release 14.0."

        VARIATION   atmInterfaceMaxActiveVciBits
            ACCESS  read-only
            DESCRIPTION
                 "atmInterfaceMaxActiveVciBits is implemented as read-only on
                  Nokia 7750 in release 14.0."

        VARIATION   atmInterfaceMaxActiveVpiBits
            ACCESS  read-only
            DESCRIPTION
                 "atmInterfaceMaxActiveVpiBits is implemented as read-only on
                  Nokia 7750 in release 14.0."

        VARIATION   atmInterfaceMaxVccs
            ACCESS  read-only
            DESCRIPTION
                 "atmInterfaceMaxVccs is implemented as read-only on Nokia 7750
                  in release 14.0."

        VARIATION   atmInterfaceMaxVpcs
            ACCESS  read-only
            DESCRIPTION
                 "atmInterfaceMaxVpcs is implemented as read-only on Nokia 7750
                  in release 14.0."

        VARIATION   atmInterfaceMyNeighborIfName
            ACCESS  not-implemented
            DESCRIPTION
                 "atmInterfaceMyNeighborIfName is not implemented on Nokia 7750
                  in release 14.0."

        VARIATION   atmInterfaceMyNeighborIpAddress
            ACCESS  not-implemented
            DESCRIPTION
                 "atmInterfaceMyNeighborIpAddress is not implemented on Nokia
                  7750 in release 14.0."

        VARIATION   atmInterfaceSubscrAddress
            ACCESS  not-implemented
            DESCRIPTION
                 "atmInterfaceSubscrAddress is not implemented on Nokia 7750 in
                  release 14.0."

        VARIATION   atmVccAal5CpcsReceiveSduSize
            ACCESS  not-implemented
            DESCRIPTION
                 "atmVccAal5CpcsReceiveSduSize is not implemented on Nokia 7750
                  in release 14.0."

        VARIATION   atmVccAal5CpcsTransmitSduSize
            ACCESS  not-implemented
            DESCRIPTION
                 "atmVccAal5CpcsTransmitSduSize is not implemented on Nokia 7750
                  in release 14.0."

        VARIATION   atmVccAal5EncapsType
            ACCESS  read-only
            DESCRIPTION
                 "atmVccAal5EncapsType is implemented as read-only on Nokia 7750
                  in release 14.0."

        VARIATION   atmVccAalType
            ACCESS  read-only
            DESCRIPTION
                 "atmVccAalType is implemented as read-only on Nokia 7750 in
                  release 14.0."

        VARIATION   atmVclAdminStatus
            ACCESS  read-only
            DESCRIPTION
                 "atmVclAdminStatus is implemented as read-only on Nokia 7750 in
                  release 14.0."

        VARIATION   atmVclCastType
            ACCESS  read-only
            DESCRIPTION
                 "atmVclCastType is implemented as read-only on Nokia 7750 in
                  release 14.0."

        VARIATION   atmVclConnKind
            ACCESS  read-only
            DESCRIPTION
                 "atmVclConnKind is implemented as read-only on Nokia 7750 in
                  release 14.0."

        VARIATION   atmVclCrossConnectIdentifier
            ACCESS  not-implemented
            DESCRIPTION
                 "atmVclCrossConnectIdentifier is not implemented on Nokia 7750
                  in release 14.0."

        VARIATION   atmVclReceiveTrafficDescrIndex
            ACCESS  read-only
            DESCRIPTION
                 "atmVclReceiveTrafficDescrIndex is implemented as read-only on
                  Nokia 7750 in release 14.0."

        VARIATION   atmVclRowStatus
            ACCESS  read-only
            DESCRIPTION
                 "atmVclRowStatus is implemented as read-only on Nokia 7750 in
                  release 14.0."

        VARIATION   atmVclTransmitTrafficDescrIndex
            ACCESS  read-only
            DESCRIPTION
                 "atmVclTransmitTrafficDescrIndex is implemented as read-only on
                  Nokia 7750 in release 14.0."

        VARIATION   atmVplAdminStatus
            ACCESS  read-only
            DESCRIPTION
                 "atmVplAdminStatus is implemented as read-only on Nokia 7750 in
                  release 14.0."

        VARIATION   atmVplCastType
            ACCESS  read-only
            DESCRIPTION
                 "atmVplCastType is implemented as read-only on Nokia 7750 in
                  release 14.0."

        VARIATION   atmVplConnKind
            ACCESS  read-only
            DESCRIPTION
                 "atmVplConnKind is implemented as read-only on Nokia 7750 in
                  release 14.0."

        VARIATION   atmVplCrossConnectIdentifier
            ACCESS  not-implemented
            DESCRIPTION
                 "atmVplCrossConnectIdentifier is not implemented on Nokia 7750
                  in release 14.0."

        VARIATION   atmVplReceiveTrafficDescrIndex
            ACCESS  read-only
            DESCRIPTION
                 "atmVplReceiveTrafficDescrIndex is implemented as read-only on
                  Nokia 7750 in release 14.0."

        VARIATION   atmVplRowStatus
            ACCESS  read-only
            DESCRIPTION
                 "atmVplRowStatus is implemented as read-only on Nokia 7750 in
                  release 14.0."

        VARIATION   atmVplTransmitTrafficDescrIndex
            ACCESS  read-only
            DESCRIPTION
                 "atmVplTransmitTrafficDescrIndex is implemented as read-only on
                  Nokia 7750 in release 14.0."

    SUPPORTS        TIMETRA-ATM-MIB
        INCLUDES {
           tmnxAtmAal5VccStatisticsGroup,
           tmnxAtmCellVclStatisticsGroup,
-- EXCLUDE tmnxAtmCpStatisticsGroup
           tmnxAtmIfcInfoGroup,
           tmnxAtmIfcStatisticsGroup,
           tmnxAtmIlmiLinkGroup,
           tmnxAtmIlmiStatisticsGroup,
           tmnxAtmIntfConfV4v0Group,
           tmnxAtmIntfStatsV4v0Group,
           tmnxAtmNotificationsR4r0Group,
           tmnxAtmSysConfV4v0Group,
           tmnxAtmTCSublayerGroup,
           tmnxAtmVclInfoGroup,
           tmnxAtmVclInfoGroupV9v0,
           tmnxAtmVclStatisticsGroup,
           tmnxAtmVplInfoGroup,
           tmnxAtmVplStatisticsGroup,
           tmnxAtmVtlInfoGroup,
           tmnxAtmVtlStatisticsGroup
        }

        VARIATION   tAtmIlmiLinkRowStatus
            SYNTAX  RowStatus {
                       active               (1),
                    -- notInService         (2)
                    -- notReady             (3)
                       createAndGo          (4),
                    -- createAndWait        (5)
                       destroy              (6)
                    }
            DESCRIPTION
                 "tAtmIlmiLinkRowStatus supports only 'active (1)', 'createAndGo
                  (4)', and 'destroy (6)'."

    ::= { tmnx7750AgentV14v0   2 }

--
-- 7750SR-1 ATM CAPABILITIES
--
tmnx7750SR1AtmV14v0               AGENT-CAPABILITIES
    PRODUCT-RELEASE "Nokia SROS"
    STATUS          current
    DESCRIPTION
         "Implementation of ATM functions for Nokia 7750 SR-1 systems release
          14.0."

    SUPPORTS        ATM-MIB
        INCLUDES {
           aal5VccGroup,
-- EXCLUDE atmInterfaceConfGroup
           atmInterfaceConfGroup2,
-- EXCLUDE atmInterfaceDs3PlcpGroup
           atmInterfaceTCGroup,
-- EXCLUDE atmTrafficDescrGroup
-- EXCLUDE atmTrafficDescrGroup2
-- EXCLUDE atmVcCrossConnectGroup
-- EXCLUDE atmVcPvcCrossConnectGroup
-- EXCLUDE atmVccTerminationGroup
           atmVccTerminationGroup2
-- EXCLUDE atmVclCrossConnectGroup
-- EXCLUDE atmVpCrossConnectGroup
-- EXCLUDE atmVpPvcCrossConnectGroup
-- EXCLUDE atmVpcTerminationGroup
-- EXCLUDE atmVpcTerminationGroup2
-- EXCLUDE atmVplCrossConnectGroup
        }

        VARIATION   atmInterfaceAddressType
            ACCESS  not-implemented
            DESCRIPTION
                 "atmInterfaceAddressType is not implemented on Nokia 7750 SR-1
                  in release 14.0.

                  Deprecated object."

        VARIATION   atmInterfaceAdminAddress
            ACCESS  not-implemented
            DESCRIPTION
                 "atmInterfaceAdminAddress is not implemented on Nokia 7750 SR-1
                  in release 14.0.

                  Deprecated object."

        VARIATION   atmInterfaceIlmiVci
            ACCESS  read-only
            DESCRIPTION
                 "atmInterfaceIlmiVci is implemented as read-only on Nokia 7750
                  SR-1 in release 14.0."

        VARIATION   atmInterfaceIlmiVpi
            ACCESS  read-only
            DESCRIPTION
                 "atmInterfaceIlmiVpi is implemented as read-only on Nokia 7750
                  SR-1 in release 14.0."

        VARIATION   atmInterfaceMaxActiveVciBits
            ACCESS  read-only
            DESCRIPTION
                 "atmInterfaceMaxActiveVciBits is implemented as read-only on
                  Nokia 7750 SR-1 in release 14.0."

        VARIATION   atmInterfaceMaxActiveVpiBits
            ACCESS  read-only
            DESCRIPTION
                 "atmInterfaceMaxActiveVpiBits is implemented as read-only on
                  Nokia 7750 SR-1 in release 14.0."

        VARIATION   atmInterfaceMaxVccs
            ACCESS  read-only
            DESCRIPTION
                 "atmInterfaceMaxVccs is implemented as read-only on Nokia 7750
                  SR-1 in release 14.0."

        VARIATION   atmInterfaceMaxVpcs
            ACCESS  read-only
            DESCRIPTION
                 "atmInterfaceMaxVpcs is implemented as read-only on Nokia 7750
                  SR-1 in release 14.0."

        VARIATION   atmInterfaceMyNeighborIfName
            ACCESS  not-implemented
            DESCRIPTION
                 "atmInterfaceMyNeighborIfName is not implemented on Nokia 7750
                  SR-1 in release 14.0."

        VARIATION   atmInterfaceMyNeighborIpAddress
            ACCESS  not-implemented
            DESCRIPTION
                 "atmInterfaceMyNeighborIpAddress is not implemented on Nokia
                  7750 SR-1 in release 14.0."

        VARIATION   atmInterfaceSubscrAddress
            ACCESS  not-implemented
            DESCRIPTION
                 "atmInterfaceSubscrAddress is not implemented on Nokia 7750
                  SR-1 in release 14.0."

        VARIATION   atmVccAal5CpcsReceiveSduSize
            ACCESS  not-implemented
            DESCRIPTION
                 "atmVccAal5CpcsReceiveSduSize is not implemented on Nokia 7750
                  SR-1 in release 14.0."

        VARIATION   atmVccAal5CpcsTransmitSduSize
            ACCESS  not-implemented
            DESCRIPTION
                 "atmVccAal5CpcsTransmitSduSize is not implemented on Nokia 7750
                  SR-1 in release 14.0."

        VARIATION   atmVccAal5EncapsType
            ACCESS  read-only
            DESCRIPTION
                 "atmVccAal5EncapsType is implemented as read-only on Nokia 7750
                  SR-1 in release 14.0."

        VARIATION   atmVccAalType
            ACCESS  read-only
            DESCRIPTION
                 "atmVccAalType is implemented as read-only on Nokia 7750 SR-1
                  in release 14.0."

        VARIATION   atmVclAdminStatus
            ACCESS  read-only
            DESCRIPTION
                 "atmVclAdminStatus is implemented as read-only on Nokia 7750
                  SR-1 in release 14.0."

        VARIATION   atmVclCastType
            ACCESS  read-only
            DESCRIPTION
                 "atmVclCastType is implemented as read-only on Nokia 7750 SR-1
                  in release 14.0."

        VARIATION   atmVclConnKind
            ACCESS  read-only
            DESCRIPTION
                 "atmVclConnKind is implemented as read-only on Nokia 7750 SR-1
                  in release 14.0."

        VARIATION   atmVclCrossConnectIdentifier
            ACCESS  not-implemented
            DESCRIPTION
                 "atmVclCrossConnectIdentifier is not implemented on Nokia 7750
                  SR-1 in release 14.0."

        VARIATION   atmVclReceiveTrafficDescrIndex
            ACCESS  read-only
            DESCRIPTION
                 "atmVclReceiveTrafficDescrIndex is implemented as read-only on
                  Nokia 7750 SR-1 in release 14.0."

        VARIATION   atmVclRowStatus
            ACCESS  read-only
            DESCRIPTION
                 "atmVclRowStatus is implemented as read-only on Nokia 7750 SR-1
                  in release 14.0."

        VARIATION   atmVclTransmitTrafficDescrIndex
            ACCESS  read-only
            DESCRIPTION
                 "atmVclTransmitTrafficDescrIndex is implemented as read-only on
                  Nokia 7750 SR-1 in release 14.0."

        VARIATION   atmVplAdminStatus
            ACCESS  read-only
            DESCRIPTION
                 "atmVplAdminStatus is implemented as read-only on Nokia 7750
                  SR-1 in release 14.0."

        VARIATION   atmVplCastType
            ACCESS  read-only
            DESCRIPTION
                 "atmVplCastType is implemented as read-only on Nokia 7750 SR-1
                  in release 14.0."

        VARIATION   atmVplConnKind
            ACCESS  read-only
            DESCRIPTION
                 "atmVplConnKind is implemented as read-only on Nokia 7750 SR-1
                  in release 14.0."

        VARIATION   atmVplCrossConnectIdentifier
            ACCESS  not-implemented
            DESCRIPTION
                 "atmVplCrossConnectIdentifier is not implemented on Nokia 7750
                  SR-1 in release 14.0."

        VARIATION   atmVplReceiveTrafficDescrIndex
            ACCESS  read-only
            DESCRIPTION
                 "atmVplReceiveTrafficDescrIndex is implemented as read-only on
                  Nokia 7750 SR-1 in release 14.0."

        VARIATION   atmVplRowStatus
            ACCESS  read-only
            DESCRIPTION
                 "atmVplRowStatus is implemented as read-only on Nokia 7750 SR-1
                  in release 14.0."

        VARIATION   atmVplTransmitTrafficDescrIndex
            ACCESS  read-only
            DESCRIPTION
                 "atmVplTransmitTrafficDescrIndex is implemented as read-only on
                  Nokia 7750 SR-1 in release 14.0."

    SUPPORTS        TIMETRA-ATM-MIB
        INCLUDES {
           tmnxAtmAal5VccStatisticsGroup,
           tmnxAtmCellVclStatisticsGroup,
-- EXCLUDE tmnxAtmCpStatisticsGroup
           tmnxAtmIfcInfoGroup,
           tmnxAtmIfcStatisticsGroup,
           tmnxAtmIlmiLinkGroup,
           tmnxAtmIlmiStatisticsGroup,
           tmnxAtmIntfConfV4v0Group,
           tmnxAtmIntfStatsV4v0Group,
           tmnxAtmNotificationsR4r0Group,
           tmnxAtmSysConfV4v0Group,
           tmnxAtmTCSublayerGroup,
           tmnxAtmVclInfoGroup,
           tmnxAtmVclInfoGroupV9v0,
           tmnxAtmVclStatisticsGroup,
           tmnxAtmVplInfoGroup,
           tmnxAtmVplStatisticsGroup,
           tmnxAtmVtlInfoGroup,
           tmnxAtmVtlStatisticsGroup
        }

        VARIATION   tAtmCpStatsClp0CellsRxd
            ACCESS  not-implemented
            DESCRIPTION
                 "tAtmCpStatsClp0CellsRxd is not implemented on Nokia 7750 SR-1
                  in release 14.0."

        VARIATION   tAtmCpStatsClp0CellsRxdHi
            ACCESS  not-implemented
            DESCRIPTION
                 "tAtmCpStatsClp0CellsRxdHi is not implemented on Nokia 7750
                  SR-1 in release 14.0."

        VARIATION   tAtmCpStatsClp0CellsRxdLo
            ACCESS  not-implemented
            DESCRIPTION
                 "tAtmCpStatsClp0CellsRxdLo is not implemented on Nokia 7750
                  SR-1 in release 14.0."

        VARIATION   tAtmCpStatsClp0CellsTxd
            ACCESS  not-implemented
            DESCRIPTION
                 "tAtmCpStatsClp0CellsTxd is not implemented on Nokia 7750 SR-1
                  in release 14.0."

        VARIATION   tAtmCpStatsClp0CellsTxdHi
            ACCESS  not-implemented
            DESCRIPTION
                 "tAtmCpStatsClp0CellsTxdHi is not implemented on Nokia 7750
                  SR-1 in release 14.0."

        VARIATION   tAtmCpStatsClp0CellsTxdLo
            ACCESS  not-implemented
            DESCRIPTION
                 "tAtmCpStatsClp0CellsTxdLo is not implemented on Nokia 7750
                  SR-1 in release 14.0."

        VARIATION   tAtmCpStatsDrpCellsRxd
            ACCESS  not-implemented
            DESCRIPTION
                 "tAtmCpStatsDrpCellsRxd is not implemented on Nokia 7750 SR-1
                  in release 14.0."

        VARIATION   tAtmCpStatsDrpClp0CellsRxd
            ACCESS  not-implemented
            DESCRIPTION
                 "tAtmCpStatsDrpClp0CellsRxd is not implemented on Nokia 7750
                  SR-1 in release 14.0."

        VARIATION   tAtmCpStatsDrpClp0CellsTxd
            ACCESS  not-implemented
            DESCRIPTION
                 "tAtmCpStatsDrpClp0CellsTxd is not implemented on Nokia 7750
                  SR-1 in release 14.0."

        VARIATION   tAtmCpStatsTagCells
            ACCESS  not-implemented
            DESCRIPTION
                 "tAtmCpStatsTagCells is not implemented on Nokia 7750 SR-1 in
                  release 14.0."

        VARIATION   tAtmCpStatsTotalCellsRxd
            ACCESS  not-implemented
            DESCRIPTION
                 "tAtmCpStatsTotalCellsRxd is not implemented on Nokia 7750 SR-1
                  in release 14.0."

        VARIATION   tAtmCpStatsTotalCellsRxdHi
            ACCESS  not-implemented
            DESCRIPTION
                 "tAtmCpStatsTotalCellsRxdHi is not implemented on Nokia 7750
                  SR-1 in release 14.0."

        VARIATION   tAtmCpStatsTotalCellsRxdLo
            ACCESS  not-implemented
            DESCRIPTION
                 "tAtmCpStatsTotalCellsRxdLo is not implemented on Nokia 7750
                  SR-1 in release 14.0."

        VARIATION   tAtmCpStatsTotalCellsTxd
            ACCESS  not-implemented
            DESCRIPTION
                 "tAtmCpStatsTotalCellsTxd is not implemented on Nokia 7750 SR-1
                  in release 14.0."

        VARIATION   tAtmCpStatsTotalCellsTxdHi
            ACCESS  not-implemented
            DESCRIPTION
                 "tAtmCpStatsTotalCellsTxdHi is not implemented on Nokia 7750
                  SR-1 in release 14.0."

        VARIATION   tAtmCpStatsTotalCellsTxdLo
            ACCESS  not-implemented
            DESCRIPTION
                 "tAtmCpStatsTotalCellsTxdLo is not implemented on Nokia 7750
                  SR-1 in release 14.0."

        VARIATION   tAtmIlmiLinkRowStatus
            SYNTAX  RowStatus {
                       active               (1),
                    -- notInService         (2)
                    -- notReady             (3)
                       createAndGo          (4),
                    -- createAndWait        (5)
                       destroy              (6)
                    }
            DESCRIPTION
                 "tAtmIlmiLinkRowStatus supports only 'active (1)', 'createAndGo
                  (4)', and 'destroy (6)'."

    ::= { tmnx7750SR1AgentV14v0   2 }

--
-- 7450 ATM CAPABILITIES
--
tmnx7450AtmV14v0                  AGENT-CAPABILITIES
    PRODUCT-RELEASE "Nokia SROS"
    STATUS          current
    DESCRIPTION
         "Implementation of ATM functions for Nokia 7450 systems release 14.0."

    SUPPORTS        ATM-MIB
        INCLUDES {
           aal5VccGroup,
-- EXCLUDE atmInterfaceConfGroup
           atmInterfaceConfGroup2,
-- EXCLUDE atmInterfaceDs3PlcpGroup
           atmInterfaceTCGroup,
-- EXCLUDE atmTrafficDescrGroup
-- EXCLUDE atmTrafficDescrGroup2
-- EXCLUDE atmVcCrossConnectGroup
-- EXCLUDE atmVcPvcCrossConnectGroup
-- EXCLUDE atmVccTerminationGroup
           atmVccTerminationGroup2
-- EXCLUDE atmVclCrossConnectGroup
-- EXCLUDE atmVpCrossConnectGroup
-- EXCLUDE atmVpPvcCrossConnectGroup
-- EXCLUDE atmVpcTerminationGroup
-- EXCLUDE atmVpcTerminationGroup2
-- EXCLUDE atmVplCrossConnectGroup
        }

        VARIATION   atmInterfaceAddressType
            ACCESS  not-implemented
            DESCRIPTION
                 "atmInterfaceAddressType is not implemented on Nokia 7450 in
                  release 14.0.

                  Deprecated object."

        VARIATION   atmInterfaceAdminAddress
            ACCESS  not-implemented
            DESCRIPTION
                 "atmInterfaceAdminAddress is not implemented on Nokia 7450 in
                  release 14.0.

                  Deprecated object."

        VARIATION   atmInterfaceIlmiVci
            ACCESS  read-only
            DESCRIPTION
                 "atmInterfaceIlmiVci is implemented as read-only on Nokia 7450
                  in release 14.0."

        VARIATION   atmInterfaceIlmiVpi
            ACCESS  read-only
            DESCRIPTION
                 "atmInterfaceIlmiVpi is implemented as read-only on Nokia 7450
                  in release 14.0."

        VARIATION   atmInterfaceMaxActiveVciBits
            ACCESS  read-only
            DESCRIPTION
                 "atmInterfaceMaxActiveVciBits is implemented as read-only on
                  Nokia 7450 in release 14.0."

        VARIATION   atmInterfaceMaxActiveVpiBits
            ACCESS  read-only
            DESCRIPTION
                 "atmInterfaceMaxActiveVpiBits is implemented as read-only on
                  Nokia 7450 in release 14.0."

        VARIATION   atmInterfaceMaxVccs
            ACCESS  read-only
            DESCRIPTION
                 "atmInterfaceMaxVccs is implemented as read-only on Nokia 7450
                  in release 14.0."

        VARIATION   atmInterfaceMaxVpcs
            ACCESS  read-only
            DESCRIPTION
                 "atmInterfaceMaxVpcs is implemented as read-only on Nokia 7450
                  in release 14.0."

        VARIATION   atmInterfaceMyNeighborIfName
            ACCESS  not-implemented
            DESCRIPTION
                 "atmInterfaceMyNeighborIfName is not implemented on Nokia 7450
                  in release 14.0."

        VARIATION   atmInterfaceMyNeighborIpAddress
            ACCESS  not-implemented
            DESCRIPTION
                 "atmInterfaceMyNeighborIpAddress is not implemented on Nokia
                  7450 in release 14.0."

        VARIATION   atmInterfaceSubscrAddress
            ACCESS  not-implemented
            DESCRIPTION
                 "atmInterfaceSubscrAddress is not implemented on Nokia 7450 in
                  release 14.0."

        VARIATION   atmVccAal5CpcsReceiveSduSize
            ACCESS  not-implemented
            DESCRIPTION
                 "atmVccAal5CpcsReceiveSduSize is not implemented on Nokia 7450
                  in release 14.0."

        VARIATION   atmVccAal5CpcsTransmitSduSize
            ACCESS  not-implemented
            DESCRIPTION
                 "atmVccAal5CpcsTransmitSduSize is not implemented on Nokia 7450
                  in release 14.0."

        VARIATION   atmVccAal5EncapsType
            ACCESS  read-only
            DESCRIPTION
                 "atmVccAal5EncapsType is implemented as read-only on Nokia 7450
                  in release 14.0."

        VARIATION   atmVccAalType
            ACCESS  read-only
            DESCRIPTION
                 "atmVccAalType is implemented as read-only on Nokia 7450 in
                  release 14.0."

        VARIATION   atmVclAdminStatus
            ACCESS  read-only
            DESCRIPTION
                 "atmVclAdminStatus is implemented as read-only on Nokia 7450 in
                  release 14.0."

        VARIATION   atmVclCastType
            ACCESS  read-only
            DESCRIPTION
                 "atmVclCastType is implemented as read-only on Nokia 7450 in
                  release 14.0."

        VARIATION   atmVclConnKind
            ACCESS  read-only
            DESCRIPTION
                 "atmVclConnKind is implemented as read-only on Nokia 7450 in
                  release 14.0."

        VARIATION   atmVclCrossConnectIdentifier
            ACCESS  not-implemented
            DESCRIPTION
                 "atmVclCrossConnectIdentifier is not implemented on Nokia 7450
                  in release 14.0."

        VARIATION   atmVclReceiveTrafficDescrIndex
            ACCESS  read-only
            DESCRIPTION
                 "atmVclReceiveTrafficDescrIndex is implemented as read-only on
                  Nokia 7450 in release 14.0."

        VARIATION   atmVclRowStatus
            ACCESS  read-only
            DESCRIPTION
                 "atmVclRowStatus is implemented as read-only on Nokia 7450 in
                  release 14.0."

        VARIATION   atmVclTransmitTrafficDescrIndex
            ACCESS  read-only
            DESCRIPTION
                 "atmVclTransmitTrafficDescrIndex is implemented as read-only on
                  Nokia 7450 in release 14.0."

        VARIATION   atmVplAdminStatus
            ACCESS  read-only
            DESCRIPTION
                 "atmVplAdminStatus is implemented as read-only on Nokia 7450 in
                  release 14.0."

        VARIATION   atmVplCastType
            ACCESS  read-only
            DESCRIPTION
                 "atmVplCastType is implemented as read-only on Nokia 7450 in
                  release 14.0."

        VARIATION   atmVplConnKind
            ACCESS  read-only
            DESCRIPTION
                 "atmVplConnKind is implemented as read-only on Nokia 7450 in
                  release 14.0."

        VARIATION   atmVplCrossConnectIdentifier
            ACCESS  not-implemented
            DESCRIPTION
                 "atmVplCrossConnectIdentifier is not implemented on Nokia 7450
                  in release 14.0."

        VARIATION   atmVplReceiveTrafficDescrIndex
            ACCESS  read-only
            DESCRIPTION
                 "atmVplReceiveTrafficDescrIndex is implemented as read-only on
                  Nokia 7450 in release 14.0."

        VARIATION   atmVplRowStatus
            ACCESS  read-only
            DESCRIPTION
                 "atmVplRowStatus is implemented as read-only on Nokia 7450 in
                  release 14.0."

        VARIATION   atmVplTransmitTrafficDescrIndex
            ACCESS  read-only
            DESCRIPTION
                 "atmVplTransmitTrafficDescrIndex is implemented as read-only on
                  Nokia 7450 in release 14.0."

    SUPPORTS        TIMETRA-ATM-MIB
        INCLUDES {
           tmnxAtmAal5VccStatisticsGroup,
           tmnxAtmCellVclStatisticsGroup,
-- EXCLUDE tmnxAtmCpStatisticsGroup
           tmnxAtmIfcInfoGroup,
           tmnxAtmIfcStatisticsGroup,
           tmnxAtmIlmiLinkGroup,
           tmnxAtmIlmiStatisticsGroup,
           tmnxAtmIntfConfV4v0Group,
           tmnxAtmIntfStatsV4v0Group,
           tmnxAtmNotificationsR4r0Group,
           tmnxAtmSysConfV4v0Group,
           tmnxAtmTCSublayerGroup,
           tmnxAtmVclInfoGroup,
           tmnxAtmVclInfoGroupV9v0,
           tmnxAtmVclStatisticsGroup,
           tmnxAtmVplInfoGroup,
           tmnxAtmVplStatisticsGroup,
           tmnxAtmVtlInfoGroup,
           tmnxAtmVtlStatisticsGroup
        }

        VARIATION   tAtmIlmiLinkRowStatus
            SYNTAX  RowStatus {
                       active               (1),
                    -- notInService         (2)
                    -- notReady             (3)
                       createAndGo          (4),
                    -- createAndWait        (5)
                       destroy              (6)
                    }
            DESCRIPTION
                 "tAtmIlmiLinkRowStatus supports only 'active (1)', 'createAndGo
                  (4)', and 'destroy (6)'."

    ::= { tmnx7450AgentV14v0   2 }

--
-- 7450ESS-1 ATM CAPABILITIES
--
tmnx7450ESS1AtmV14v0              AGENT-CAPABILITIES
    PRODUCT-RELEASE "Nokia SROS"
    STATUS          current
    DESCRIPTION
         "Implementation of ATM functions for Nokia 7450 ESS-1 systems release
          14.0."

    SUPPORTS        ATM-MIB
        INCLUDES {
           aal5VccGroup,
-- EXCLUDE atmInterfaceConfGroup
           atmInterfaceConfGroup2,
-- EXCLUDE atmInterfaceDs3PlcpGroup
           atmInterfaceTCGroup,
-- EXCLUDE atmTrafficDescrGroup
-- EXCLUDE atmTrafficDescrGroup2
-- EXCLUDE atmVcCrossConnectGroup
-- EXCLUDE atmVcPvcCrossConnectGroup
-- EXCLUDE atmVccTerminationGroup
           atmVccTerminationGroup2
-- EXCLUDE atmVclCrossConnectGroup
-- EXCLUDE atmVpCrossConnectGroup
-- EXCLUDE atmVpPvcCrossConnectGroup
-- EXCLUDE atmVpcTerminationGroup
-- EXCLUDE atmVpcTerminationGroup2
-- EXCLUDE atmVplCrossConnectGroup
        }

        VARIATION   atmInterfaceAddressType
            ACCESS  not-implemented
            DESCRIPTION
                 "atmInterfaceAddressType is not implemented on Nokia 7450 ESS-1
                  in release 14.0.

                  Deprecated object."

        VARIATION   atmInterfaceAdminAddress
            ACCESS  not-implemented
            DESCRIPTION
                 "atmInterfaceAdminAddress is not implemented on Nokia 7450
                  ESS-1 in release 14.0.

                  Deprecated object."

        VARIATION   atmInterfaceIlmiVci
            ACCESS  read-only
            DESCRIPTION
                 "atmInterfaceIlmiVci is implemented as read-only on Nokia 7450
                  ESS-1 in release 14.0."

        VARIATION   atmInterfaceIlmiVpi
            ACCESS  read-only
            DESCRIPTION
                 "atmInterfaceIlmiVpi is implemented as read-only on Nokia 7450
                  ESS-1 in release 14.0."

        VARIATION   atmInterfaceMaxActiveVciBits
            ACCESS  read-only
            DESCRIPTION
                 "atmInterfaceMaxActiveVciBits is implemented as read-only on
                  Nokia 7450 ESS-1 in release 14.0."

        VARIATION   atmInterfaceMaxActiveVpiBits
            ACCESS  read-only
            DESCRIPTION
                 "atmInterfaceMaxActiveVpiBits is implemented as read-only on
                  Nokia 7450 ESS-1 in release 14.0."

        VARIATION   atmInterfaceMaxVccs
            ACCESS  read-only
            DESCRIPTION
                 "atmInterfaceMaxVccs is implemented as read-only on Nokia 7450
                  ESS-1 in release 14.0."

        VARIATION   atmInterfaceMaxVpcs
            ACCESS  read-only
            DESCRIPTION
                 "atmInterfaceMaxVpcs is implemented as read-only on Nokia 7450
                  ESS-1 in release 14.0."

        VARIATION   atmInterfaceMyNeighborIfName
            ACCESS  not-implemented
            DESCRIPTION
                 "atmInterfaceMyNeighborIfName is not implemented on Nokia 7450
                  ESS-1 in release 14.0."

        VARIATION   atmInterfaceMyNeighborIpAddress
            ACCESS  not-implemented
            DESCRIPTION
                 "atmInterfaceMyNeighborIpAddress is not implemented on Nokia
                  7450 ESS-1 in release 14.0."

        VARIATION   atmInterfaceSubscrAddress
            ACCESS  not-implemented
            DESCRIPTION
                 "atmInterfaceSubscrAddress is not implemented on Nokia 7450
                  ESS-1 in release 14.0."

        VARIATION   atmVccAal5CpcsReceiveSduSize
            ACCESS  not-implemented
            DESCRIPTION
                 "atmVccAal5CpcsReceiveSduSize is not implemented on Nokia 7450
                  ESS-1 in release 14.0."

        VARIATION   atmVccAal5CpcsTransmitSduSize
            ACCESS  not-implemented
            DESCRIPTION
                 "atmVccAal5CpcsTransmitSduSize is not implemented on Nokia 7450
                  ESS-1 in release 14.0."

        VARIATION   atmVccAal5EncapsType
            ACCESS  read-only
            DESCRIPTION
                 "atmVccAal5EncapsType is implemented as read-only on Nokia 7450
                  ESS-1 in release 14.0."

        VARIATION   atmVccAalType
            ACCESS  read-only
            DESCRIPTION
                 "atmVccAalType is implemented as read-only on Nokia 7450 ESS-1
                  in release 14.0."

        VARIATION   atmVclAdminStatus
            ACCESS  read-only
            DESCRIPTION
                 "atmVclAdminStatus is implemented as read-only on Nokia 7450
                  ESS-1 in release 14.0."

        VARIATION   atmVclCastType
            ACCESS  read-only
            DESCRIPTION
                 "atmVclCastType is implemented as read-only on Nokia 7450 ESS-1
                  in release 14.0."

        VARIATION   atmVclConnKind
            ACCESS  read-only
            DESCRIPTION
                 "atmVclConnKind is implemented as read-only on Nokia 7450 ESS-1
                  in release 14.0."

        VARIATION   atmVclCrossConnectIdentifier
            ACCESS  not-implemented
            DESCRIPTION
                 "atmVclCrossConnectIdentifier is not implemented on Nokia 7450
                  ESS-1 in release 14.0."

        VARIATION   atmVclReceiveTrafficDescrIndex
            ACCESS  read-only
            DESCRIPTION
                 "atmVclReceiveTrafficDescrIndex is implemented as read-only on
                  Nokia 7450 ESS-1 in release 14.0."

        VARIATION   atmVclRowStatus
            ACCESS  read-only
            DESCRIPTION
                 "atmVclRowStatus is implemented as read-only on Nokia 7450
                  ESS-1 in release 14.0."

        VARIATION   atmVclTransmitTrafficDescrIndex
            ACCESS  read-only
            DESCRIPTION
                 "atmVclTransmitTrafficDescrIndex is implemented as read-only on
                  Nokia 7450 ESS-1 in release 14.0."

        VARIATION   atmVplAdminStatus
            ACCESS  read-only
            DESCRIPTION
                 "atmVplAdminStatus is implemented as read-only on Nokia 7450
                  ESS-1 in release 14.0."

        VARIATION   atmVplCastType
            ACCESS  read-only
            DESCRIPTION
                 "atmVplCastType is implemented as read-only on Nokia 7450 ESS-1
                  in release 14.0."

        VARIATION   atmVplConnKind
            ACCESS  read-only
            DESCRIPTION
                 "atmVplConnKind is implemented as read-only on Nokia 7450 ESS-1
                  in release 14.0."

        VARIATION   atmVplCrossConnectIdentifier
            ACCESS  not-implemented
            DESCRIPTION
                 "atmVplCrossConnectIdentifier is not implemented on Nokia 7450
                  ESS-1 in release 14.0."

        VARIATION   atmVplReceiveTrafficDescrIndex
            ACCESS  read-only
            DESCRIPTION
                 "atmVplReceiveTrafficDescrIndex is implemented as read-only on
                  Nokia 7450 ESS-1 in release 14.0."

        VARIATION   atmVplRowStatus
            ACCESS  read-only
            DESCRIPTION
                 "atmVplRowStatus is implemented as read-only on Nokia 7450
                  ESS-1 in release 14.0."

        VARIATION   atmVplTransmitTrafficDescrIndex
            ACCESS  read-only
            DESCRIPTION
                 "atmVplTransmitTrafficDescrIndex is implemented as read-only on
                  Nokia 7450 ESS-1 in release 14.0."

    SUPPORTS        TIMETRA-ATM-MIB
        INCLUDES {
           tmnxAtmAal5VccStatisticsGroup,
           tmnxAtmCellVclStatisticsGroup,
-- EXCLUDE tmnxAtmCpStatisticsGroup
           tmnxAtmIfcInfoGroup,
           tmnxAtmIfcStatisticsGroup,
           tmnxAtmIlmiLinkGroup,
           tmnxAtmIlmiStatisticsGroup,
           tmnxAtmIntfConfV4v0Group,
           tmnxAtmIntfStatsV4v0Group,
           tmnxAtmNotificationsR4r0Group,
           tmnxAtmSysConfV4v0Group,
           tmnxAtmTCSublayerGroup,
           tmnxAtmVclInfoGroup,
           tmnxAtmVclInfoGroupV9v0,
           tmnxAtmVclStatisticsGroup,
           tmnxAtmVplInfoGroup,
           tmnxAtmVplStatisticsGroup,
           tmnxAtmVtlInfoGroup,
           tmnxAtmVtlStatisticsGroup
        }

        VARIATION   tAtmCpStatsClp0CellsRxd
            ACCESS  not-implemented
            DESCRIPTION
                 "tAtmCpStatsClp0CellsRxd is not implemented on Nokia 7450 ESS-1
                  in release 14.0."

        VARIATION   tAtmCpStatsClp0CellsRxdHi
            ACCESS  not-implemented
            DESCRIPTION
                 "tAtmCpStatsClp0CellsRxdHi is not implemented on Nokia 7450
                  ESS-1 in release 14.0."

        VARIATION   tAtmCpStatsClp0CellsRxdLo
            ACCESS  not-implemented
            DESCRIPTION
                 "tAtmCpStatsClp0CellsRxdLo is not implemented on Nokia 7450
                  ESS-1 in release 14.0."

        VARIATION   tAtmCpStatsClp0CellsTxd
            ACCESS  not-implemented
            DESCRIPTION
                 "tAtmCpStatsClp0CellsTxd is not implemented on Nokia 7450 ESS-1
                  in release 14.0."

        VARIATION   tAtmCpStatsClp0CellsTxdHi
            ACCESS  not-implemented
            DESCRIPTION
                 "tAtmCpStatsClp0CellsTxdHi is not implemented on Nokia 7450
                  ESS-1 in release 14.0."

        VARIATION   tAtmCpStatsClp0CellsTxdLo
            ACCESS  not-implemented
            DESCRIPTION
                 "tAtmCpStatsClp0CellsTxdLo is not implemented on Nokia 7450
                  ESS-1 in release 14.0."

        VARIATION   tAtmCpStatsDrpCellsRxd
            ACCESS  not-implemented
            DESCRIPTION
                 "tAtmCpStatsDrpCellsRxd is not implemented on Nokia 7450 ESS-1
                  in release 14.0."

        VARIATION   tAtmCpStatsDrpClp0CellsRxd
            ACCESS  not-implemented
            DESCRIPTION
                 "tAtmCpStatsDrpClp0CellsRxd is not implemented on Nokia 7450
                  ESS-1 in release 14.0."

        VARIATION   tAtmCpStatsDrpClp0CellsTxd
            ACCESS  not-implemented
            DESCRIPTION
                 "tAtmCpStatsDrpClp0CellsTxd is not implemented on Nokia 7450
                  ESS-1 in release 14.0."

        VARIATION   tAtmCpStatsTagCells
            ACCESS  not-implemented
            DESCRIPTION
                 "tAtmCpStatsTagCells is not implemented on Nokia 7450 ESS-1 in
                  release 14.0."

        VARIATION   tAtmCpStatsTotalCellsRxd
            ACCESS  not-implemented
            DESCRIPTION
                 "tAtmCpStatsTotalCellsRxd is not implemented on Nokia 7450
                  ESS-1 in release 14.0."

        VARIATION   tAtmCpStatsTotalCellsRxdHi
            ACCESS  not-implemented
            DESCRIPTION
                 "tAtmCpStatsTotalCellsRxdHi is not implemented on Nokia 7450
                  ESS-1 in release 14.0."

        VARIATION   tAtmCpStatsTotalCellsRxdLo
            ACCESS  not-implemented
            DESCRIPTION
                 "tAtmCpStatsTotalCellsRxdLo is not implemented on Nokia 7450
                  ESS-1 in release 14.0."

        VARIATION   tAtmCpStatsTotalCellsTxd
            ACCESS  not-implemented
            DESCRIPTION
                 "tAtmCpStatsTotalCellsTxd is not implemented on Nokia 7450
                  ESS-1 in release 14.0."

        VARIATION   tAtmCpStatsTotalCellsTxdHi
            ACCESS  not-implemented
            DESCRIPTION
                 "tAtmCpStatsTotalCellsTxdHi is not implemented on Nokia 7450
                  ESS-1 in release 14.0."

        VARIATION   tAtmCpStatsTotalCellsTxdLo
            ACCESS  not-implemented
            DESCRIPTION
                 "tAtmCpStatsTotalCellsTxdLo is not implemented on Nokia 7450
                  ESS-1 in release 14.0."

        VARIATION   tAtmIlmiLinkRowStatus
            SYNTAX  RowStatus {
                       active               (1),
                    -- notInService         (2)
                    -- notReady             (3)
                       createAndGo          (4),
                    -- createAndWait        (5)
                       destroy              (6)
                    }
            DESCRIPTION
                 "tAtmIlmiLinkRowStatus supports only 'active (1)', 'createAndGo
                  (4)', and 'destroy (6)'."

    ::= { tmnx7450ESS1AgentV14v0   2 }

--
-- 7710 ATM CAPABILITIES
--
tmnx7710AtmV14v0                  AGENT-CAPABILITIES
    PRODUCT-RELEASE "Nokia SROS"
    STATUS          current
    DESCRIPTION
         "Implementation of ATM functions for Nokia 7710 systems release 14.0."

    SUPPORTS        ATM-MIB
        INCLUDES {
           aal5VccGroup,
-- EXCLUDE atmInterfaceConfGroup
           atmInterfaceConfGroup2,
-- EXCLUDE atmInterfaceDs3PlcpGroup
           atmInterfaceTCGroup,
-- EXCLUDE atmTrafficDescrGroup
-- EXCLUDE atmTrafficDescrGroup2
-- EXCLUDE atmVcCrossConnectGroup
-- EXCLUDE atmVcPvcCrossConnectGroup
-- EXCLUDE atmVccTerminationGroup
           atmVccTerminationGroup2
-- EXCLUDE atmVclCrossConnectGroup
-- EXCLUDE atmVpCrossConnectGroup
-- EXCLUDE atmVpPvcCrossConnectGroup
-- EXCLUDE atmVpcTerminationGroup
-- EXCLUDE atmVpcTerminationGroup2
-- EXCLUDE atmVplCrossConnectGroup
        }

        VARIATION   atmInterfaceAddressType
            ACCESS  not-implemented
            DESCRIPTION
                 "atmInterfaceAddressType is not implemented on Nokia 7710 in
                  release 14.0.

                  Deprecated object."

        VARIATION   atmInterfaceAdminAddress
            ACCESS  not-implemented
            DESCRIPTION
                 "atmInterfaceAdminAddress is not implemented on Nokia 7710 in
                  release 14.0.

                  Deprecated object."

        VARIATION   atmInterfaceIlmiVci
            ACCESS  read-only
            DESCRIPTION
                 "atmInterfaceIlmiVci is implemented as read-only on Nokia 7710
                  in release 14.0."

        VARIATION   atmInterfaceIlmiVpi
            ACCESS  read-only
            DESCRIPTION
                 "atmInterfaceIlmiVpi is implemented as read-only on Nokia 7710
                  in release 14.0."

        VARIATION   atmInterfaceMaxActiveVciBits
            ACCESS  read-only
            DESCRIPTION
                 "atmInterfaceMaxActiveVciBits is implemented as read-only on
                  Nokia 7710 in release 14.0."

        VARIATION   atmInterfaceMaxActiveVpiBits
            ACCESS  read-only
            DESCRIPTION
                 "atmInterfaceMaxActiveVpiBits is implemented as read-only on
                  Nokia 7710 in release 14.0."

        VARIATION   atmInterfaceMaxVccs
            ACCESS  read-only
            DESCRIPTION
                 "atmInterfaceMaxVccs is implemented as read-only on Nokia 7710
                  in release 14.0."

        VARIATION   atmInterfaceMaxVpcs
            ACCESS  read-only
            DESCRIPTION
                 "atmInterfaceMaxVpcs is implemented as read-only on Nokia 7710
                  in release 14.0."

        VARIATION   atmInterfaceMyNeighborIfName
            ACCESS  not-implemented
            DESCRIPTION
                 "atmInterfaceMyNeighborIfName is not implemented on Nokia 7710
                  in release 14.0."

        VARIATION   atmInterfaceMyNeighborIpAddress
            ACCESS  not-implemented
            DESCRIPTION
                 "atmInterfaceMyNeighborIpAddress is not implemented on Nokia
                  7710 in release 14.0."

        VARIATION   atmInterfaceSubscrAddress
            ACCESS  not-implemented
            DESCRIPTION
                 "atmInterfaceSubscrAddress is not implemented on Nokia 7710 in
                  release 14.0."

        VARIATION   atmVccAal5CpcsReceiveSduSize
            ACCESS  not-implemented
            DESCRIPTION
                 "atmVccAal5CpcsReceiveSduSize is not implemented on Nokia 7710
                  in release 14.0."

        VARIATION   atmVccAal5CpcsTransmitSduSize
            ACCESS  not-implemented
            DESCRIPTION
                 "atmVccAal5CpcsTransmitSduSize is not implemented on Nokia 7710
                  in release 14.0."

        VARIATION   atmVccAal5EncapsType
            ACCESS  read-only
            DESCRIPTION
                 "atmVccAal5EncapsType is implemented as read-only on Nokia 7710
                  in release 14.0."

        VARIATION   atmVccAalType
            ACCESS  read-only
            DESCRIPTION
                 "atmVccAalType is implemented as read-only on Nokia 7710 in
                  release 14.0."

        VARIATION   atmVclAdminStatus
            ACCESS  read-only
            DESCRIPTION
                 "atmVclAdminStatus is implemented as read-only on Nokia 7710 in
                  release 14.0."

        VARIATION   atmVclCastType
            ACCESS  read-only
            DESCRIPTION
                 "atmVclCastType is implemented as read-only on Nokia 7710 in
                  release 14.0."

        VARIATION   atmVclConnKind
            ACCESS  read-only
            DESCRIPTION
                 "atmVclConnKind is implemented as read-only on Nokia 7710 in
                  release 14.0."

        VARIATION   atmVclCrossConnectIdentifier
            ACCESS  not-implemented
            DESCRIPTION
                 "atmVclCrossConnectIdentifier is not implemented on Nokia 7710
                  in release 14.0."

        VARIATION   atmVclReceiveTrafficDescrIndex
            ACCESS  read-only
            DESCRIPTION
                 "atmVclReceiveTrafficDescrIndex is implemented as read-only on
                  Nokia 7710 in release 14.0."

        VARIATION   atmVclRowStatus
            ACCESS  read-only
            DESCRIPTION
                 "atmVclRowStatus is implemented as read-only on Nokia 7710 in
                  release 14.0."

        VARIATION   atmVclTransmitTrafficDescrIndex
            ACCESS  read-only
            DESCRIPTION
                 "atmVclTransmitTrafficDescrIndex is implemented as read-only on
                  Nokia 7710 in release 14.0."

        VARIATION   atmVplAdminStatus
            ACCESS  read-only
            DESCRIPTION
                 "atmVplAdminStatus is implemented as read-only on Nokia 7710 in
                  release 14.0."

        VARIATION   atmVplCastType
            ACCESS  read-only
            DESCRIPTION
                 "atmVplCastType is implemented as read-only on Nokia 7710 in
                  release 14.0."

        VARIATION   atmVplConnKind
            ACCESS  read-only
            DESCRIPTION
                 "atmVplConnKind is implemented as read-only on Nokia 7710 in
                  release 14.0."

        VARIATION   atmVplCrossConnectIdentifier
            ACCESS  not-implemented
            DESCRIPTION
                 "atmVplCrossConnectIdentifier is not implemented on Nokia 7710
                  in release 14.0."

        VARIATION   atmVplReceiveTrafficDescrIndex
            ACCESS  read-only
            DESCRIPTION
                 "atmVplReceiveTrafficDescrIndex is implemented as read-only on
                  Nokia 7710 in release 14.0."

        VARIATION   atmVplRowStatus
            ACCESS  read-only
            DESCRIPTION
                 "atmVplRowStatus is implemented as read-only on Nokia 7710 in
                  release 14.0."

        VARIATION   atmVplTransmitTrafficDescrIndex
            ACCESS  read-only
            DESCRIPTION
                 "atmVplTransmitTrafficDescrIndex is implemented as read-only on
                  Nokia 7710 in release 14.0."

    SUPPORTS        TIMETRA-ATM-MIB
        INCLUDES {
           tmnxAtmAal5VccStatisticsGroup,
           tmnxAtmCellVclStatisticsGroup,
-- EXCLUDE tmnxAtmCpStatisticsGroup
           tmnxAtmIfcInfoGroup,
           tmnxAtmIfcStatisticsGroup,
           tmnxAtmIlmiLinkGroup,
           tmnxAtmIlmiStatisticsGroup,
           tmnxAtmIntfConfV4v0Group,
           tmnxAtmIntfStatsV4v0Group,
           tmnxAtmNotificationsR4r0Group,
           tmnxAtmSysConfV4v0Group,
           tmnxAtmTCSublayerGroup,
           tmnxAtmVclInfoGroup,
           tmnxAtmVclInfoGroupV9v0,
           tmnxAtmVclStatisticsGroup,
           tmnxAtmVplInfoGroup,
           tmnxAtmVplStatisticsGroup,
           tmnxAtmVtlInfoGroup,
           tmnxAtmVtlStatisticsGroup
        }

        VARIATION   tAtmIlmiLinkRowStatus
            SYNTAX  RowStatus {
                       active               (1),
                    -- notInService         (2)
                    -- notReady             (3)
                       createAndGo          (4),
                    -- createAndWait        (5)
                       destroy              (6)
                    }
            DESCRIPTION
                 "tAtmIlmiLinkRowStatus supports only 'active (1)', 'createAndGo
                  (4)', and 'destroy (6)'."

    ::= { tmnx7710AgentV14v0   2 }

--
-- SROS BFD CAPABILITIES
--
tmnxSROSBfdV14v0                  AGENT-CAPABILITIES
    PRODUCT-RELEASE "Nokia SROS"
    STATUS          current
    DESCRIPTION
         "Implementation of Dynamic Services on Nokia SROS systems release
          14.0."

    SUPPORTS        TIMETRA-BFD-MIB
        INCLUDES {
           tmnxBfdV11v0Group,
           tmnxBfdV13v0Group,
           tmnxBfdV13v0NotificationGroup,
           tmnxBfdV13v0NotifyObjsGroup
        }

    ::= { tmnxSROSAgentV14v0  86 }

--
-- SROS BGP CAPABILITIES
--
tmnxSROSBgpV14v0                  AGENT-CAPABILITIES
    PRODUCT-RELEASE "Nokia SROS"
    STATUS          current
    DESCRIPTION
         "Implementation of BGP functions for Nokia SROS systems release 14.0."

    SUPPORTS        BGP4-MIB
        INCLUDES {
           bgp4MIBGlobalsGroup,
           bgp4MIBNotificationGroup,
           bgp4MIBPathAttrGroup,
           bgp4MIBPeerGroup
        }

        VARIATION   bgp4PathAttrASPathSegment
            SYNTAX  OCTET STRING (SIZE (0|2..255))
            DESCRIPTION
                 "An octet string of size 'zero' is returned if there are no
                  elements in the Autonomous System (AS) path segments."

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds.

                  bgpPeerMinASOriginationInterval is not implemented on Nokia
                  SROS in release 14.0."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
           tmnxBgpDPOscilationV11v0Group,
           tmnxBgpDisableCapNegoV9v0Group,
           tmnxBgpDynPeerLmtNtfnV13v0Group,
           tmnxBgpDynamicPeerLmtV13v0Group,
           tmnxBgpEntropyLabelV14v0Group,
           tmnxBgpFlowSpecV9v0Group,
           tmnxBgpGlobalDCGroup,
           tmnxBgpGlobalV10v0Group,
           tmnxBgpGlobalV13v0Group,
           tmnxBgpGlobalV13v1Group,
           tmnxBgpInstanceParamsV14v4Group,
           tmnxBgpInstanceParamsV5v0Group,
           tmnxBgpInstanceParamsV6v0Group,
           tmnxBgpInstanceV14v0Group,
           tmnxBgpInstanceV8v0Group,
           tmnxBgpLabelRtTunnelV13v0Group,
           tmnxBgpLabelRtTunnelV14v0Group,
           tmnxBgpLblRibSeparateV14v0Group,
           tmnxBgpLinkBandwidthExtCommGroup,
           tmnxBgpMcastIpv6Group,
           tmnxBgpMultiPathV14v0Group,
           tmnxBgpMvpnVrfImportGroup,
           tmnxBgpNHUnchangedGroup,
           tmnxBgpNotificationV12v0Group,
           tmnxBgpNotificationV13v0Group,
           tmnxBgpNotificationV13v1Group,
           tmnxBgpNotificationV7v0Group,
           tmnxBgpNotifyObjsV11v0Group,
           tmnxBgpNotifyObjsV12v0Group,
           tmnxBgpNotifyObjsV7v0Group,
           tmnxBgpObsoleteV13v0Group,
           tmnxBgpObsoletedNtfnV13v0Group,
           tmnxBgpPeerGroupParamsV14v4Group,
           tmnxBgpPeerGroupParamsV5v0Group,
           tmnxBgpPeerGroupParamsV6v0Group,
           tmnxBgpPeerGroupV11v0Group,
           tmnxBgpPeerGroupV13v0Group,
           tmnxBgpPeerGroupV13v1Group,
           tmnxBgpPeerNgDynamicV13v0Group,
           tmnxBgpPeerNgEvpnMplsV13v0Group,
           tmnxBgpPeerNgV13v0Group,
           tmnxBgpPeerNgV14v0Group,
           tmnxBgpPeerParamsGroup,
           tmnxBgpPeerParamsV6v0Group,
           tmnxBgpPeerV13v0Group,
           tmnxBgpPeerV8v0Group,
           tmnxBgpPeerV9v0Group,
           tmnxBgpPeeringPlcyV10v0Group,
           tmnxBgpPeeringPolicyV10v0Group,
           tmnxBgpPrefixOriginValidGroup,
           tmnxBgpRTConstraintV10v0Group,
           tmnxBgpResolveLabelRoutesGroup,
           tmnxBgpRibLeakImportV13v0Group,
           tmnxBgpRibRouteImportV14v0Group,
           tmnxBgpShortcutTunnelV13v0Group,
           tmnxBgpShortcutTunnelV14v0Group,
           tmnxBgpThirdPartyNHGroup,
           tmnxPeerNgV14v1Group
        }

        VARIATION   tBgpInstanceAdvertiseExternal
            SYNTAX  BITS {
                    -- unused               (0)
                       ipv4                 (1),
                    -- vpnIpv4              (2)
                       ipv6                 (3)
                    }
            DESCRIPTION
                 "tBgpInstanceAdvertiseExternal is supported only for 'ipv4 (1)'
                  and 'ipv6 (3)' address families.

                  An 'inconsistentValue' error is returned if an attempt is
                  made to set tBgpInstanceAdvertiseExternal for non base router
                  instance."

        VARIATION   tBgpInstanceAsPathIgnoreFamily
            SYNTAX  BITS {
                    -- unused               (0)
                       ipv4                 (1),
                       vpnIpv4              (2),
                       ipv6                 (3),
                       mcastIpv4            (4),
                       vpnIpv6              (5),
                       l2vpn                (6),
                       mvpnIpv4             (7),
                    -- mdtSafi              (8)
                    -- mspw                 (9)
                    -- flowIpv4             (10)
                    -- routeTarget          (11)
                    -- mcastVpnIpv4         (12)
                       mvpnIpv6             (13),
                    -- flowIpv6             (14)
                    -- evpn                 (15)
                       mcastIpv6            (16)
                    }
            DESCRIPTION
                 "tBgpInstanceAsPathIgnoreFamily is supported only for 'ipv4
                  (1)', 'vpnIpv4 (2)', 'ipv6 (3)', 'mcastIpv4 (4)', 'vpnIpv6
                  (5)', 'l2vpn (6)', 'mvpnIpv4 (7)' and 'mvpnIpv6 (13)'address
                  families on base router instance.

                  'mcastIpv6 (16)' address family is supported on base router
                  instance. tBgpInstanceAsPathIgnoreFamily is supported only for
                  'ipv4 (1)', and 'ipv6 (3)' address families for non-base
                  router instance. An 'inconsistentValue' error is returned if
                  an attempt is made to set the value of
                  tBgpInstanceAsPathIgnoreFamily to an unsupported family for
                  non-base router instance."

        VARIATION   tBgpInstanceBackupPath
            SYNTAX  BITS {
                    -- unused               (0)
                       ipv4                 (1),
                    -- vpnIpv4              (2)
                       ipv6                 (3)
                    }
            DESCRIPTION
                 "tBgpInstanceBackupPath is supported only for 'ipv4 (1)' and
                  'ipv6 (3)' address families."

        VARIATION   tBgpInstanceDefaultOriginate
            ACCESS  not-implemented
            DESCRIPTION
                 "tBgpInstanceDefaultOriginate is not implemented on Nokia SROS
                  in release 14.0."

        VARIATION   tBgpInstanceFamily
            SYNTAX  BITS {
                    -- unused               (0)
                       ipv4                 (1),
                       vpnIpv4              (2),
                       ipv6                 (3),
                       mcastIpv4            (4),
                       vpnIpv6              (5),
                       l2vpn                (6),
                       mvpnIpv4             (7),
                       mdtSafi              (8),
                       mspw                 (9),
                       flowIpv4             (10),
                       routeTarget          (11),
                       mcastIpv6            (16)
                    }
            DESCRIPTION
                 "tBgpInstanceFamily does not support 'unused (0)'. Only 'ipv4
                  (1)', 'ipv6 (3)' ,'mcastIpv4 (4)' and 'mcastIpv6 (16)' address
                  families are supported on non-base router instance.

                  An 'inconsistentValue' error is returned if an attempt is
                  made to set tBgpInstanceFamily to families other than 'ipv4
                  (1)', 'ipv6 (3)','mcastIpv4 (4)' and 'mcastIpv6 (16)' for
                  non-base router instance."

        VARIATION   tBgpInstanceGRAdminState
            ACCESS  not-implemented
            DESCRIPTION
                 "tBgpInstanceGRAdminState is not implemented on Nokia SROS in
                  release 14.0."

        VARIATION   tBgpInstanceGROperState
            ACCESS  not-implemented
            DESCRIPTION
                 "tBgpInstanceGROperState is not implemented on Nokia SROS in
                  release 14.0."

        VARIATION   tBgpInstanceGRPathSelectDefer
            ACCESS  read-only
            DESCRIPTION
                 "tBgpInstanceGRPathSelectDefer is implemented as read-only on
                  Nokia SROS in release 14.0."

        VARIATION   tBgpInstanceIgpShortcut
            SYNTAX  BITS {
                       te                   (0),
                       ldp                  (1),
                    -- ip                   (2)
                       mpls                 (3)
                    }
            DESCRIPTION
                 "tBgpInstanceIgpShortcut dose not support 'ip (2)'.

                  tBgpInstanceIgpShortcut is only supported on base router
                  instance. An 'inconsistentValue' error is returned if an
                  attempt is made to set tBgpInstanceIgpShortcut for non-base
                  router instance."

        VARIATION   tBgpInstanceIpv4AddPathLimit
            SYNTAX  Integer32 (0..16)
            DESCRIPTION
                 "tBgpInstanceIpv4AddPathLimit does not support the value -1 in
                  the current release."

        VARIATION   tBgpInstanceIpv6AddPathLimit
            SYNTAX  Integer32 (0..16)
            DESCRIPTION
                 "tBgpInstanceIpv6AddPathLimit does not support the value -1 in
                  the current release."

        VARIATION   tBgpInstanceLblIpv4AddPathLimit
            SYNTAX  Integer32 (0..16)
            DESCRIPTION
                 "tBgpInstanceLblIpv4AddPathLimit does not support the value -1
                  in the current release."

        VARIATION   tBgpInstanceLblIpv6AddPathLimit
            SYNTAX  Integer32 (0..16)
            DESCRIPTION
                 "tBgpInstanceLblIpv6AddPathLimit does not support the value -1
                  in the current release."

        VARIATION   tBgpInstanceRapidUpdate
            SYNTAX  BITS {
                    -- unused               (0)
                    -- ipv4                 (1)
                    -- vpnIpv4              (2)
                    -- ipv6                 (3)
                    -- mcastIpv4            (4)
                    -- vpnIpv6              (5)
                       l2vpn                (6),
                       mvpnIpv4             (7),
                       mdtSafi              (8),
                    -- mspw                 (9)
                    -- flowIpv4             (10)
                    -- routeTarget          (11)
                    -- mcastVpnIpv4         (12)
                       mvpnIpv6             (13),
                    -- flowIpv6             (14)
                       evpn                 (15)
                    }
            DESCRIPTION
                 "tBgpInstanceRapidUpdate is supported only for l2vpn(6),
                  mvpnIPv4(7), mdtSafi(8), mvpnIpv6(13) and evpn(15) address
                  families.

                  An 'inconsistentValue' error is returned if an attempt is
                  made to set tBgpInstanceRapidUpdate for non base router
                  instance."

        VARIATION   tBgpInstanceTransportTunnel
            DESCRIPTION
                 "tBgpInstanceTransportTunnel is only supported on base router
                  instance. An 'inconsistentValue' error is returned if an
                  attempt is made to set tBgpInstanceTransportTunnel for
                  non-base router instance."

        VARIATION   tBgpInstanceVpnIpv4AddPathLimit
            SYNTAX  Integer32 (0..16)
            DESCRIPTION
                 "tBgpInstanceVpnIpv4AddPathLimit does not support the value -1
                  in the current release."

        VARIATION   tBgpInstanceVpnIpv6AddPathLimit
            SYNTAX  Integer32 (0..16)
            DESCRIPTION
                 "tBgpInstanceVpnIpv6AddPathLimit does not support the value -1
                  in the current release."

        VARIATION   tBgpLabelRtTunnelFamily
            SYNTAX  INTEGER {
                    -- unused               (0)
                       ipv4                 (1),
                       vpnIpv4              (2),
                       ipv6                 (3),
                    -- mcastIpv4            (4)
                       vpnIpv6              (5)
                    -- l2vpn                (6)
                    -- mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    -- mcastIpv6            (16)
                    -- labelIpv4            (17)
                    -- labelIpv6            (18)
                    }
            DESCRIPTION
                 "Only values 'ipv4(1)', vpnIpv4(2), 'ipv6(3)' and vpnIpv6(5)
                  are supported."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGDefaultOriginate
            ACCESS  not-implemented
            DESCRIPTION
                 "tBgpPGDefaultOriginate is not implemented on Nokia SROS in
                  release 14.0."

        VARIATION   tBgpPGIpv4AddPathLimit
            SYNTAX  Integer32 (0..16)
            DESCRIPTION
                 "tBgpPGIpv4AddPathLimit does not support the value -1 in the
                  current release."

        VARIATION   tBgpPGIpv6AddPathLimit
            SYNTAX  Integer32 (0..16)
            DESCRIPTION
                 "tBgpPGIpv6AddPathLimit does not support the value -1 in the
                  current release."

        VARIATION   tBgpPGLblIpv4AddPathLimit
            SYNTAX  Integer32 (0..16)
            DESCRIPTION
                 "tBgpPGLblIpv4AddPathLimit does not support the value -1 in the
                  current release."

        VARIATION   tBgpPGLblIpv6AddPathLimit
            SYNTAX  Integer32 (0..16)
            DESCRIPTION
                 "tBgpPGLblIpv6AddPathLimit does not support the value -1 in the
                  current release."

        VARIATION   tBgpPGTTLLogId
            ACCESS  not-implemented
            DESCRIPTION
                 "tBgpPGTTLLogId is not implemented on Nokia SROS in release
                  14.0."

        VARIATION   tBgpPGVpnIpv4AddPathLimit
            SYNTAX  Integer32 (0..16)
            DESCRIPTION
                 "tBgpPGVpnIpv4AddPathLimit does not support the value -1 in the
                  current release."

        VARIATION   tBgpPGVpnIpv6AddPathLimit
            SYNTAX  Integer32 (0..16)
            DESCRIPTION
                 "tBgpPGVpnIpv6AddPathLimit does not support the value -1 in the
                  current release."

        VARIATION   tBgpPeerGroupFamily
            SYNTAX  BITS {
                    -- unused               (0)
                       ipv4                 (1),
                       vpnIpv4              (2),
                       ipv6                 (3),
                       mcastIpv4            (4),
                       vpnIpv6              (5),
                       l2vpn                (6),
                       mvpnIpv4             (7),
                       mdtSafi              (8),
                       mspw                 (9),
                       flowIpv4             (10),
                       routeTarget          (11),
                       mcastIpv6            (16)
                    }
            DESCRIPTION
                 "tBgpPeerGroupFamily does not support 'unused (0)'. Only 'ipv4
                  (1)', 'ipv6 (3)', 'mcastIpv4 (4)' and 'mcastIpv6 (16)' address
                  families are supported on non-base router instance.

                  An 'inconsistentValue' error is returned if an attempt is
                  made to set tBgpPeerGroupFamily to families other than 'ipv4
                  (1)', 'ipv6 (3)','mcastIpv4 (4)' and 'mcastIpv6 (16) for
                  non-base router instance."

        VARIATION   tBgpPeerGroupGRAdminState
            ACCESS  not-implemented
            DESCRIPTION
                 "tBgpPeerGroupGRAdminState is not implemented on Nokia SROS in
                  release 14.0."

        VARIATION   tBgpPeerGroupGROperState
            ACCESS  not-implemented
            DESCRIPTION
                 "tBgpPeerGroupGROperState is not implemented on Nokia SROS in
                  release 14.0."

        VARIATION   tBgpPeerGroupPfxLmtRowStatus
            SYNTAX  RowStatus {
                       active               (1),
                    -- notInService         (2)
                    -- notReady             (3)
                       createAndGo          (4),
                    -- createAndWait        (5)
                       destroy              (6)
                    }
            DESCRIPTION
                 "tBgpPeerGroupPfxLmtRowStatus supports only 'active (1)',
                  'createAndGo (4)', and 'destroy (6)'."

        VARIATION   tBgpPeerNgAdvLabelAddrFamily
            DESCRIPTION
                 "tBgpPeerNgAdvertiseLdpPrefix is supported only for 'ipv4 (2)'
                  family on non-base router instance. An 'inconsistentValue'
                  error is returned if an attempt is made to set
                  tBgpPeerNgAdvertiseLdpPrefix to 'ipv6(1)' for non base router
                  instance."

        VARIATION   tBgpPeerNgAdvertiseLdpPrefix
            DESCRIPTION
                 "tBgpPeerNgAdvertiseLdpPrefix is supported only when
                  tBgpPeerNgAdvLabelAddrFamily is set to 'ipv4'.

                  When tBgpPeerNgAdvLabelAddrFamily is set to 'ipv6', an
                  attempt to set tBgpPeerNgAdvertiseLdpPrefix to 'true' results
                  in an 'inconsistentValue' error."

        VARIATION   tBgpPeerNgDefaultOriginate
            ACCESS  not-implemented
            DESCRIPTION
                 "tBgpPeerNgDefaultOriginate is not implemented on Nokia SROS in
                  release 14.0."

        VARIATION   tBgpPeerNgFamily
            SYNTAX  BITS {
                    -- unused               (0)
                       ipv4                 (1),
                       vpnIpv4              (2),
                       ipv6                 (3),
                       mcastIpv4            (4),
                       vpnIpv6              (5),
                       l2vpn                (6),
                       mvpnIpv4             (7),
                       mdtSafi              (8),
                       mspw                 (9),
                       flowIpv4             (10),
                       routeTarget          (11),
                       mcastIpv6            (16)
                    }
            DESCRIPTION
                 "tBgpPeerNgFamily does not support 'unused (0)'. Only 'ipv4
                  (1)', 'ipv6 (3)', 'mcastIpv4 (4)' and 'mcastIpv6 (16)' address
                  families are supported on non-base router instance.

                  An 'inconsistentValue' error is returned if an attempt is
                  made to set tBgpPeerNgFamily to families other than 'ipv4
                  (1)', 'ipv6 (3)','mcastIpv4 (4)' and 'mcastIpv6 (16) for
                  non-base router instance."

        VARIATION   tBgpPeerNgGRAdminState
            ACCESS  not-implemented
            DESCRIPTION
                 "tBgpPeerNgGRAdminState is not implemented on Nokia SROS in
                  release 14.0."

        VARIATION   tBgpPeerNgGROperState
            ACCESS  not-implemented
            DESCRIPTION
                 "tBgpPeerNgGROperState is not implemented on Nokia SROS in
                  release 14.0."

        VARIATION   tBgpPeerNgIpv4AddPathLimit
            SYNTAX  Integer32 (0..16)
            DESCRIPTION
                 "tBgpPeerNgIpv4AddPathLimit does not support the value -1 in
                  the current release."

        VARIATION   tBgpPeerNgIpv6AddPathLimit
            SYNTAX  Integer32 (0..16)
            DESCRIPTION
                 "tBgpPeerNgIpv6AddPathLimit does not support the value -1 in
                  the current release."

        VARIATION   tBgpPeerNgLblIpv4AddPathLimit
            SYNTAX  Integer32 (0..16)
            DESCRIPTION
                 "tBgpPeerNgLblIpv4AddPathLimit does not support the value -1 in
                  the current release."

        VARIATION   tBgpPeerNgLblIpv6AddPathLimit
            SYNTAX  Integer32 (0..16)
            DESCRIPTION
                 "tBgpPeerNgLblIpv6AddPathLimit does not support the value -1 in
                  the current release."

        VARIATION   tBgpPeerNgPfxLmtRowStatus
            SYNTAX  RowStatus {
                       active               (1),
                    -- notInService         (2)
                    -- notReady             (3)
                       createAndGo          (4),
                    -- createAndWait        (5)
                       destroy              (6)
                    }
            DESCRIPTION
                 "tBgpPeerNgPfxLmtRowStatus supports only 'active (1)',
                  'createAndGo (4)', and 'destroy (6)'."

        VARIATION   tBgpPeerNgVpnIpv4AddPathLimit
            SYNTAX  Integer32 (0..16)
            DESCRIPTION
                 "tBgpPeerNgVpnIpv4AddPathLimit does not support the value -1 in
                  the current release."

        VARIATION   tBgpPeerNgVpnIpv6AddPathLimit
            SYNTAX  Integer32 (0..16)
            DESCRIPTION
                 "tBgpPeerNgVpnIpv6AddPathLimit does not support the value -1 in
                  the current release."

        VARIATION   tBgpPrngPlcyMaxPrefixLogOnly
            ACCESS  read-only
            DESCRIPTION
                 "tBgpPrngPlcyMaxPrefixLogOnly is implemented as read-only on
                  Nokia SROS in release 14.0."

        VARIATION   tBgpPrngPlcyMaxPrefixThreshold
            ACCESS  read-only
            DESCRIPTION
                 "tBgpPrngPlcyMaxPrefixThreshold is implemented as read-only on
                  Nokia SROS in release 14.0."

        VARIATION   tBgpRibLeakImportPolicyFamily
            SYNTAX  INTEGER {
                    -- unused               (0)
                       ipv4                 (1),
                    -- vpnIpv4              (2)
                       ipv6                 (3)
                    -- mcastIpv4            (4)
                    -- vpnIpv6              (5)
                    -- l2vpn                (6)
                    -- mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    -- mcastIpv6            (16)
                    -- labelIpv4            (17)
                    -- labelIpv6            (18)
                    }
            DESCRIPTION
                 "Only values 'ipv4(1)' and 'ipv6(3)' are supported."

        VARIATION   tBgpShortcutTunnelFamily
            SYNTAX  INTEGER {
                    -- unused               (0)
                       ipv4                 (1),
                    -- vpnIpv4              (2)
                       ipv6                 (3)
                    -- mcastIpv4            (4)
                    -- vpnIpv6              (5)
                    -- l2vpn                (6)
                    -- mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    -- mcastIpv6            (16)
                    -- labelIpv4            (17)
                    -- labelIpv6            (18)
                    }
            DESCRIPTION
                 "Only values 'ipv4(1)' and 'ipv6(3)' are supported."

    ::= { tmnxSROSAgentV14v0   3 }

--
-- 7450 BGP CAPABILITIES
--
tmnx7450BgpV14v0                  AGENT-CAPABILITIES
    PRODUCT-RELEASE "Nokia SROS"
    STATUS          current
    DESCRIPTION
         "Implementation of BGP functions for Nokia 7450 systems release 14.0."

    SUPPORTS        BGP4-MIB
        INCLUDES {
           bgp4MIBGlobalsGroup,
           bgp4MIBNotificationGroup,
           bgp4MIBPathAttrGroup,
           bgp4MIBPeerGroup
        }

        VARIATION   bgp4PathAttrASPathSegment
            SYNTAX  OCTET STRING (SIZE (0|2..255))
            DESCRIPTION
                 "An octet string of size 'zero' is returned if there are no
                  elements in the Autonomous System (AS) path segments."

        VARIATION   bgpBackwardTransition
            DESCRIPTION
                 "The bgpBackwardTransition notification has vRtrID appended to
                  the variable list."

        VARIATION   bgpEstablished
            DESCRIPTION
                 "The bgpEstablished notification has vRtrID appended to the
                  variable list."

        VARIATION   bgpPeerMinASOriginationInterval
            SYNTAX  INTEGER (1..255)
            DESCRIPTION
                 "The maximum supported value for
                  bgpPeerMinASOriginationInterval is 255 seconds.

                  bgpPeerMinASOriginationInterval is not implemented on Nokia
                  7450 in release 14.0."

        VARIATION   bgpPeerMinRouteAdvertisementInterval
            SYNTAX  INTEGER (1..255)
            DESCRIPTION
                 "The maximum supported value for
                  bgpPeerMinRouteAdvertisementInterval is 255 seconds."

    SUPPORTS        TIMETRA-BGP-MIB
        INCLUDES {
           tmnxBgp4ByteASNV7v0Group,
           tmnxBgp4PathAttrGroup,
           tmnxBgpAddPathV9v0R4Group,
           tmnxBgpDPOscilationV11v0Group,
           tmnxBgpDisableCapNegoV9v0Group,
           tmnxBgpDynPeerLmtNtfnV13v0Group,
           tmnxBgpDynamicPeerLmtV13v0Group,
           tmnxBgpEntropyLabelV14v0Group,
           tmnxBgpFlowSpecV9v0Group,
           tmnxBgpGlobalDCGroup,
           tmnxBgpGlobalV10v0Group,
           tmnxBgpGlobalV13v0Group,
           tmnxBgpGlobalV13v1Group,
           tmnxBgpInstanceParamsV14v4Group,
           tmnxBgpInstanceParamsV5v0Group,
           tmnxBgpInstanceParamsV6v0Group,
           tmnxBgpInstanceV14v0Group,
           tmnxBgpInstanceV8v0Group,
           tmnxBgpLabelRtTunnelV13v0Group,
           tmnxBgpLabelRtTunnelV14v0Group,
           tmnxBgpLblRibSeparateV14v0Group,
           tmnxBgpLinkBandwidthExtCommGroup,
           tmnxBgpMcastIpv6Group,
           tmnxBgpMultiPathV14v0Group,
           tmnxBgpMvpnVrfImportGroup,
           tmnxBgpNHUnchangedGroup,
           tmnxBgpNotificationV12v0Group,
           tmnxBgpNotificationV13v0Group,
           tmnxBgpNotificationV13v1Group,
           tmnxBgpNotificationV7v0Group,
           tmnxBgpNotifyObjsV11v0Group,
           tmnxBgpNotifyObjsV12v0Group,
           tmnxBgpNotifyObjsV7v0Group,
           tmnxBgpObsoleteV13v0Group,
           tmnxBgpObsoletedNtfnV13v0Group,
           tmnxBgpPeerGroupParamsV14v4Group,
           tmnxBgpPeerGroupParamsV5v0Group,
           tmnxBgpPeerGroupParamsV6v0Group,
           tmnxBgpPeerGroupV11v0Group,
           tmnxBgpPeerGroupV13v0Group,
           tmnxBgpPeerGroupV13v1Group,
           tmnxBgpPeerNgDynamicV13v0Group,
           tmnxBgpPeerNgEvpnMplsV13v0Group,
           tmnxBgpPeerNgV13v0Group,
           tmnxBgpPeerNgV14v0Group,
           tmnxBgpPeerParamsGroup,
           tmnxBgpPeerParamsV6v0Group,
           tmnxBgpPeerV13v0Group,
           tmnxBgpPeerV8v0Group,
           tmnxBgpPeerV9v0Group,
           tmnxBgpPeeringPlcyV10v0Group,
           tmnxBgpPeeringPolicyV10v0Group,
           tmnxBgpPrefixOriginValidGroup,
           tmnxBgpRTConstraintV10v0Group,
           tmnxBgpResolveLabelRoutesGroup,
           tmnxBgpRibLeakImportV13v0Group,
           tmnxBgpRibRouteImportV14v0Group,
           tmnxBgpShortcutTunnelV13v0Group,
           tmnxBgpShortcutTunnelV14v0Group,
           tmnxBgpThirdPartyNHGroup,
           tmnxPeerNgV14v1Group
        }

        VARIATION   tBgpInstanceAdvertiseExternal
            SYNTAX  BITS {
                    -- unused               (0)
                       ipv4                 (1),
                    -- vpnIpv4              (2)
                       ipv6                 (3)
                    }
            DESCRIPTION
                 "tBgpInstanceAdvertiseExternal is supported only for 'ipv4 (1)'
                  and 'ipv6 (3)' address families.

                  An 'inconsistentValue' error is returned if an attempt is
                  made to set tBgpInstanceAdvertiseExternal for non base router
                  instance."

        VARIATION   tBgpInstanceAsPathIgnoreFamily
            SYNTAX  BITS {
                    -- unused               (0)
                       ipv4                 (1),
                       vpnIpv4              (2),
                       ipv6                 (3),
                       mcastIpv4            (4),
                       vpnIpv6              (5),
                       l2vpn                (6),
                       mvpnIpv4             (7),
                    -- mdtSafi              (8)
                    -- mspw                 (9)
                    -- flowIpv4             (10)
                    -- routeTarget          (11)
                    -- mcastVpnIpv4         (12)
                       mvpnIpv6             (13),
                    -- flowIpv6             (14)
                    -- evpn                 (15)
                       mcastIpv6            (16)
                    }
            DESCRIPTION
                 "tBgpInstanceAsPathIgnoreFamily is supported only for 'ipv4
                  (1)', 'vpnIpv4 (2)', 'ipv6 (3)', 'mcastIpv4 (4)', 'vpnIpv6
                  (5)', 'l2vpn (6)', 'mvpnIpv4 (7)' and 'mvpnIpv6 (13)'address
                  families on base router instance.

                  'mcastIpv6 (16)' address family is supported on base router
                  instance. tBgpInstanceAsPathIgnoreFamily is supported only for
                  'ipv4 (1)', and 'ipv6 (3)' address families for non-base
                  router instance. An 'inconsistentValue' error is returned if
                  an attempt is made to set the value of
                  tBgpInstanceAsPathIgnoreFamily to an unsupported family for
                  non-base router instance."

        VARIATION   tBgpInstanceBackupPath
            SYNTAX  BITS {
                    -- unused               (0)
                       ipv4                 (1),
                    -- vpnIpv4              (2)
                       ipv6                 (3)
                    }
            DESCRIPTION
                 "tBgpInstanceBackupPath is supported only for 'ipv4 (1)' and
                  'ipv6 (3)' address families."

        VARIATION   tBgpInstanceDefaultOriginate
            ACCESS  not-implemented
            DESCRIPTION
                 "tBgpInstanceDefaultOriginate is not implemented on Nokia 7450
                  in release 14.0."

        VARIATION   tBgpInstanceFamily
            SYNTAX  BITS {
                    -- unused               (0)
                       ipv4                 (1),
                    -- vpnIpv4              (2)
                    -- ipv6                 (3)
                    -- mcastIpv4            (4)
                    -- vpnIpv6              (5)
                       l2vpn                (6),
                    -- mvpnIpv4             (7)
                    -- mdtSafi              (8)
                       mspw                 (9)
                    -- flowIpv4             (10)
                    -- routeTarget          (11)
                    }
            DESCRIPTION
                 "Only 'ipv4 (1)' and 'l2vpn (6)' and 'mspw (9)' families are
                  supported on the Nokia 7450."

        VARIATION   tBgpInstanceGRAdminState
            ACCESS  not-implemented
            DESCRIPTION
                 "tBgpInstanceGRAdminState is not implemented on Nokia 7450 in
                  release 14.0."

        VARIATION   tBgpInstanceGROperState
            ACCESS  not-implemented
            DESCRIPTION
                 "tBgpInstanceGROperState is not implemented on Nokia 7450 in
                  release 14.0."

        VARIATION   tBgpInstanceGRPathSelectDefer
            ACCESS  read-only
            DESCRIPTION
                 "tBgpInstanceGRPathSelectDefer is implemented as read-only on
                  Nokia 7450 in release 14.0."

        VARIATION   tBgpInstanceIgpShortcut
            SYNTAX  BITS {
                       te                   (0),
                       ldp                  (1),
                    -- ip                   (2)
                       mpls                 (3)
                    }
            DESCRIPTION
                 "tBgpInstanceIgpShortcut dose not support 'ip (2)'.

                  tBgpInstanceIgpShortcut is only supported on base router
                  instance. An 'inconsistentValue' error is returned if an
                  attempt is made to set tBgpInstanceIgpShortcut for non-base
                  router instance."

        VARIATION   tBgpInstanceIpv4AddPathLimit
            SYNTAX  Integer32 (0..16)
            DESCRIPTION
                 "tBgpInstanceIpv4AddPathLimit does not support the value -1 in
                  the current release."

        VARIATION   tBgpInstanceIpv6AddPathLimit
            SYNTAX  Integer32 (0..16)
            DESCRIPTION
                 "tBgpInstanceIpv6AddPathLimit does not support the value -1 in
                  the current release."

        VARIATION   tBgpInstanceLblIpv4AddPathLimit
            SYNTAX  Integer32 (0..16)
            DESCRIPTION
                 "tBgpInstanceLblIpv4AddPathLimit does not support the value -1
                  in the current release."

        VARIATION   tBgpInstanceLblIpv6AddPathLimit
            SYNTAX  Integer32 (0..16)
            DESCRIPTION
                 "tBgpInstanceLblIpv6AddPathLimit does not support the value -1
                  in the current release."

        VARIATION   tBgpInstanceRapidUpdate
            SYNTAX  BITS {
                    -- unused               (0)
                    -- ipv4                 (1)
                    -- vpnIpv4              (2)
                    -- ipv6                 (3)
                    -- mcastIpv4            (4)
                    -- vpnIpv6              (5)
                       l2vpn                (6)
                    -- mvpnIpv4             (7)
                    -- mdtSafi              (8)
                    }
            DESCRIPTION
                 "tBgpInstanceRapidUpdate supports only l2vpn(6) address family
                  on the SROS 7450 platform.

                  An 'inconsistentValue' error is returned if an attempt is
                  made to set tBgpInstanceRapidUpdate for non base router
                  instance."

        VARIATION   tBgpInstanceTransportTunnel
            DESCRIPTION
                 "tBgpInstanceTransportTunnel is only supported on base router
                  instance. An 'inconsistentValue' error is returned if an
                  attempt is made to set tBgpInstanceTransportTunnel for
                  non-base router instance."

        VARIATION   tBgpInstanceVpnIpv4AddPathLimit
            SYNTAX  Integer32 (0..16)
            DESCRIPTION
                 "tBgpInstanceVpnIpv4AddPathLimit does not support the value -1
                  in the current release."

        VARIATION   tBgpInstanceVpnIpv6AddPathLimit
            SYNTAX  Integer32 (0..16)
            DESCRIPTION
                 "tBgpInstanceVpnIpv6AddPathLimit does not support the value -1
                  in the current release."

        VARIATION   tBgpLabelRtTunnelFamily
            SYNTAX  INTEGER {
                    -- unused               (0)
                       ipv4                 (1),
                       vpnIpv4              (2),
                       ipv6                 (3),
                    -- mcastIpv4            (4)
                       vpnIpv6              (5)
                    -- l2vpn                (6)
                    -- mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    -- mcastIpv6            (16)
                    -- labelIpv4            (17)
                    -- labelIpv6            (18)
                    }
            DESCRIPTION
                 "Only values 'ipv4(1)', vpnIpv4(2), 'ipv6(3)' and vpnIpv6(5)
                  are supported."

        VARIATION   tBgpNgBackwardTransition
            DESCRIPTION
                 "The tBgpNgBackwardTransition notification has vRtrID appended
                  to the variable list."

        VARIATION   tBgpNgEstablished
            DESCRIPTION
                 "The tBgpNgEstablished notification has vRtrID appended to the
                  variable list."

        VARIATION   tBgpPGDefaultOriginate
            ACCESS  not-implemented
            DESCRIPTION
                 "tBgpPGDefaultOriginate is not implemented on Nokia 7450 in
                  release 14.0."

        VARIATION   tBgpPGIpv4AddPathLimit
            SYNTAX  Integer32 (0..16)
            DESCRIPTION
                 "tBgpPGIpv4AddPathLimit does not support the value -1 in the
                  current release."

        VARIATION   tBgpPGIpv6AddPathLimit
            SYNTAX  Integer32 (0..16)
            DESCRIPTION
                 "tBgpPGIpv6AddPathLimit does not support the value -1 in the
                  current release."

        VARIATION   tBgpPGLblIpv4AddPathLimit
            SYNTAX  Integer32 (0..16)
            DESCRIPTION
                 "tBgpPGLblIpv4AddPathLimit does not support the value -1 in the
                  current release."

        VARIATION   tBgpPGLblIpv6AddPathLimit
            SYNTAX  Integer32 (0..16)
            DESCRIPTION
                 "tBgpPGLblIpv6AddPathLimit does not support the value -1 in the
                  current release."

        VARIATION   tBgpPGTTLLogId
            ACCESS  not-implemented
            DESCRIPTION
                 "tBgpPGTTLLogId is not implemented on Nokia 7450 in release
                  14.0."

        VARIATION   tBgpPGVpnIpv4AddPathLimit
            SYNTAX  Integer32 (0..16)
            DESCRIPTION
                 "tBgpPGVpnIpv4AddPathLimit does not support the value -1 in the
                  current release."

        VARIATION   tBgpPGVpnIpv6AddPathLimit
            SYNTAX  Integer32 (0..16)
            DESCRIPTION
                 "tBgpPGVpnIpv6AddPathLimit does not support the value -1 in the
                  current release."

        VARIATION   tBgpPeerGroupFamily
            SYNTAX  BITS {
                    -- unused               (0)
                       ipv4                 (1),
                    -- vpnIpv4              (2)
                    -- ipv6                 (3)
                    -- mcastIpv4            (4)
                    -- vpnIpv6              (5)
                       l2vpn                (6),
                    -- mvpnIpv4             (7)
                    -- mdtSafi              (8)
                       mspw                 (9)
                    -- flowIpv4             (10)
                    -- routeTarget          (11)
                    }
            DESCRIPTION
                 "Only 'ipv4 (1)' and 'l2vpn (6)' and 'mspw (9)' families are
                  supported on the Nokia 7450 platform."

        VARIATION   tBgpPeerGroupGRAdminState
            ACCESS  not-implemented
            DESCRIPTION
                 "tBgpPeerGroupGRAdminState is not implemented on Nokia 7450 in
                  release 14.0."

        VARIATION   tBgpPeerGroupGROperState
            ACCESS  not-implemented
            DESCRIPTION
                 "tBgpPeerGroupGROperState is not implemented on Nokia 7450 in
                  release 14.0."

        VARIATION   tBgpPeerGroupPfxLmtRowStatus
            SYNTAX  RowStatus {
                       active               (1),
                    -- notInService         (2)
                    -- notReady             (3)
                       createAndGo          (4),
                    -- createAndWait        (5)
                       destroy              (6)
                    }
            DESCRIPTION
                 "tBgpPeerGroupPfxLmtRowStatus supports only 'active (1)',
                  'createAndGo (4)', and 'destroy (6)'."

        VARIATION   tBgpPeerNgAdvLabelAddrFamily
            DESCRIPTION
                 "tBgpPeerNgAdvertiseLdpPrefix is supported only for 'ipv4 (2)'
                  family on non-base router instance. An 'inconsistentValue'
                  error is returned if an attempt is made to set
                  tBgpPeerNgAdvertiseLdpPrefix to 'ipv6(1)' for non base router
                  instance."

        VARIATION   tBgpPeerNgAdvertiseLdpPrefix
            DESCRIPTION
                 "tBgpPeerNgAdvertiseLdpPrefix is supported only when
                  tBgpPeerNgAdvLabelAddrFamily is set to 'ipv4'.

                  When tBgpPeerNgAdvLabelAddrFamily is set to 'ipv6', an
                  attempt to set tBgpPeerNgAdvertiseLdpPrefix to 'true' results
                  in an 'inconsistentValue' error."

        VARIATION   tBgpPeerNgDefaultOriginate
            ACCESS  not-implemented
            DESCRIPTION
                 "tBgpPeerNgDefaultOriginate is not implemented on Nokia 7450 in
                  release 14.0."

        VARIATION   tBgpPeerNgFamily
            SYNTAX  BITS {
                    -- unused               (0)
                       ipv4                 (1),
                    -- vpnIpv4              (2)
                    -- ipv6                 (3)
                    -- mcastIpv4            (4)
                    -- vpnIpv6              (5)
                       l2vpn                (6),
                    -- mvpnIpv4             (7)
                    -- mdtSafi              (8)
                       mspw                 (9)
                    -- flowIpv4             (10)
                    -- routeTarget          (11)
                    }
            DESCRIPTION
                 "Only 'ipv4 (1)' and 'l2vpn (6)' and 'mspw (9)' families are
                  supported on the SROS 7450 platform."

        VARIATION   tBgpPeerNgGRAdminState
            ACCESS  not-implemented
            DESCRIPTION
                 "tBgpPeerNgGRAdminState is not implemented on Nokia 7450 in
                  release 14.0."

        VARIATION   tBgpPeerNgGROperState
            ACCESS  not-implemented
            DESCRIPTION
                 "tBgpPeerNgGROperState is not implemented on Nokia 7450 in
                  release 14.0."

        VARIATION   tBgpPeerNgIpv4AddPathLimit
            SYNTAX  Integer32 (0..16)
            DESCRIPTION
                 "tBgpPeerNgIpv4AddPathLimit does not support the value -1 in
                  the current release."

        VARIATION   tBgpPeerNgIpv6AddPathLimit
            SYNTAX  Integer32 (0..16)
            DESCRIPTION
                 "tBgpPeerNgIpv6AddPathLimit does not support the value -1 in
                  the current release."

        VARIATION   tBgpPeerNgLblIpv4AddPathLimit
            SYNTAX  Integer32 (0..16)
            DESCRIPTION
                 "tBgpPeerNgLblIpv4AddPathLimit does not support the value -1 in
                  the current release."

        VARIATION   tBgpPeerNgLblIpv6AddPathLimit
            SYNTAX  Integer32 (0..16)
            DESCRIPTION
                 "tBgpPeerNgLblIpv6AddPathLimit does not support the value -1 in
                  the current release."

        VARIATION   tBgpPeerNgPfxLmtRowStatus
            SYNTAX  RowStatus {
                       active               (1),
                    -- notInService         (2)
                    -- notReady             (3)
                       createAndGo          (4),
                    -- createAndWait        (5)
                       destroy              (6)
                    }
            DESCRIPTION
                 "tBgpPeerNgPfxLmtRowStatus supports only 'active (1)',
                  'createAndGo (4)', and 'destroy (6)'."

        VARIATION   tBgpPeerNgVpnIpv4AddPathLimit
            SYNTAX  Integer32 (0..16)
            DESCRIPTION
                 "tBgpPeerNgVpnIpv4AddPathLimit does not support the value -1 in
                  the current release."

        VARIATION   tBgpPeerNgVpnIpv6AddPathLimit
            SYNTAX  Integer32 (0..16)
            DESCRIPTION
                 "tBgpPeerNgVpnIpv6AddPathLimit does not support the value -1 in
                  the current release."

        VARIATION   tBgpPrngPlcyMaxPrefixLogOnly
            ACCESS  read-only
            DESCRIPTION
                 "tBgpPrngPlcyMaxPrefixLogOnly is implemented as read-only on
                  Nokia 7450 in release 14.0."

        VARIATION   tBgpPrngPlcyMaxPrefixThreshold
            ACCESS  read-only
            DESCRIPTION
                 "tBgpPrngPlcyMaxPrefixThreshold is implemented as read-only on
                  Nokia 7450 in release 14.0."

        VARIATION   tBgpRibLeakImportPolicyFamily
            SYNTAX  INTEGER {
                    -- unused               (0)
                       ipv4                 (1),
                    -- vpnIpv4              (2)
                       ipv6                 (3)
                    -- mcastIpv4            (4)
                    -- vpnIpv6              (5)
                    -- l2vpn                (6)
                    -- mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    -- mcastIpv6            (16)
                    -- labelIpv4            (17)
                    -- labelIpv6            (18)
                    }
            DESCRIPTION
                 "Only values 'ipv4(1)' and 'ipv6(3)' are supported."

        VARIATION   tBgpShortcutTunnelFamily
            SYNTAX  INTEGER {
                    -- unused               (0)
                       ipv4                 (1),
                    -- vpnIpv4              (2)
                       ipv6                 (3)
                    -- mcastIpv4            (4)
                    -- vpnIpv6              (5)
                    -- l2vpn                (6)
                    -- mvpnIpv4             (7)
                    -- mdtSafi              (8)
                    -- mspw                 (9)
                    -- flowIpv4             (10)
                    -- routeTarget          (11)
                    -- mcastVpnIpv4         (12)
                    -- mvpnIpv6             (13)
                    -- flowIpv6             (14)
                    -- evpn                 (15)
                    -- mcastIpv6            (16)
                    -- labelIpv4            (17)
                    -- labelIpv6            (18)
                    }
            DESCRIPTION
                 "Only values 'ipv4(1)' and 'ipv6(3)' are supported."

    ::= { tmnx7450AgentV14v0   3 }

--
-- 7750 BSX CAPABILITIES
--
tmnx7750BsxV14v0                  AGENT-CAPABILITIES
    PRODUCT-RELEASE "Nokia SROS"
    STATUS          current
    DESCRIPTION
         "Implementation of BSX capabilities for Nokia 7750 systems release
          14.0."

    SUPPORTS        TIMETRA-BSX-NG-MIB
        INCLUDES {
           tmnxBsxCflowdDirectExportGroup,
           tmnxBsxCflowdGroup,
           tmnxBsxCflowdGroupV10v0,
           tmnxBsxCflowdGroupV9v0,
           tmnxBsxDnsIpCacheGroupV13v0,
           tmnxBsxEventLogSyslogObjGrp,
           tmnxBsxGtpGroupV13v0,
           tmnxBsxGtpUntunnelingObjGrp,
           tmnxBsxHttpEnAntiSpfStObGrpV11v0,
           tmnxBsxHttpEnrAntiSpfObjGrpV11v0,
           tmnxBsxHttpEnrEncObjGrpV11v0,
           tmnxBsxHttpEnrStStrObjGrpV12v0,
           tmnxBsxHttpEnrichObjGroup,
           tmnxBsxHttpEnrichStatObjGroup,
           tmnxBsxHttpNotifObjGrp,
           tmnxBsxHttpNotifObjGrpV13v0,
           tmnxBsxHttpRedirErrGroup,
           tmnxBsxHttpRedirGroup,
           tmnxBsxHttpRedirObjGrpV12v0,
           tmnxBsxHttpRedirObjGrpV13v0,
           tmnxBsxHttpsCaptiveRedirObjGrp,
           tmnxBsxIpPrefixListObjGrpV12v0,
           tmnxBsxIsa2ObjGroup,
           tmnxBsxLwObjGrpV12v0,
           tmnxBsxMdaGroupV10v0,
           tmnxBsxMdaGroupV11v0,
           tmnxBsxMdaGroupV12v0,
           tmnxBsxMdaGroupV7v0,
           tmnxBsxMdaGroupV8v0,
           tmnxBsxMgBillingExclusionsGroup,
           tmnxBsxMgTetherDetectGroup,
           tmnxBsxMobileGatewayGroup,
           tmnxBsxNotificationGroup,
           tmnxBsxNotificationGroupV10v0,
           tmnxBsxNotificationGroupV11v0,
           tmnxBsxNotificationGroupV12v0,
           tmnxBsxNotificationGroupV13v0,
           tmnxBsxNotificationGroupV14v0,
           tmnxBsxNotificationGroupV7v0,
           tmnxBsxNotificationGroupV8v0,
           tmnxBsxNotificationGroupV9v0,
           tmnxBsxNotifyObjsGroup,
           tmnxBsxNotifyObjsGroupV13v0,
           tmnxBsxNotifyObjsGroupV14v0,
           tmnxBsxNotifyObjsGroupV7v0,
           tmnxBsxNotifyObjsGroupV8v0,
           tmnxBsxOvrdGroup,
           tmnxBsxPolicyObjGrp12v0,
           tmnxBsxPolicyObjGrp13v0,
           tmnxBsxPolicyTimeStampExtObjGrp,
           tmnxBsxPolicyTodObjGrp,
           tmnxBsxRadApNotificationGroup,
           tmnxBsxRadApObjGroup,
           tmnxBsxRadApStatObjGroup,
           tmnxBsxRadiusAccountingObjGroup,
           tmnxBsxRadiusAcctObjGroupV11v0,
           tmnxBsxRedundancyEnhObjGroup,
           tmnxBsxRedundancyObjGroup,
           tmnxBsxSessionFilterObjGrp,
           tmnxBsxStaticObjGroup,
           tmnxBsxStatsGroup,
           tmnxBsxStatsGroupV9v0,
           tmnxBsxStflFwEnhacementsObjGrp,
           tmnxBsxTcpMssObjGrp,
           tmnxBsxTcpValObjGrp,
           tmnxBsxTrafficStatsObjGrpV12v0,
           tmnxBsxTrafficStatsObjGrpV13v0,
           tmnxBsxTransitGroup,
           tmnxBsxTransitGroupV10v0,
           tmnxBsxTransitIpPolicyDiamObjGrp,
           tmnxBsxTransitSeenIpGroup,
           tmnxBsxTrapPerfObjGrp,
           tmnxBsxUrlFilterObjGrp,
           tmnxBsxUrlFilterObjGrpV12v0,
           tmnxBsxUrlFilterStatsObjGrp,
           tmnxBsxUrlListExtendedGroup,
           tmnxBsxUrlListGroupV13v0,
           tmnxBsxUsageMonObjGrpV12v0,
           tmnxBsxXHeaderObjGroup
        }

        VARIATION   tmnxBsxAaGrpPartRowStatus
            SYNTAX  RowStatus {
                       active               (1),
                    -- notInService         (2)
                    -- notReady             (3)
                       createAndGo          (4),
                    -- createAndWait        (5)
                       destroy              (6)
                    }
            DESCRIPTION
                 "tmnxBsxAaGrpPartRowStatus supports only 'active (1)',
                  'createAndGo (4)', and 'destroy (6)'."

        VARIATION   tmnxBsxAaIfAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfAddrType supports only the InetAddressType values
                  'unknown (0)' and 'ipv4 (1)'."

        VARIATION   tmnxBsxAaIfIsaAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfIsaAddrType supports only the InetAddressType
                  values 'unknown (0)' and 'ipv4 (1)'."

        VARIATION   tmnxBsxAarpInstPeerEPSapEncType
            SYNTAX  INTEGER {
                       unknown              (0),
                       nullEncap            (1),
                    -- qEncap               (2)
                    -- mplsEncap            (3)
                    -- bcpNullEncap         (4)
                       bcpDot1qEncap        (5),
                    -- ipcpEncap            (6)
                    -- frEncap              (7)
                    -- pppAutoEncap         (8)
                    -- atmEncap             (9)
                       qinqEncap            (10)
                    -- wanMirrorEncap       (11)
                    -- ciscoHDLCEncap       (12)
                    -- cemEncap             (13)
                    }
            DESCRIPTION
                 "tmnxBsxAarpInstPeerEPSapEncType supports only
                  TmnxPortEncapType 'unknown(0)', 'nullEncap(1)',
                  'bcpDot1qEncap(5)', and 'qinqEncap(10)'."

        VARIATION   tmnxBsxAarpInstPeerIpType
            SYNTAX  InetAddressType {
                       unknown              (0),
                       ipv4                 (1)
                    -- ipv6                 (2)
                    -- ipv4z                (3)
                    -- ipv6z                (4)
                    -- dns                  (16)
                    }
            DESCRIPTION
                 "tmnxBsxAarpInstPeerIpType supports only the InetAddressType
                  values 'unknown (0)' and 'ipv4 (1)'."

        VARIATION   tmnxBsxAarpInstRowStatus
            SYNTAX  RowStatus {
                       active               (1),
                    -- notInService         (2)
                    -- notReady             (3)
                       createAndGo          (4),
                    -- createAndWait        (5)
                       destroy              (6)
                    }
            DESCRIPTION
                 "tmnxBsxAarpInstRowStatus supports only 'active (1)',
                  'createAndGo (4)', and 'destroy (6)'."

        VARIATION   tmnxBsxAppFilterExprIndex
            SYNTAX  Integer32 (1..4)
            DESCRIPTION
                 "tmnxBsxAppFilterExprIndex supports a range from 1 to 4
                  expressions."

        VARIATION   tmnxBsxAppFilterExprOperator
            SYNTAX  TmnxBsxOperator {
                       none                 (0),
                       eq                   (1),
                       neq                  (2)
                    -- lt                   (3)
                    -- gt                   (4)
                    -- range                (5)
                    }
            DESCRIPTION
                 "tmnxBsxAppFilterExprOperator only supports TmnxBsxOperator
                  values of 'none (0)', 'eq (1)' and 'neq (2)."

        VARIATION   tmnxBsxAppFilterNetworkAddrOp
            SYNTAX  TmnxBsxOperator {
                       none                 (0),
                       eq                   (1),
                       neq                  (2)
                    -- lt                   (3)
                    -- gt                   (4)
                    -- range                (5)
                    }
            DESCRIPTION
                 "tmnxBsxAppFilterNetworkAddrOp only supports TmnxBsxOperator
                  values of 'none (0)', 'eq (1)' and 'neq (2)."

        VARIATION   tmnxBsxAppFilterNetworkAddrType
            SYNTAX  InetAddressType {
                       unknown              (0),
                       ipv4                 (1),
                       ipv6                 (2)
                    -- ipv4z                (3)
                    -- ipv6z                (4)
                    -- dns                  (16)
                    }
            DESCRIPTION
                 "tmnxBsxAppFilterNetworkAddrType supports only the
                  InetAddressType values 'unknown (0)', 'ipv4 (1)', and 'ipv6
                  (2)'."

        VARIATION   tmnxBsxAppFilterServerAddrOp
            SYNTAX  TmnxBsxOperator {
                       none                 (0),
                       eq                   (1),
                       neq                  (2)
                    -- lt                   (3)
                    -- gt                   (4)
                    -- range                (5)
                    }
            DESCRIPTION
                 "tmnxBsxAppFilterServerAddrOp only supports TmnxBsxOperator
                  values of 'none (0)', 'eq (1)' and 'neq (2)."

        VARIATION   tmnxBsxAppFilterServerAddrType
            SYNTAX  InetAddressType {
                       unknown              (0),
                       ipv4                 (1),
                       ipv6                 (2)
                    -- ipv4z                (3)
                    -- ipv6z                (4)
                    -- dns                  (16)
                    }
            DESCRIPTION
                 "tmnxBsxAppFilterServerAddrType supports only the
                  InetAddressType values 'unknown (0)', 'ipv4 (1)', and 'ipv6
                  (2)'."

        VARIATION   tmnxBsxAppFilterServerPortOp
            SYNTAX  TmnxBsxOperator {
                       none                 (0),
                       eq                   (1),
                       neq                  (2),
                       lt                   (3),
                       gt                   (4)
                    -- range                (5)
                    }
            DESCRIPTION
                 "tmnxBsxAppFilterServerPortOp only supports TmnxBsxOperator
                  values of 'none (0)', 'eq (1)', 'neq (2)', 'lt (3)' and 'gt
                  (4)."

        VARIATION   tmnxBsxAppGrpRowStatus
            SYNTAX  RowStatus {
                       active               (1),
                    -- notInService         (2)
                    -- notReady             (3)
                       createAndGo          (4),
                    -- createAndWait        (5)
                       destroy              (6)
                    }
            DESCRIPTION
                 "tmnxBsxAppGrpRowStatus supports only 'active (1)',
                  'createAndGo (4)', and 'destroy (6)'."

        VARIATION   tmnxBsxAppGrpStorageType
            SYNTAX  StorageType {
                    -- other(1)
                    -- volatile(2)
                       nonVolatile(3),
                       permanent(4)
                    -- readOnly(5)
                    }
            DESCRIPTION
                 "tmnxBsxAppGrpStorageType supports only the values 'nonVolatile
                  (3)' and 'permanent (4)'."

        VARIATION   tmnxBsxAppProfRowStatus
            SYNTAX  RowStatus {
                       active               (1),
                    -- notInService         (2)
                    -- notReady             (3)
                       createAndGo          (4),
                    -- createAndWait        (5)
                       destroy              (6)
                    }
            DESCRIPTION
                 "tmnxBsxAppProfRowStatus supports only 'active (1)',
                  'createAndGo (4)', and 'destroy (6)'."

        VARIATION   tmnxBsxAppRowStatus
            SYNTAX  RowStatus {
                       active               (1),
                    -- notInService         (2)
                    -- notReady             (3)
                       createAndGo          (4),
                    -- createAndWait        (5)
                       destroy              (6)
                    }
            DESCRIPTION
                 "tmnxBsxAppRowStatus supports only 'active (1)', 'createAndGo
                  (4)', and 'destroy (6)'."

        VARIATION   tmnxBsxAppStorageType
            SYNTAX  StorageType {
                    -- other(1)
                    -- volatile(2)
                       nonVolatile(3),
                       permanent(4)
                    -- readOnly(5)
                    }
            DESCRIPTION
                 "tmnxBsxAppStorageType supports only the values 'nonVolatile
                  (3)' and 'permanent (4)'."

        VARIATION   tmnxBsxAqpBaseRowStatus
            SYNTAX  RowStatus {
                       active               (1),
                    -- notInService         (2)
                    -- notReady             (3)
                       createAndGo          (4),
                    -- createAndWait        (5)
                       destroy              (6)
                    }
            DESCRIPTION
                 "tmnxBsxAqpBaseRowStatus supports only 'active (1)',
                  'createAndGo (4)', and 'destroy (6)'."

        VARIATION   tmnxBsxAqpCharOperator
            SYNTAX  TmnxBsxOperator {
                    -- none                 (0)
                       eq                   (1)
                    -- neq                  (2)
                    -- lt                   (3)
                    -- gt                   (4)
                    -- range                (5)
                    }
            DESCRIPTION
                 "tmnxBsxAqpCharOperator only supports the TmnxBsxOperator value
                  of 'eq (1)'."

        VARIATION   tmnxBsxAqpCharRowStatus
            SYNTAX  RowStatus {
                       active               (1),
                    -- notInService         (2)
                    -- notReady             (3)
                       createAndGo          (4),
                    -- createAndWait        (5)
                       destroy              (6)
                    }
            DESCRIPTION
                 "tmnxBsxAqpCharRowStatus supports only 'active (1)',
                  'createAndGo (4)', and 'destroy (6)'."

        VARIATION   tmnxBsxAqpChargeGrpOp
            SYNTAX  TmnxBsxOperator {
                       none                 (0),
                       eq                   (1),
                       neq                  (2)
                    -- lt                   (3)
                    -- gt                   (4)
                    -- range                (5)
                    }
            DESCRIPTION
                 "tmnxBsxAqpChargeGrpOp only supports TmnxBsxOperator values of
                  'none (0)', 'eq (1)' and 'neq (2)."

        VARIATION   tmnxBsxAqpDstAddress
            SYNTAX  InetAddress (SIZE (0|4))
            DESCRIPTION
                 "tmnxBsxAqpDstAddress only supports InetAddressType 'unknown
                  (0)' and 'ipv4 (1)'."

        VARIATION   tmnxBsxAqpDstAddressOp
            SYNTAX  TmnxBsxOperator {
                       none                 (0),
                       eq                   (1),
                       neq                  (2)
                    -- lt                   (3)
                    -- gt                   (4)
                    -- range                (5)
                    }
            DESCRIPTION
                 "tmnxBsxAqpDstAddressOp only supports TmnxBsxOperator values of
                  'none (0)', 'eq (1)' and 'neq (2)."

        VARIATION   tmnxBsxAqpDstAddressType
            SYNTAX  InetAddressType {
                       unknown              (0),
                       ipv4                 (1)
                    -- ipv6                 (2)
                    -- ipv4z                (3)
                    -- ipv6z                (4)
                    -- dns                  (16)
                    }
            DESCRIPTION
                 "tmnxBsxAqpDstAddressType supports only the InetAddressType
                  values 'unknown (0)' and 'ipv4 (1)'."

        VARIATION   tmnxBsxAqpDstPortOp
            SYNTAX  TmnxBsxOperator {
                       none                 (0),
                       eq                   (1),
                       neq                  (2)
                    -- lt                   (3)
                    -- gt                   (4)
                    -- range                (5)
                    }
            DESCRIPTION
                 "tmnxBsxAqpDstPortOp only supports TmnxBsxOperator values of
                  'none (0)', 'eq (1)' and 'neq (2)."

        VARIATION   tmnxBsxAqpIpProtocolNumOp
            SYNTAX  TmnxBsxOperator {
                       none                 (0),
                       eq                   (1),
                       neq                  (2)
                    -- lt                   (3)
                    -- gt                   (4)
                    -- range                (5)
                    }
            DESCRIPTION
                 "tmnxBsxAqpIpProtocolNumOp only supports TmnxBsxOperator values
                  of 'none (0)', 'eq (1)' and 'neq (2)."

        VARIATION   tmnxBsxAqpOutOfOrderFrags
            ACCESS  not-implemented
            DESCRIPTION
                 "tmnxBsxAqpOutOfOrderFrags is not implemented on Nokia 7750 in
                  release 14.0."

        VARIATION   tmnxBsxAqpSapSubscrOp
            SYNTAX  TmnxBsxOperator {
                       none                 (0),
                       eq                   (1),
                       neq                  (2)
                    -- lt                   (3)
                    -- gt                   (4)
                    -- range                (5)
                    }
            DESCRIPTION
                 "tmnxBsxAqpSapSubscrOp only supports TmnxBsxOperator values of
                  'none (0)', 'eq (1)' and 'neq (2)."

        VARIATION   tmnxBsxAqpSrcAddress
            SYNTAX  InetAddress (SIZE (0|4))
            DESCRIPTION
                 "tmnxBsxAqpSrcAddress only supports InetAddressType 'unknown
                  (0)' and 'ipv4 (1)'."

        VARIATION   tmnxBsxAqpSrcAddressOp
            SYNTAX  TmnxBsxOperator {
                       none                 (0),
                       eq                   (1),
                       neq                  (2)
                    -- lt                   (3)
                    -- gt                   (4)
                    -- range                (5)
                    }
            DESCRIPTION
                 "tmnxBsxAqpSrcAddressOp only supports TmnxBsxOperator values of
                  'none (0)', 'eq (1)' and 'neq (2)."

        VARIATION   tmnxBsxAqpSrcAddressType
            SYNTAX  InetAddressType {
                       unknown              (0),
                       ipv4                 (1)
                    -- ipv6                 (2)
                    -- ipv4z                (3)
                    -- ipv6z                (4)
                    -- dns                  (16)
                    }
            DESCRIPTION
                 "tmnxBsxAqpSrcAddressType supports only the InetAddressType
                  values 'unknown (0)' and 'ipv4 (1)'."

        VARIATION   tmnxBsxAqpSrcPortOp
            SYNTAX  TmnxBsxOperator {
                       none                 (0),
                       eq                   (1),
                       neq                  (2)
                    -- lt                   (3)
                    -- gt                   (4)
                    -- range                (5)
                    }
            DESCRIPTION
                 "tmnxBsxAqpSrcPortOp only supports TmnxBsxOperator values of
                  'none (0)', 'eq (1)' and 'neq (2)."

        VARIATION   tmnxBsxAsoPersistId
            ACCESS  not-implemented
            DESCRIPTION
                 "tmnxBsxAsoPersistId is not implemented on Nokia 7750 in
                  release 14.0."

        VARIATION   tmnxBsxAsoRowStatus
            SYNTAX  RowStatus {
                       active               (1),
                    -- notInService         (2)
                    -- notReady             (3)
                       createAndGo          (4),
                    -- createAndWait        (5)
                       destroy              (6)
                    }
            DESCRIPTION
                 "tmnxBsxAsoRowStatus supports only 'active (1)', 'createAndGo
                  (4)', and 'destroy (6)'."

        VARIATION   tmnxBsxAsoValPersistId
            ACCESS  not-implemented
            DESCRIPTION
                 "tmnxBsxAsoValPersistId is not implemented on Nokia 7750 in
                  release 14.0."

        VARIATION   tmnxBsxAsoValRowStatus
            SYNTAX  RowStatus {
                       active               (1),
                    -- notInService         (2)
                    -- notReady             (3)
                       createAndGo          (4),
                    -- createAndWait        (5)
                       destroy              (6)
                    }
            DESCRIPTION
                 "tmnxBsxAsoValRowStatus supports only 'active (1)',
                  'createAndGo (4)', and 'destroy (6)'."

        VARIATION   tmnxBsxCflowdCollAddress
            SYNTAX  InetAddress (SIZE (0|4))
            DESCRIPTION
                 "tmnxBsxCflowdCollAddress only supports InetAddressType
                  'unknown (0)' and 'ipv4 (1)'."

        VARIATION   tmnxBsxCflowdCollAddressType
            SYNTAX  InetAddressType {
                       unknown              (0),
                       ipv4                 (1)
                    -- ipv6                 (2)
                    -- ipv4z                (3)
                    -- ipv6z                (4)
                    -- dns                  (16)
                    }
            DESCRIPTION
                 "tmnxBsxCflowdCollAddressType supports only the InetAddressType
                  values 'unknown (0)' and 'ipv4 (1)'."

        VARIATION   tmnxBsxCflowdCollRowStatus
            SYNTAX  RowStatus {
                       active               (1),
                    -- notInService         (2)
                    -- notReady             (3)
                       createAndGo          (4),
                    -- createAndWait        (5)
                       destroy              (6)
                    }
            DESCRIPTION
                 "tmnxBsxCflowdCollRowStatus supports only 'active (1)',
                  'createAndGo (4)', and 'destroy (6)'."

        VARIATION   tmnxBsxCflowdDirExpAddrRowStatus
            SYNTAX  RowStatus {
                       active               (1),
                    -- notInService         (2)
                    -- notReady             (3)
                       createAndGo          (4),
                    -- createAndWait        (5)
                       destroy              (6)
                    }
            DESCRIPTION
                 "tmnxBsxCflowdDirExpAddrRowStatus supports only 'active (1)',
                  'createAndGo (4)', and 'destroy (6)'."

        VARIATION   tmnxBsxCflowdDirectExpRowStatus
            SYNTAX  RowStatus {
                       active               (1),
                    -- notInService         (2)
                    -- notReady             (3)
                       createAndGo          (4),
                    -- createAndWait        (5)
                       destroy              (6)
                    }
            DESCRIPTION
                 "tmnxBsxCflowdDirectExpRowStatus supports only 'active (1)',
                  'createAndGo (4)', and 'destroy (6)'."

        VARIATION   tmnxBsxCflowdPerfExpRowStatus
            SYNTAX  RowStatus {
                       active               (1),
                    -- notInService         (2)
                    -- notReady             (3)
                       createAndGo          (4),
                    -- createAndWait        (5)
                       destroy              (6)
                    }
            DESCRIPTION
                 "tmnxBsxCflowdPerfExpRowStatus supports only 'active (1)',
                  'createAndGo (4)', and 'destroy (6)'."

        VARIATION   tmnxBsxChargeGrpRowStatus
            SYNTAX  RowStatus {
                       active               (1),
                    -- notInService         (2)
                    -- notReady             (3)
                       createAndGo          (4),
                    -- createAndWait        (5)
                       destroy              (6)
                    }
            DESCRIPTION
                 "tmnxBsxChargeGrpRowStatus supports only 'active (1)',
                  'createAndGo (4)', and 'destroy (6)'."

        VARIATION   tmnxBsxCustProtEntryId
            SYNTAX  TEntryId (1..10)
            DESCRIPTION
                 "tmnxBsxCustProtEntryId supports a range from 1 to 10 custom
                  protocol entries."

        VARIATION   tmnxBsxCustProtExprIndex
            SYNTAX  Integer32 (1)
            DESCRIPTION
                 "tmnxBsxCustProtExprIndex only supports 1 custom protocol
                  expression."

        VARIATION   tmnxBsxCustProtExprOperator
            SYNTAX  TmnxBsxOperator {
                    -- none                 (0)
                       eq                   (1)
                    -- neq                  (2)
                    -- lt                   (3)
                    -- gt                   (4)
                    -- range                (5)
                    }
            DESCRIPTION
                 "tmnxBsxCustProtExprOperator only supports the TmnxBsxOperator
                  value of 'eq (1)'."

        VARIATION   tmnxBsxCustProtExprRowStatus
            SYNTAX  RowStatus {
                       active               (1),
                    -- notInService         (2)
                    -- notReady             (3)
                       createAndGo          (4),
                    -- createAndWait        (5)
                       destroy              (6)
                    }
            DESCRIPTION
                 "tmnxBsxCustProtExprRowStatus supports only 'active (1)',
                  'createAndGo (4)', and 'destroy (6)'."

        VARIATION   tmnxBsxCustProtIpProtocolNum
            DESCRIPTION
                 "tmnxBsxCustProtIpProtocolNum supports only the values not set
                  (-1), tcp (6) and udp (17)."

        VARIATION   tmnxBsxCustProtRowStatus
            SYNTAX  RowStatus {
                       active               (1),
                    -- notInService         (2)
                    -- notReady             (3)
                       createAndGo          (4),
                    -- createAndWait        (5)
                       destroy              (6)
                    }
            DESCRIPTION
                 "tmnxBsxCustProtRowStatus supports only 'active (1)',
                  'createAndGo (4)', and 'destroy (6)'."

        VARIATION   tmnxBsxDnsIpCacheDomainRowStatus
            SYNTAX  RowStatus {
                       active               (1),
                    -- notInService         (2)
                    -- notReady             (3)
                       createAndGo          (4),
                    -- createAndWait        (5)
                       destroy              (6)
                    }
            DESCRIPTION
                 "tmnxBsxDnsIpCacheDomainRowStatus supports only 'active (1)',
                  'createAndGo (4)', and 'destroy (6)'."

        VARIATION   tmnxBsxDnsIpCacheRowStatus
            SYNTAX  RowStatus {
                       active               (1),
                    -- notInService         (2)
                    -- notReady             (3)
                       createAndGo          (4),
                    -- createAndWait        (5)
                       destroy              (6)
                    }
            DESCRIPTION
                 "tmnxBsxDnsIpCacheRowStatus supports only 'active (1)',
                  'createAndGo (4)', and 'destroy (6)'."

        VARIATION   tmnxBsxDnsIpCacheServerAddrType
            SYNTAX  InetAddressType {
                    -- unknown              (0)
                       ipv4                 (1),
                       ipv6                 (2)
                    -- ipv4z                (3)
                    -- ipv6z                (4)
                    -- dns                  (16)
                    }
            DESCRIPTION
                 "tmnxBsxDnsIpCacheServerAddrType supports only the
                  InetAddressType values 'ipv4 (1)', and 'ipv6 (2)'."

        VARIATION   tmnxBsxDnsIpCacheServerRowStatus
            SYNTAX  RowStatus {
                       active               (1),
                    -- notInService         (2)
                    -- notReady             (3)
                       createAndGo          (4),
                    -- createAndWait        (5)
                       destroy              (6)
                    }
            DESCRIPTION
                 "tmnxBsxDnsIpCacheServerRowStatus supports only 'active (1)',
                  'createAndGo (4)', and 'destroy (6)'."

        VARIATION   tmnxBsxEventLogRowStatus
            SYNTAX  RowStatus {
                       active               (1),
                    -- notInService         (2)
                    -- notReady             (3)
                       createAndGo          (4),
                    -- createAndWait        (5)
                       destroy              (6)
                    }
            DESCRIPTION
                 "tmnxBsxEventLogRowStatus supports only 'active (1)',
                  'createAndGo (4)', and 'destroy (6)'."

        VARIATION   tmnxBsxGtpFltrMsgRowStatus
            SYNTAX  RowStatus {
                       active               (1),
                    -- notInService         (2)
                    -- notReady             (3)
                       createAndGo          (4),
                    -- createAndWait        (5)
                       destroy              (6)
                    }
            DESCRIPTION
                 "tmnxBsxGtpFltrMsgRowStatus supports only 'active (1)',
                  'createAndGo (4)', and 'destroy (6)'."

        VARIATION   tmnxBsxGtpFltrRowStatus
            SYNTAX  RowStatus {
                       active               (1),
                    -- notInService         (2)
                    -- notReady             (3)
                       createAndGo          (4),
                    -- createAndWait        (5)
                       destroy              (6)
                    }
            DESCRIPTION
                 "tmnxBsxGtpFltrRowStatus supports only 'active (1)',
                  'createAndGo (4)', and 'destroy (6)'."

        VARIATION   tmnxBsxHttpEnrichFieldRowStatus
            SYNTAX  RowStatus {
                       active               (1),
                    -- notInService         (2)
                    -- notReady             (3)
                       createAndGo          (4),
                    -- createAndWait        (5)
                       destroy              (6)
                    }
            DESCRIPTION
                 "tmnxBsxHttpEnrichFieldRowStatus supports only 'active (1)',
                  'createAndGo (4)', and 'destroy (6)'."

        VARIATION   tmnxBsxHttpEnrichRowStatus
            SYNTAX  RowStatus {
                       active               (1),
                    -- notInService         (2)
                    -- notReady             (3)
                       createAndGo          (4),
                    -- createAndWait        (5)
                       destroy              (6)
                    }
            DESCRIPTION
                 "tmnxBsxHttpEnrichRowStatus supports only 'active (1)',
                  'createAndGo (4)', and 'destroy (6)'."

        VARIATION   tmnxBsxHttpNotifRowStatus
            SYNTAX  RowStatus {
                       active               (1),
                    -- notInService         (2)
                    -- notReady             (3)
                       createAndGo          (4),
                    -- createAndWait        (5)
                       destroy              (6)
                    }
            DESCRIPTION
                 "tmnxBsxHttpNotifRowStatus supports only 'active (1)',
                  'createAndGo (4)', and 'destroy (6)'."

        VARIATION   tmnxBsxHttpRedirErrCodeRowStatus
            SYNTAX  RowStatus {
                       active               (1),
                    -- notInService         (2)
                    -- notReady             (3)
                       createAndGo          (4),
                    -- createAndWait        (5)
                       destroy              (6)
                    }
            DESCRIPTION
                 "tmnxBsxHttpRedirErrCodeRowStatus supports only 'active (1)',
                  'createAndGo (4)', and 'destroy (6)'."

        VARIATION   tmnxBsxHttpRedirErrRowStatus
            SYNTAX  RowStatus {
                       active               (1),
                    -- notInService         (2)
                    -- notReady             (3)
                       createAndGo          (4),
                    -- createAndWait        (5)
                       destroy              (6)
                    }
            DESCRIPTION
                 "tmnxBsxHttpRedirErrRowStatus supports only 'active (1)',
                  'createAndGo (4)', and 'destroy (6)'."

        VARIATION   tmnxBsxHttpRedirRowStatus
            SYNTAX  RowStatus {
                       active               (1),
                    -- notInService         (2)
                    -- notReady             (3)
                       createAndGo          (4),
                    -- createAndWait        (5)
                       destroy              (6)
                    }
            DESCRIPTION
                 "tmnxBsxHttpRedirRowStatus supports only 'active (1)',
                  'createAndGo (4)', and 'destroy (6)'."

        VARIATION   tmnxBsxIcapServerAddrType
            SYNTAX  InetAddressType {
                       unknown              (0),
                       ipv4                 (1)
                    -- ipv6                 (2)
                    -- ipv4z                (3)
                    -- ipv6z                (4)
                    -- dns                  (16)
                    }
            DESCRIPTION
                 "tmnxBsxIcapServerAddrType supports only the InetAddressType
                  values 'unknown (0)' and 'ipv4 (1)'."

        VARIATION   tmnxBsxIcapServerRowStatus
            SYNTAX  RowStatus {
                       active               (1),
                    -- notInService         (2)
                    -- notReady             (3)
                       createAndGo          (4),
                    -- createAndWait        (5)
                       destroy              (6)
                    }
            DESCRIPTION
                 "tmnxBsxIcapServerRowStatus supports only 'active (1)',
                  'createAndGo (4)', and 'destroy (6)'."

        VARIATION   tmnxBsxIsaAaGrpTransPrefV4NmEntr
            SYNTAX  Unsigned32 (0..16383)
            DESCRIPTION
                 "tmnxBsxIsaAaGrpTransPrefV4NmEntr supports the range from 0 to
                  16383."

        VARIATION   tmnxBsxNotifyActionStatus
            SYNTAX  TmnxBsxActionStatus {
                    -- none                 (0)
                       start                (1),
                       stop                 (2)
                    }
            DESCRIPTION
                 "tmnxBsxNotifyActionStatus only supports TmnxBsxActionStatus
                  values of 'start (1)' and 'stop (2)."

        VARIATION   tmnxBsxPolicerOvrdRowStatus
            SYNTAX  RowStatus {
                       active               (1),
                    -- notInService         (2)
                    -- notReady             (3)
                       createAndGo          (4),
                    -- createAndWait        (5)
                       destroy              (6)
                    }
            DESCRIPTION
                 "tmnxBsxPolicerOvrdRowStatus supports only 'active (1)',
                  'createAndGo (4)', and 'destroy (6)'."

        VARIATION   tmnxBsxPolicerRowStatus
            SYNTAX  RowStatus {
                       active               (1),
                    -- notInService         (2)
                    -- notReady             (3)
                       createAndGo          (4),
                    -- createAndWait        (5)
                       destroy              (6)
                    }
            DESCRIPTION
                 "tmnxBsxPolicerRowStatus supports only 'active (1)',
                  'createAndGo (4)', and 'destroy (6)'."

        VARIATION   tmnxBsxPrefixListRowStatus
            SYNTAX  RowStatus {
                       active               (1),
                    -- notInService         (2)
                    -- notReady             (3)
                       createAndGo          (4),
                    -- createAndWait        (5)
                       destroy              (6)
                    }
            DESCRIPTION
                 "tmnxBsxPrefixListRowStatus supports only 'active (1)',
                  'createAndGo (4)', and 'destroy (6)'."

        VARIATION   tmnxBsxPrefixRowStatus
            SYNTAX  RowStatus {
                       active               (1),
                    -- notInService         (2)
                    -- notReady             (3)
                       createAndGo          (4),
                    -- createAndWait        (5)
                       destroy              (6)
                    }
            DESCRIPTION
                 "tmnxBsxPrefixRowStatus supports only 'active (1)',
                  'createAndGo (4)', and 'destroy (6)'."

        VARIATION   tmnxBsxRadApRowStatus
            SYNTAX  RowStatus {
                       active               (1),
                    -- notInService         (2)
                    -- notReady             (3)
                       createAndGo          (4),
                    -- createAndWait        (5)
                       destroy              (6)
                    }
            DESCRIPTION
                 "tmnxBsxRadApRowStatus supports only 'active (1)', 'createAndGo
                  (4)', and 'destroy (6)'."

        VARIATION   tmnxBsxRadApServAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServAddrType supports only the InetAddressType
                  values 'unknown (0)' and 'ipv4 (1)'."

        VARIATION   tmnxBsxRadApServRowStatus
            SYNTAX  RowStatus {
                       active               (1),
                    -- notInService         (2)
                    -- notReady             (3)
                       createAndGo          (4),
                    -- createAndWait        (5)
                       destroy              (6)
                    }
            DESCRIPTION
                 "tmnxBsxRadApServRowStatus supports only 'active (1)',
                  'createAndGo (4)', and 'destroy (6)'."

        VARIATION   tmnxBsxRadApServerAlgorithm
            SYNTAX  TmnxSubRadServAlgorithm {
                       direct               (1),
                       roundRobin           (2)
                    }
            DESCRIPTION
                 "tmnxBsxRadApServerAlgorithm supports only the values 'direct
                  (1)' and 'roundRobin (2)'."

        VARIATION   tmnxBsxRadApServerSrcAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServerSrcAddrType supports only the
                  InetAddressType values 'unknown (0)' and 'ipv4 (1)'."

        VARIATION   tmnxBsxSctpFltrPpidRowStatus
            SYNTAX  RowStatus {
                       active               (1),
                    -- notInService         (2)
                    -- notReady             (3)
                       createAndGo          (4),
                    -- createAndWait        (5)
                       destroy              (6)
                    }
            DESCRIPTION
                 "tmnxBsxSctpFltrPpidRowStatus supports only 'active (1)',
                  'createAndGo (4)', and 'destroy (6)'."

        VARIATION   tmnxBsxSctpFltrRowStatus
            SYNTAX  RowStatus {
                       active               (1),
                    -- notInService         (2)
                    -- notReady             (3)
                       createAndGo          (4),
                    -- createAndWait        (5)
                       destroy              (6)
                    }
            DESCRIPTION
                 "tmnxBsxSctpFltrRowStatus supports only 'active (1)',
                  'createAndGo (4)', and 'destroy (6)'."

        VARIATION   tmnxBsxSessFltrParamsDstAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsDstAddrType supports only the
                  InetAddressType values 'unknown (0)', 'ipv4 (1)', and 'ipv6
                  (2)'."

        VARIATION   tmnxBsxSessFltrParamsDstPortOp
            SYNTAX  TmnxBsxOperator {
                       none                 (0),
                       eq                   (1),
                    -- neq                  (2)
                       lt                   (3),
                       gt                   (4)
                    -- range                (5)
                    }
            DESCRIPTION
                 "tmnxBsxSessFltrParamsDstPortOp only supports the
                  TmnxBsxOperator values of 'none (0)', 'eq (1)', 'lt (3)' and
                  'gt (4)'."

        VARIATION   tmnxBsxSessFltrParamsRowStatus
            SYNTAX  RowStatus {
                       active               (1),
                    -- notInService         (2)
                    -- notReady             (3)
                       createAndGo          (4),
                    -- createAndWait        (5)
                       destroy              (6)
                    }
            DESCRIPTION
                 "tmnxBsxSessFltrParamsRowStatus supports only 'active (1)',
                  'createAndGo (4)', and 'destroy (6)'."

        VARIATION   tmnxBsxSessFltrParamsSrcAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsSrcAddrType supports only the
                  InetAddressType values 'unknown (0)', 'ipv4 (1)', and 'ipv6
                  (2)'."

        VARIATION   tmnxBsxSessFltrParamsSrcPortOp
            SYNTAX  TmnxBsxOperator {
                       none                 (0),
                       eq                   (1),
                    -- neq                  (2)
                       lt                   (3),
                       gt                   (4)
                    -- range                (5)
                    }
            DESCRIPTION
                 "tmnxBsxSessFltrParamsSrcPortOp only supports the
                  TmnxBsxOperator values of 'none (0)', 'eq (1)', 'lt (3)' and
                  'gt (4)'."

        VARIATION   tmnxBsxSessFltrRowStatus
            SYNTAX  RowStatus {
                       active               (1),
                    -- notInService         (2)
                    -- notReady             (3)
                       createAndGo          (4),
                    -- createAndWait        (5)
                       destroy              (6)
                    }
            DESCRIPTION
                 "tmnxBsxSessFltrRowStatus supports only 'active (1)',
                  'createAndGo (4)', and 'destroy (6)'."

        VARIATION   tmnxBsxStatAaSubCfgEntry
            CREATION-REQUIRES {
                       tmnxBsxStatAaSubCfgRowStatus,
                       tmnxBsxStatAaSubCfgExportMethod
                    }
            DESCRIPTION
                 "Both tmnxBsxStatAaSubCfgRowStatus and
                  tmnxBsxStatAaSubCfgExportMethod must be set for row creation
                  to succeed."

        VARIATION   tmnxBsxStatAaSubCfgRowStatus
            SYNTAX  RowStatus {
                       active               (1),
                    -- notInService         (2)
                    -- notReady             (3)
                       createAndGo          (4),
                    -- createAndWait        (5)
                       destroy              (6)
                    }
            DESCRIPTION
                 "tmnxBsxStatAaSubCfgRowStatus supports only 'active (1)',
                  'createAndGo (4)', and 'destroy (6)'."

        VARIATION   tmnxBsxStatAaSubSdyRowStatus
            SYNTAX  RowStatus {
                       active               (1),
                    -- notInService         (2)
                    -- notReady             (3)
                       createAndGo          (4),
                    -- createAndWait        (5)
                       destroy              (6)
                    }
            DESCRIPTION
                 "tmnxBsxStatAaSubSdyRowStatus supports only 'active (1)',
                  'createAndGo (4)', and 'destroy (6)'."

        VARIATION   tmnxBsxStatTcaCfgRowStatus
            SYNTAX  RowStatus {
                       active               (1),
                    -- notInService         (2)
                    -- notReady             (3)
                       createAndGo          (4),
                    -- createAndWait        (5)
                       destroy              (6)
                    }
            DESCRIPTION
                 "tmnxBsxStatTcaCfgRowStatus supports only 'active (1)',
                  'createAndGo (4)', and 'destroy (6)'."

        VARIATION   tmnxBsxStatTcaFtrCfgRowStatus
            SYNTAX  RowStatus {
                       active               (1),
                    -- notInService         (2)
                    -- notReady             (3)
                       createAndGo          (4),
                    -- createAndWait        (5)
                       destroy              (6)
                    }
            DESCRIPTION
                 "tmnxBsxStatTcaFtrCfgRowStatus supports only 'active (1)',
                  'createAndGo (4)', and 'destroy (6)'."

        VARIATION   tmnxBsxStatTcaFtrEnCfgRowStatus
            SYNTAX  RowStatus {
                       active               (1),
                    -- notInService         (2)
                    -- notReady             (3)
                       createAndGo          (4),
                    -- createAndWait        (5)
                       destroy              (6)
                    }
            DESCRIPTION
                 "tmnxBsxStatTcaFtrEnCfgRowStatus supports only 'active (1)',
                  'createAndGo (4)', and 'destroy (6)'."

        VARIATION   tmnxBsxStatTcaPolcrCfgRowStatus
            SYNTAX  RowStatus {
                       active               (1),
                    -- notInService         (2)
                    -- notReady             (3)
                       createAndGo          (4),
                    -- createAndWait        (5)
                       destroy              (6)
                    }
            DESCRIPTION
                 "tmnxBsxStatTcaPolcrCfgRowStatus supports only 'active (1)',
                  'createAndGo (4)', and 'destroy (6)'."

        VARIATION   tmnxBsxTcpValRowStatus
            SYNTAX  RowStatus {
                       active               (1),
                    -- notInService         (2)
                    -- notReady             (3)
                       createAndGo          (4),
                    -- createAndWait        (5)
                       destroy              (6)
                    }
            DESCRIPTION
                 "tmnxBsxTcpValRowStatus supports only 'active (1)',
                  'createAndGo (4)', and 'destroy (6)'."

        VARIATION   tmnxBsxTcpValTcaRowStatus
            SYNTAX  RowStatus {
                       active               (1),
                    -- notInService         (2)
                    -- notReady             (3)
                       createAndGo          (4),
                    -- createAndWait        (5)
                       destroy              (6)
                    }
            DESCRIPTION
                 "tmnxBsxTcpValTcaRowStatus supports only 'active (1)',
                  'createAndGo (4)', and 'destroy (6)'."

        VARIATION   tmnxBsxTransIpPlcyAddrRowStatus
            SYNTAX  RowStatus {
                       active               (1),
                    -- notInService         (2)
                    -- notReady             (3)
                       createAndGo          (4),
                    -- createAndWait        (5)
                       destroy              (6)
                    }
            DESCRIPTION
                 "tmnxBsxTransIpPlcyAddrRowStatus supports only 'active (1)',
                  'createAndGo (4)', and 'destroy (6)'."

        VARIATION   tmnxBsxTransIpPlcySubRowStatus
            SYNTAX  RowStatus {
                       active               (1),
                    -- notInService         (2)
                    -- notReady             (3)
                       createAndGo          (4),
                    -- createAndWait        (5)
                       destroy              (6)
                    }
            DESCRIPTION
                 "tmnxBsxTransIpPlcySubRowStatus supports only 'active (1)',
                  'createAndGo (4)', and 'destroy (6)'."

        VARIATION   tmnxBsxTransPrefEntryNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntryNetAddrType supports only the
                  InetAddressType values 'unknown (0)' and 'ipv4 (1)'."

        VARIATION   tmnxBsxTransPrefEntryRowStatus
            SYNTAX  RowStatus {
                       active               (1),
                    -- notInService         (2)
                    -- notReady             (3)
                       createAndGo          (4),
                    -- createAndWait        (5)
                       destroy              (6)
                    }
            DESCRIPTION
                 "tmnxBsxTransPrefEntryRowStatus supports only 'active (1)',
                  'createAndGo (4)', and 'destroy (6)'."

        VARIATION   tmnxBsxTransPrefEntrySubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntrySubAddrType supports only the
                  InetAddressType values 'unknown (0)' and 'ipv4 (1)'."

        VARIATION   tmnxBsxTransPrefPolicyRowStatus
            SYNTAX  RowStatus {
                       active               (1),
                    -- notInService         (2)
                    -- notReady             (3)
                       createAndGo          (4),
                    -- createAndWait        (5)
                       destroy              (6)
                    }
            DESCRIPTION
                 "tmnxBsxTransPrefPolicyRowStatus supports only 'active (1)',
                  'createAndGo (4)', and 'destroy (6)'."

        VARIATION   tmnxBsxTransPrefSubRowStatus
            SYNTAX  RowStatus {
                       active               (1),
                    -- notInService         (2)
                    -- notReady             (3)
                       createAndGo          (4),
                    -- createAndWait        (5)
                       destroy              (6)
                    }
            DESCRIPTION
                 "tmnxBsxTransPrefSubRowStatus supports only 'active (1)',
                  'createAndGo (4)', and 'destroy (6)'."

        VARIATION   tmnxBsxTransPrefSumNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumNetAddrType supports only the
                  InetAddressType values 'unknown (0)' and 'ipv4 (1)'."

        VARIATION   tmnxBsxTransPrefSumSubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumSubAddrType supports only the
                  InetAddressType values 'unknown (0)' and 'ipv4 (1)'."

        VARIATION   tmnxBsxTransitIpPolicyAddrType
            SYNTAX  InetAddressType {
                    -- unknown              (0)
                       ipv4                 (1),
                       ipv6                 (2)
                    -- ipv4z                (3)
                    -- ipv6z                (4)
                    -- dns                  (16)
                    }
            DESCRIPTION
                 "tmnxBsxTransitIpPolicyAddrType supports only the
                  InetAddressType values 'ipv4 (1)', and 'ipv6 (2)'."

        VARIATION   tmnxBsxTransitIpPolicyIPv6PfxLen
            SYNTAX  InetAddressPrefixLength (32..64)
            DESCRIPTION
                 "tmnxBsxTransitIpPolicyIPv6PfxLen supports only the range from
                  32 to 64."

        VARIATION   tmnxBsxTransitIpPolicyRowStatus
            SYNTAX  RowStatus {
                       active               (1),
                    -- notInService         (2)
                    -- notReady             (3)
                       createAndGo          (4),
                    -- createAndWait        (5)
                       destroy              (6)
                    }
            DESCRIPTION
                 "tmnxBsxTransitIpPolicyRowStatus supports only 'active (1)',
                  'createAndGo (4)', and 'destroy (6)'."

        VARIATION   tmnxBsxTransitIpSumParentSubType
            SYNTAX  TmnxBsxAaSubscriberType {
                       unknown              (0),
                    -- esm                  (1)
                       sap                  (2),
                       spokeSdp             (3)
                    -- transit              (4)
                    }
            DESCRIPTION
                 "tmnxBsxTransitIpSumParentSubType supports only the values
                  'unknown(0)', 'sap(2)', and 'spokeSdp(3)'."

        VARIATION   tmnxBsxUrlFilterRowStatus
            SYNTAX  RowStatus {
                       active               (1),
                    -- notInService         (2)
                    -- notReady             (3)
                       createAndGo          (4),
                    -- createAndWait        (5)
                       destroy              (6)
                    }
            DESCRIPTION
                 "tmnxBsxUrlFilterRowStatus supports only 'active (1)',
                  'createAndGo (4)', and 'destroy (6)'."

        VARIATION   tmnxBsxUrlFltrUrlListRowStatus
            SYNTAX  RowStatus {
                       active               (1),
                    -- notInService         (2)
                    -- notReady             (3)
                       createAndGo          (4),
                    -- createAndWait        (5)
                       destroy              (6)
                    }
            DESCRIPTION
                 "tmnxBsxUrlFltrUrlListRowStatus supports only 'active (1)',
                  'createAndGo (4)', and 'destroy (6)'."

        VARIATION   tmnxBsxUrlListRowStatus
            SYNTAX  RowStatus {
                       active               (1),
                    -- notInService         (2)
                    -- notReady             (3)
                       createAndGo          (4),
                    -- createAndWait        (5)
                       destroy              (6)
                    }
            DESCRIPTION
                 "tmnxBsxUrlListRowStatus supports only 'active (1)',
                  'createAndGo (4)', and 'destroy (6)'."

    ::= { tmnx7750AgentV14v0  66 }

--
-- 7750c12 BSX CAPABILITIES
--
tmnx7750c12BsxV14v0               AGENT-CAPABILITIES
    PRODUCT-RELEASE "Nokia SROS"
    STATUS          current
    DESCRIPTION
         "Implementation of BSX capabilities for Nokia 7750 c12 systems release
          14.0."

    SUPPORTS        TIMETRA-BSX-NG-MIB
        INCLUDES {
           tmnxBsxCflowdDirectExportGroup,
           tmnxBsxCflowdGroup,
           tmnxBsxCflowdGroupV10v0,
           tmnxBsxCflowdGroupV9v0,
           tmnxBsxDnsIpCacheGroupV13v0,
           tmnxBsxEventLogSyslogObjGrp,
           tmnxBsxGtpGroupV13v0,
           tmnxBsxGtpUntunnelingObjGrp,
           tmnxBsxHttpEnAntiSpfStObGrpV11v0,
           tmnxBsxHttpEnrAntiSpfObjGrpV11v0,
           tmnxBsxHttpEnrEncObjGrpV11v0,
           tmnxBsxHttpEnrStStrObjGrpV12v0,
           tmnxBsxHttpEnrichObjGroup,
           tmnxBsxHttpEnrichStatObjGroup,
           tmnxBsxHttpNotifObjGrp,
           tmnxBsxHttpNotifObjGrpV13v0,
           tmnxBsxHttpRedirErrGroup,
           tmnxBsxHttpRedirGroup,
           tmnxBsxHttpRedirObjGrpV12v0,
           tmnxBsxHttpRedirObjGrpV13v0,
           tmnxBsxHttpsCaptiveRedirObjGrp,
           tmnxBsxIpPrefixListObjGrpV12v0,
           tmnxBsxIsa2ObjGroup,
           tmnxBsxLwObjGrpV12v0,
           tmnxBsxMdaGroupV10v0,
           tmnxBsxMdaGroupV11v0,
           tmnxBsxMdaGroupV12v0,
           tmnxBsxMdaGroupV7v0,
           tmnxBsxMdaGroupV8v0,
           tmnxBsxMgBillingExclusionsGroup,
           tmnxBsxMgTetherDetectGroup,
           tmnxBsxMobileGatewayGroup,
           tmnxBsxNotificationGroup,
           tmnxBsxNotificationGroupV10v0,
           tmnxBsxNotificationGroupV11v0,
           tmnxBsxNotificationGroupV12v0,
           tmnxBsxNotificationGroupV13v0,
           tmnxBsxNotificationGroupV14v0,
           tmnxBsxNotificationGroupV7v0,
           tmnxBsxNotificationGroupV8v0,
           tmnxBsxNotificationGroupV9v0,
           tmnxBsxNotifyObjsGroup,
           tmnxBsxNotifyObjsGroupV13v0,
           tmnxBsxNotifyObjsGroupV14v0,
           tmnxBsxNotifyObjsGroupV7v0,
           tmnxBsxNotifyObjsGroupV8v0,
           tmnxBsxOvrdGroup,
           tmnxBsxPolicyObjGrp12v0,
           tmnxBsxPolicyObjGrp13v0,
           tmnxBsxPolicyTimeStampExtObjGrp,
           tmnxBsxPolicyTodObjGrp,
           tmnxBsxRadApNotificationGroup,
           tmnxBsxRadApObjGroup,
           tmnxBsxRadApStatObjGroup,
           tmnxBsxRadiusAccountingObjGroup,
           tmnxBsxRadiusAcctObjGroupV11v0,
           tmnxBsxRedundancyEnhObjGroup,
           tmnxBsxRedundancyObjGroup,
           tmnxBsxSessionFilterObjGrp,
           tmnxBsxStaticObjGroup,
           tmnxBsxStatsGroup,
           tmnxBsxStatsGroupV9v0,
           tmnxBsxStflFwEnhacementsObjGrp,
           tmnxBsxTcpMssObjGrp,
           tmnxBsxTcpValObjGrp,
           tmnxBsxTrafficStatsObjGrpV12v0,
           tmnxBsxTrafficStatsObjGrpV13v0,
           tmnxBsxTransitGroup,
           tmnxBsxTransitGroupV10v0,
           tmnxBsxTransitIpPolicyDiamObjGrp,
           tmnxBsxTransitSeenIpGroup,
           tmnxBsxTrapPerfObjGrp,
           tmnxBsxUrlFilterObjGrp,
           tmnxBsxUrlFilterObjGrpV12v0,
           tmnxBsxUrlFilterStatsObjGrp,
           tmnxBsxUrlListExtendedGroup,
           tmnxBsxUrlListGroupV13v0,
           tmnxBsxUsageMonObjGrpV12v0,
           tmnxBsxXHeaderObjGroup
        }

        VARIATION   tmnxBsxAaGrpPartRowStatus
            SYNTAX  RowStatus {
                       active               (1),
                    -- notInService         (2)
                    -- notReady             (3)
                       createAndGo          (4),
                    -- createAndWait        (5)
                       destroy              (6)
                    }
            DESCRIPTION
                 "tmnxBsxAaGrpPartRowStatus supports only 'active (1)',
                  'createAndGo (4)', and 'destroy (6)'."

        VARIATION   tmnxBsxAaIfAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfAddrType supports only the InetAddressType values
                  'unknown (0)' and 'ipv4 (1)'."

        VARIATION   tmnxBsxAaIfIsaAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfIsaAddrType supports only the InetAddressType
                  values 'unknown (0)' and 'ipv4 (1)'."

        VARIATION   tmnxBsxAarpInstPeerEPSapEncType
            SYNTAX  INTEGER {
                       unknown              (0),
                       nullEncap            (1),
                    -- qEncap               (2)
                    -- mplsEncap            (3)
                    -- bcpNullEncap         (4)
                       bcpDot1qEncap        (5),
                    -- ipcpEncap            (6)
                    -- frEncap              (7)
                    -- pppAutoEncap         (8)
                    -- atmEncap             (9)
                       qinqEncap            (10)
                    -- wanMirrorEncap       (11)
                    -- ciscoHDLCEncap       (12)
                    -- cemEncap             (13)
                    }
            DESCRIPTION
                 "tmnxBsxAarpInstPeerEPSapEncType supports only
                  TmnxPortEncapType 'unknown(0)', 'nullEncap(1)',
                  'bcpDot1qEncap(5)', and 'qinqEncap(10)'."

        VARIATION   tmnxBsxAarpInstPeerIpType
            SYNTAX  InetAddressType {
                       unknown              (0),
                       ipv4                 (1)
                    -- ipv6                 (2)
                    -- ipv4z                (3)
                    -- ipv6z                (4)
                    -- dns                  (16)
                    }
            DESCRIPTION
                 "tmnxBsxAarpInstPeerIpType supports only the InetAddressType
                  values 'unknown (0)' and 'ipv4 (1)'."

        VARIATION   tmnxBsxAarpInstRowStatus
            SYNTAX  RowStatus {
                       active               (1),
                    -- notInService         (2)
                    -- notReady             (3)
                       createAndGo          (4),
                    -- createAndWait        (5)
                       destroy              (6)
                    }
            DESCRIPTION
                 "tmnxBsxAarpInstRowStatus supports only 'active (1)',
                  'createAndGo (4)', and 'destroy (6)'."

        VARIATION   tmnxBsxAppFilterExprIndex
            SYNTAX  Integer32 (1..4)
            DESCRIPTION
                 "tmnxBsxAppFilterExprIndex supports a range from 1 to 4
                  expressions."

        VARIATION   tmnxBsxAppFilterExprOperator
            SYNTAX  TmnxBsxOperator {
                       none                 (0),
                       eq                   (1),
                       neq                  (2)
                    -- lt                   (3)
                    -- gt                   (4)
                    -- range                (5)
                    }
            DESCRIPTION
                 "tmnxBsxAppFilterExprOperator only supports TmnxBsxOperator
                  values of 'none (0)', 'eq (1)' and 'neq (2)."

        VARIATION   tmnxBsxAppFilterNetworkAddrOp
            SYNTAX  TmnxBsxOperator {
                       none                 (0),
                       eq                   (1),
                       neq                  (2)
                    -- lt                   (3)
                    -- gt                   (4)
                    -- range                (5)
                    }
            DESCRIPTION
                 "tmnxBsxAppFilterNetworkAddrOp only supports TmnxBsxOperator
                  values of 'none (0)', 'eq (1)' and 'neq (2)."

        VARIATION   tmnxBsxAppFilterNetworkAddrType
            SYNTAX  InetAddressType {
                       unknown              (0),
                       ipv4                 (1),
                       ipv6                 (2)
                    -- ipv4z                (3)
                    -- ipv6z                (4)
                    -- dns                  (16)
                    }
            DESCRIPTION
                 "tmnxBsxAppFilterNetworkAddrType supports only the
                  InetAddressType values 'unknown (0)', 'ipv4 (1)', and 'ipv6
                  (2)'."

        VARIATION   tmnxBsxAppFilterServerAddrOp
            SYNTAX  TmnxBsxOperator {
                       none                 (0),
                       eq                   (1),
                       neq                  (2)
                    -- lt                   (3)
                    -- gt                   (4)
                    -- range                (5)
                    }
            DESCRIPTION
                 "tmnxBsxAppFilterServerAddrOp only supports TmnxBsxOperator
                  values of 'none (0)', 'eq (1)' and 'neq (2)."

        VARIATION   tmnxBsxAppFilterServerAddrType
            SYNTAX  InetAddressType {
                       unknown              (0),
                       ipv4                 (1),
                       ipv6                 (2)
                    -- ipv4z                (3)
                    -- ipv6z                (4)
                    -- dns                  (16)
                    }
            DESCRIPTION
                 "tmnxBsxAppFilterServerAddrType supports only the
                  InetAddressType values 'unknown (0)', 'ipv4 (1)', and 'ipv6
                  (2)'."

        VARIATION   tmnxBsxAppFilterServerPortOp
            SYNTAX  TmnxBsxOperator {
                       none                 (0),
                       eq                   (1),
                       neq                  (2),
                       lt                   (3),
                       gt                   (4)
                    -- range                (5)
                    }
            DESCRIPTION
                 "tmnxBsxAppFilterServerPortOp only supports TmnxBsxOperator
                  values of 'none (0)', 'eq (1)', 'neq (2)', 'lt (3)' and 'gt
                  (4)."

        VARIATION   tmnxBsxAppGrpRowStatus
            SYNTAX  RowStatus {
                       active               (1),
                    -- notInService         (2)
                    -- notReady             (3)
                       createAndGo          (4),
                    -- createAndWait        (5)
                       destroy              (6)
                    }
            DESCRIPTION
                 "tmnxBsxAppGrpRowStatus supports only 'active (1)',
                  'createAndGo (4)', and 'destroy (6)'."

        VARIATION   tmnxBsxAppGrpStorageType
            SYNTAX  StorageType {
                    -- other(1)
                    -- volatile(2)
                       nonVolatile(3),
                       permanent(4)
                    -- readOnly(5)
                    }
            DESCRIPTION
                 "tmnxBsxAppGrpStorageType supports only the values 'nonVolatile
                  (3)' and 'permanent (4)'."

        VARIATION   tmnxBsxAppProfRowStatus
            SYNTAX  RowStatus {
                       active               (1),
                    -- notInService         (2)
                    -- notReady             (3)
                       createAndGo          (4),
                    -- createAndWait        (5)
                       destroy              (6)
                    }
            DESCRIPTION
                 "tmnxBsxAppProfRowStatus supports only 'active (1)',
                  'createAndGo (4)', and 'destroy (6)'."

        VARIATION   tmnxBsxAppRowStatus
            SYNTAX  RowStatus {
                       active               (1),
                    -- notInService         (2)
                    -- notReady             (3)
                       createAndGo          (4),
                    -- createAndWait        (5)
                       destroy              (6)
                    }
            DESCRIPTION
                 "tmnxBsxAppRowStatus supports only 'active (1)', 'createAndGo
                  (4)', and 'destroy (6)'."

        VARIATION   tmnxBsxAppStorageType
            SYNTAX  StorageType {
                    -- other(1)
                    -- volatile(2)
                       nonVolatile(3),
                       permanent(4)
                    -- readOnly(5)
                    }
            DESCRIPTION
                 "tmnxBsxAppStorageType supports only the values 'nonVolatile
                  (3)' and 'permanent (4)'."

        VARIATION   tmnxBsxAqpBaseRowStatus
            SYNTAX  RowStatus {
                       active               (1),
                    -- notInService         (2)
                    -- notReady             (3)
                       createAndGo          (4),
                    -- createAndWait        (5)
                       destroy              (6)
                    }
            DESCRIPTION
                 "tmnxBsxAqpBaseRowStatus supports only 'active (1)',
                  'createAndGo (4)', and 'destroy (6)'."

        VARIATION   tmnxBsxAqpCharOperator
            SYNTAX  TmnxBsxOperator {
                    -- none                 (0)
                       eq                   (1)
                    -- neq                  (2)
                    -- lt                   (3)
                    -- gt                   (4)
                    -- range                (5)
                    }
            DESCRIPTION
                 "tmnxBsxAqpCharOperator only supports the TmnxBsxOperator value
                  of 'eq (1)'."

        VARIATION   tmnxBsxAqpCharRowStatus
            SYNTAX  RowStatus {
                       active               (1),
                    -- notInService         (2)
                    -- notReady             (3)
                       createAndGo          (4),
                    -- createAndWait        (5)
                       destroy              (6)
                    }
            DESCRIPTION
                 "tmnxBsxAqpCharRowStatus supports only 'active (1)',
                  'createAndGo (4)', and 'destroy (6)'."

        VARIATION   tmnxBsxAqpChargeGrpOp
            SYNTAX  TmnxBsxOperator {
                       none                 (0),
                       eq                   (1),
                       neq                  (2)
                    -- lt                   (3)
                    -- gt                   (4)
                    -- range                (5)
                    }
            DESCRIPTION
                 "tmnxBsxAqpChargeGrpOp only supports TmnxBsxOperator values of
                  'none (0)', 'eq (1)' and 'neq (2)."

        VARIATION   tmnxBsxAqpDstAddress
            SYNTAX  InetAddress (SIZE (0|4))
            DESCRIPTION
                 "tmnxBsxAqpDstAddress only supports InetAddressType 'unknown
                  (0)' and 'ipv4 (1)'."

        VARIATION   tmnxBsxAqpDstAddressOp
            SYNTAX  TmnxBsxOperator {
                       none                 (0),
                       eq                   (1),
                       neq                  (2)
                    -- lt                   (3)
                    -- gt                   (4)
                    -- range                (5)
                    }
            DESCRIPTION
                 "tmnxBsxAqpDstAddressOp only supports TmnxBsxOperator values of
                  'none (0)', 'eq (1)' and 'neq (2)."

        VARIATION   tmnxBsxAqpDstAddressType
            SYNTAX  InetAddressType {
                       unknown              (0),
                       ipv4                 (1)
                    -- ipv6                 (2)
                    -- ipv4z                (3)
                    -- ipv6z                (4)
                    -- dns                  (16)
                    }
            DESCRIPTION
                 "tmnxBsxAqpDstAddressType supports only the InetAddressType
                  values 'unknown (0)' and 'ipv4 (1)'."

        VARIATION   tmnxBsxAqpDstPortOp
            SYNTAX  TmnxBsxOperator {
                       none                 (0),
                       eq                   (1),
                       neq                  (2)
                    -- lt                   (3)
                    -- gt                   (4)
                    -- range                (5)
                    }
            DESCRIPTION
                 "tmnxBsxAqpDstPortOp only supports TmnxBsxOperator values of
                  'none (0)', 'eq (1)' and 'neq (2)."

        VARIATION   tmnxBsxAqpIpProtocolNumOp
            SYNTAX  TmnxBsxOperator {
                       none                 (0),
                       eq                   (1),
                       neq                  (2)
                    -- lt                   (3)
                    -- gt                   (4)
                    -- range                (5)
                    }
            DESCRIPTION
                 "tmnxBsxAqpIpProtocolNumOp only supports TmnxBsxOperator values
                  of 'none (0)', 'eq (1)' and 'neq (2)."

        VARIATION   tmnxBsxAqpOutOfOrderFrags
            ACCESS  not-implemented
            DESCRIPTION
                 "tmnxBsxAqpOutOfOrderFrags is not implemented on Nokia 7750 c12
                  in release 14.0."

        VARIATION   tmnxBsxAqpSapSubscrOp
            SYNTAX  TmnxBsxOperator {
                       none                 (0),
                       eq                   (1),
                       neq                  (2)
                    -- lt                   (3)
                    -- gt                   (4)
                    -- range                (5)
                    }
            DESCRIPTION
                 "tmnxBsxAqpSapSubscrOp only supports TmnxBsxOperator values of
                  'none (0)', 'eq (1)' and 'neq (2)."

        VARIATION   tmnxBsxAqpSrcAddress
            SYNTAX  InetAddress (SIZE (0|4))
            DESCRIPTION
                 "tmnxBsxAqpSrcAddress only supports InetAddressType 'unknown
                  (0)' and 'ipv4 (1)'."

        VARIATION   tmnxBsxAqpSrcAddressOp
            SYNTAX  TmnxBsxOperator {
                       none                 (0),
                       eq                   (1),
                       neq                  (2)
                    -- lt                   (3)
                    -- gt                   (4)
                    -- range                (5)
                    }
            DESCRIPTION
                 "tmnxBsxAqpSrcAddressOp only supports TmnxBsxOperator values of
                  'none (0)', 'eq (1)' and 'neq (2)."

        VARIATION   tmnxBsxAqpSrcAddressType
            SYNTAX  InetAddressType {
                       unknown              (0),
                       ipv4                 (1)
                    -- ipv6                 (2)
                    -- ipv4z                (3)
                    -- ipv6z                (4)
                    -- dns                  (16)
                    }
            DESCRIPTION
                 "tmnxBsxAqpSrcAddressType supports only the InetAddressType
                  values 'unknown (0)' and 'ipv4 (1)'."

        VARIATION   tmnxBsxAqpSrcPortOp
            SYNTAX  TmnxBsxOperator {
                       none                 (0),
                       eq                   (1),
                       neq                  (2)
                    -- lt                   (3)
                    -- gt                   (4)
                    -- range                (5)
                    }
            DESCRIPTION
                 "tmnxBsxAqpSrcPortOp only supports TmnxBsxOperator values of
                  'none (0)', 'eq (1)' and 'neq (2)."

        VARIATION   tmnxBsxAsoPersistId
            ACCESS  not-implemented
            DESCRIPTION
                 "tmnxBsxAsoPersistId is not implemented on Nokia 7750 c12 in
                  release 14.0."

        VARIATION   tmnxBsxAsoRowStatus
            SYNTAX  RowStatus {
                       active               (1),
                    -- notInService         (2)
                    -- notReady             (3)
                       createAndGo          (4),
                    -- createAndWait        (5)
                       destroy              (6)
                    }
            DESCRIPTION
                 "tmnxBsxAsoRowStatus supports only 'active (1)', 'createAndGo
                  (4)', and 'destroy (6)'."

        VARIATION   tmnxBsxAsoValPersistId
            ACCESS  not-implemented
            DESCRIPTION
                 "tmnxBsxAsoValPersistId is not implemented on Nokia 7750 c12 in
                  release 14.0."

        VARIATION   tmnxBsxAsoValRowStatus
            SYNTAX  RowStatus {
                       active               (1),
                    -- notInService         (2)
                    -- notReady             (3)
                       createAndGo          (4),
                    -- createAndWait        (5)
                       destroy              (6)
                    }
            DESCRIPTION
                 "tmnxBsxAsoValRowStatus supports only 'active (1)',
                  'createAndGo (4)', and 'destroy (6)'."

        VARIATION   tmnxBsxCflowdCollAddress
            SYNTAX  InetAddress (SIZE (0|4))
            DESCRIPTION
                 "tmnxBsxCflowdCollAddress only supports InetAddressType
                  'unknown (0)' and 'ipv4 (1)'."

        VARIATION   tmnxBsxCflowdCollAddressType
            SYNTAX  InetAddressType {
                       unknown              (0),
                       ipv4                 (1)
                    -- ipv6                 (2)
                    -- ipv4z                (3)
                    -- ipv6z                (4)
                    -- dns                  (16)
                    }
            DESCRIPTION
                 "tmnxBsxCflowdCollAddressType supports only the InetAddressType
                  values 'unknown (0)' and 'ipv4 (1)'."

        VARIATION   tmnxBsxCflowdCollRowStatus
            SYNTAX  RowStatus {
                       active               (1),
                    -- notInService         (2)
                    -- notReady             (3)
                       createAndGo          (4),
                    -- createAndWait        (5)
                       destroy              (6)
                    }
            DESCRIPTION
                 "tmnxBsxCflowdCollRowStatus supports only 'active (1)',
                  'createAndGo (4)', and 'destroy (6)'."

        VARIATION   tmnxBsxCflowdDirExpAddrRowStatus
            SYNTAX  RowStatus {
                       active               (1),
                    -- notInService         (2)
                    -- notReady             (3)
                       createAndGo          (4),
                    -- createAndWait        (5)
                       destroy              (6)
                    }
            DESCRIPTION
                 "tmnxBsxCflowdDirExpAddrRowStatus supports only 'active (1)',
                  'createAndGo (4)', and 'destroy (6)'."

        VARIATION   tmnxBsxCflowdDirectExpRowStatus
            SYNTAX  RowStatus {
                       active               (1),
                    -- notInService         (2)
                    -- notReady             (3)
                       createAndGo          (4),
                    -- createAndWait        (5)
                       destroy              (6)
                    }
            DESCRIPTION
                 "tmnxBsxCflowdDirectExpRowStatus supports only 'active (1)',
                  'createAndGo (4)', and 'destroy (6)'."

        VARIATION   tmnxBsxCflowdPerfExpRowStatus
            SYNTAX  RowStatus {
                       active               (1),
                    -- notInService         (2)
                    -- notReady             (3)
                       createAndGo          (4),
                    -- createAndWait        (5)
                       destroy              (6)
                    }
            DESCRIPTION
                 "tmnxBsxCflowdPerfExpRowStatus supports only 'active (1)',
                  'createAndGo (4)', and 'destroy (6)'."

        VARIATION   tmnxBsxChargeGrpRowStatus
            SYNTAX  RowStatus {
                       active               (1),
                    -- notInService         (2)
                    -- notReady             (3)
                       createAndGo          (4),
                    -- createAndWait        (5)
                       destroy              (6)
                    }
            DESCRIPTION
                 "tmnxBsxChargeGrpRowStatus supports only 'active (1)',
                  'createAndGo (4)', and 'destroy (6)'."

        VARIATION   tmnxBsxCustProtEntryId
            SYNTAX  TEntryId (1..10)
            DESCRIPTION
                 "tmnxBsxCustProtEntryId supports a range from 1 to 10 custom
                  protocol entries."

        VARIATION   tmnxBsxCustProtExprIndex
            SYNTAX  Integer32 (1)
            DESCRIPTION
                 "tmnxBsxCustProtExprIndex only supports 1 custom protocol
                  expression."

        VARIATION   tmnxBsxCustProtExprOperator
            SYNTAX  TmnxBsxOperator {
                    -- none                 (0)
                       eq                   (1)
                    -- neq                  (2)
                    -- lt                   (3)
                    -- gt                   (4)
                    -- range                (5)
                    }
            DESCRIPTION
                 "tmnxBsxCustProtExprOperator only supports the TmnxBsxOperator
                  value of 'eq (1)'."

        VARIATION   tmnxBsxCustProtExprRowStatus
            SYNTAX  RowStatus {
                       active               (1),
                    -- notInService         (2)
                    -- notReady             (3)
                       createAndGo          (4),
                    -- createAndWait        (5)
                       destroy              (6)
                    }
            DESCRIPTION
                 "tmnxBsxCustProtExprRowStatus supports only 'active (1)',
                  'createAndGo (4)', and 'destroy (6)'."

        VARIATION   tmnxBsxCustProtIpProtocolNum
            DESCRIPTION
                 "tmnxBsxCustProtIpProtocolNum supports only the values not set
                  (-1), tcp (6) and udp (17)."

        VARIATION   tmnxBsxCustProtRowStatus
            SYNTAX  RowStatus {
                       active               (1),
                    -- notInService         (2)
                    -- notReady             (3)
                       createAndGo          (4),
                    -- createAndWait        (5)
                       destroy              (6)
                    }
            DESCRIPTION
                 "tmnxBsxCustProtRowStatus supports only 'active (1)',
                  'createAndGo (4)', and 'destroy (6)'."

        VARIATION   tmnxBsxDnsIpCacheDomainRowStatus
            SYNTAX  RowStatus {
                       active               (1),
                    -- notInService         (2)
                    -- notReady             (3)
                       createAndGo          (4),
                    -- createAndWait        (5)
                       destroy              (6)
                    }
            DESCRIPTION
                 "tmnxBsxDnsIpCacheDomainRowStatus supports only 'active (1)',
                  'createAndGo (4)', and 'destroy (6)'."

        VARIATION   tmnxBsxDnsIpCacheRowStatus
            SYNTAX  RowStatus {
                       active               (1),
                    -- notInService         (2)
                    -- notReady             (3)
                       createAndGo          (4),
                    -- createAndWait        (5)
                       destroy              (6)
                    }
            DESCRIPTION
                 "tmnxBsxDnsIpCacheRowStatus supports only 'active (1)',
                  'createAndGo (4)', and 'destroy (6)'."

        VARIATION   tmnxBsxDnsIpCacheServerAddrType
            SYNTAX  InetAddressType {
                    -- unknown              (0)
                       ipv4                 (1),
                       ipv6                 (2)
                    -- ipv4z                (3)
                    -- ipv6z                (4)
                    -- dns                  (16)
                    }
            DESCRIPTION
                 "tmnxBsxDnsIpCacheServerAddrType supports only the
                  InetAddressType values 'ipv4 (1)', and 'ipv6 (2)'."

        VARIATION   tmnxBsxDnsIpCacheServerRowStatus
            SYNTAX  RowStatus {
                       active               (1),
                    -- notInService         (2)
                    -- notReady             (3)
                       createAndGo          (4),
                    -- createAndWait        (5)
                       destroy              (6)
                    }
            DESCRIPTION
                 "tmnxBsxDnsIpCacheServerRowStatus supports only 'active (1)',
                  'createAndGo (4)', and 'destroy (6)'."

        VARIATION   tmnxBsxEventLogRowStatus
            SYNTAX  RowStatus {
                       active               (1),
                    -- notInService         (2)
                    -- notReady             (3)
                       createAndGo          (4),
                    -- createAndWait        (5)
                       destroy              (6)
                    }
            DESCRIPTION
                 "tmnxBsxEventLogRowStatus supports only 'active (1)',
                  'createAndGo (4)', and 'destroy (6)'."

        VARIATION   tmnxBsxGtpFltrMsgRowStatus
            SYNTAX  RowStatus {
                       active               (1),
                    -- notInService         (2)
                    -- notReady             (3)
                       createAndGo          (4),
                    -- createAndWait        (5)
                       destroy              (6)
                    }
            DESCRIPTION
                 "tmnxBsxGtpFltrMsgRowStatus supports only 'active (1)',
                  'createAndGo (4)', and 'destroy (6)'."

        VARIATION   tmnxBsxGtpFltrRowStatus
            SYNTAX  RowStatus {
                       active               (1),
                    -- notInService         (2)
                    -- notReady             (3)
                       createAndGo          (4),
                    -- createAndWait        (5)
                       destroy              (6)
                    }
            DESCRIPTION
                 "tmnxBsxGtpFltrRowStatus supports only 'active (1)',
                  'createAndGo (4)', and 'destroy (6)'."

        VARIATION   tmnxBsxHttpEnrichFieldRowStatus
            SYNTAX  RowStatus {
                       active               (1),
                    -- notInService         (2)
                    -- notReady             (3)
                       createAndGo          (4),
                    -- createAndWait        (5)
                       destroy              (6)
                    }
            DESCRIPTION
                 "tmnxBsxHttpEnrichFieldRowStatus supports only 'active (1)',
                  'createAndGo (4)', and 'destroy (6)'."

        VARIATION   tmnxBsxHttpEnrichRowStatus
            SYNTAX  RowStatus {
                       active               (1),
                    -- notInService         (2)
                    -- notReady             (3)
                       createAndGo          (4),
                    -- createAndWait        (5)
                       destroy              (6)
                    }
            DESCRIPTION
                 "tmnxBsxHttpEnrichRowStatus supports only 'active (1)',
                  'createAndGo (4)', and 'destroy (6)'."

        VARIATION   tmnxBsxHttpNotifRowStatus
            SYNTAX  RowStatus {
                       active               (1),
                    -- notInService         (2)
                    -- notReady             (3)
                       createAndGo          (4),
                    -- createAndWait        (5)
                       destroy              (6)
                    }
            DESCRIPTION
                 "tmnxBsxHttpNotifRowStatus supports only 'active (1)',
                  'createAndGo (4)', and 'destroy (6)'."

        VARIATION   tmnxBsxHttpRedirErrCodeRowStatus
            SYNTAX  RowStatus {
                       active               (1),
                    -- notInService         (2)
                    -- notReady             (3)
                       createAndGo          (4),
                    -- createAndWait        (5)
                       destroy              (6)
                    }
            DESCRIPTION
                 "tmnxBsxHttpRedirErrCodeRowStatus supports only 'active (1)',
                  'createAndGo (4)', and 'destroy (6)'."

        VARIATION   tmnxBsxHttpRedirErrRowStatus
            SYNTAX  RowStatus {
                       active               (1),
                    -- notInService         (2)
                    -- notReady             (3)
                       createAndGo          (4),
                    -- createAndWait        (5)
                       destroy              (6)
                    }
            DESCRIPTION
                 "tmnxBsxHttpRedirErrRowStatus supports only 'active (1)',
                  'createAndGo (4)', and 'destroy (6)'."

        VARIATION   tmnxBsxHttpRedirRowStatus
            SYNTAX  RowStatus {
                       active               (1),
                    -- notInService         (2)
                    -- notReady             (3)
                       createAndGo          (4),
                    -- createAndWait        (5)
                       destroy              (6)
                    }
            DESCRIPTION
                 "tmnxBsxHttpRedirRowStatus supports only 'active (1)',
                  'createAndGo (4)', and 'destroy (6)'."

        VARIATION   tmnxBsxIcapServerAddrType
            SYNTAX  InetAddressType {
                       unknown              (0),
                       ipv4                 (1)
                    -- ipv6                 (2)
                    -- ipv4z                (3)
                    -- ipv6z                (4)
                    -- dns                  (16)
                    }
            DESCRIPTION
                 "tmnxBsxIcapServerAddrType supports only the InetAddressType
                  values 'unknown (0)' and 'ipv4 (1)'."

        VARIATION   tmnxBsxIcapServerRowStatus
            SYNTAX  RowStatus {
                       active               (1),
                    -- notInService         (2)
                    -- notReady             (3)
                       createAndGo          (4),
                    -- createAndWait        (5)
                       destroy              (6)
                    }
            DESCRIPTION
                 "tmnxBsxIcapServerRowStatus supports only 'active (1)',
                  'createAndGo (4)', and 'destroy (6)'."

        VARIATION   tmnxBsxIsaAaGrpTransPrefV4NmEntr
            SYNTAX  Unsigned32 (0..4095)
            DESCRIPTION
                 "tmnxBsxIsaAaGrpTransPrefV4NmEntr supports the range from 0 to
                  4095."

        VARIATION   tmnxBsxIsaAaGrpTransPrefV4RmEntr
            SYNTAX  Unsigned32 (0..511)
            DESCRIPTION
                 "tmnxBsxIsaAaGrpTransPrefV4RmEntr supports the range from 0 to
                  511."

        VARIATION   tmnxBsxNotifyActionStatus
            SYNTAX  TmnxBsxActionStatus {
                    -- none                 (0)
                       start                (1),
                       stop                 (2)
                    }
            DESCRIPTION
                 "tmnxBsxNotifyActionStatus only supports TmnxBsxActionStatus
                  values of 'start (1)' and 'stop (2)."

        VARIATION   tmnxBsxPolicerOvrdRowStatus
            SYNTAX  RowStatus {
                       active               (1),
                    -- notInService         (2)
                    -- notReady             (3)
                       createAndGo          (4),
                    -- createAndWait        (5)
                       destroy              (6)
                    }
            DESCRIPTION
                 "tmnxBsxPolicerOvrdRowStatus supports only 'active (1)',
                  'createAndGo (4)', and 'destroy (6)'."

        VARIATION   tmnxBsxPolicerRowStatus
            SYNTAX  RowStatus {
                       active               (1),
                    -- notInService         (2)
                    -- notReady             (3)
                       createAndGo          (4),
                    -- createAndWait        (5)
                       destroy              (6)
                    }
            DESCRIPTION
                 "tmnxBsxPolicerRowStatus supports only 'active (1)',
                  'createAndGo (4)', and 'destroy (6)'."

        VARIATION   tmnxBsxPrefixListRowStatus
            SYNTAX  RowStatus {
                       active               (1),
                    -- notInService         (2)
                    -- notReady             (3)
                       createAndGo          (4),
                    -- createAndWait        (5)
                       destroy              (6)
                    }
            DESCRIPTION
                 "tmnxBsxPrefixListRowStatus supports only 'active (1)',
                  'createAndGo (4)', and 'destroy (6)'."

        VARIATION   tmnxBsxPrefixRowStatus
            SYNTAX  RowStatus {
                       active               (1),
                    -- notInService         (2)
                    -- notReady             (3)
                       createAndGo          (4),
                    -- createAndWait        (5)
                       destroy              (6)
                    }
            DESCRIPTION
                 "tmnxBsxPrefixRowStatus supports only 'active (1)',
                  'createAndGo (4)', and 'destroy (6)'."

        VARIATION   tmnxBsxRadApRowStatus
            SYNTAX  RowStatus {
                       active               (1),
                    -- notInService         (2)
                    -- notReady             (3)
                       createAndGo          (4),
                    -- createAndWait        (5)
                       destroy              (6)
                    }
            DESCRIPTION
                 "tmnxBsxRadApRowStatus supports only 'active (1)', 'createAndGo
                  (4)', and 'destroy (6)'."

        VARIATION   tmnxBsxRadApServAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServAddrType supports only the InetAddressType
                  values 'unknown (0)' and 'ipv4 (1)'."

        VARIATION   tmnxBsxRadApServRowStatus
            SYNTAX  RowStatus {
                       active               (1),
                    -- notInService         (2)
                    -- notReady             (3)
                       createAndGo          (4),
                    -- createAndWait        (5)
                       destroy              (6)
                    }
            DESCRIPTION
                 "tmnxBsxRadApServRowStatus supports only 'active (1)',
                  'createAndGo (4)', and 'destroy (6)'."

        VARIATION   tmnxBsxRadApServerAlgorithm
            SYNTAX  TmnxSubRadServAlgorithm {
                       direct               (1),
                       roundRobin           (2)
                    }
            DESCRIPTION
                 "tmnxBsxRadApServerAlgorithm supports only the values 'direct
                  (1)' and 'roundRobin (2)'."

        VARIATION   tmnxBsxRadApServerSrcAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServerSrcAddrType supports only the
                  InetAddressType values 'unknown (0)' and 'ipv4 (1)'."

        VARIATION   tmnxBsxSctpFltrPpidRowStatus
            SYNTAX  RowStatus {
                       active               (1),
                    -- notInService         (2)
                    -- notReady             (3)
                       createAndGo          (4),
                    -- createAndWait        (5)
                       destroy              (6)
                    }
            DESCRIPTION
                 "tmnxBsxSctpFltrPpidRowStatus supports only 'active (1)',
                  'createAndGo (4)', and 'destroy (6)'."

        VARIATION   tmnxBsxSctpFltrRowStatus
            SYNTAX  RowStatus {
                       active               (1),
                    -- notInService         (2)
                    -- notReady             (3)
                       createAndGo          (4),
                    -- createAndWait        (5)
                       destroy              (6)
                    }
            DESCRIPTION
                 "tmnxBsxSctpFltrRowStatus supports only 'active (1)',
                  'createAndGo (4)', and 'destroy (6)'."

        VARIATION   tmnxBsxSessFltrParamsDstAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsDstAddrType supports only the
                  InetAddressType values 'unknown (0)', 'ipv4 (1)', and 'ipv6
                  (2)'."

        VARIATION   tmnxBsxSessFltrParamsDstPortOp
            SYNTAX  TmnxBsxOperator {
                       none                 (0),
                       eq                   (1),
                    -- neq                  (2)
                       lt                   (3),
                       gt                   (4)
                    -- range                (5)
                    }
            DESCRIPTION
                 "tmnxBsxSessFltrParamsDstPortOp only supports the
                  TmnxBsxOperator values of 'none (0)', 'eq (1)', 'lt (3)' and
                  'gt (4)'."

        VARIATION   tmnxBsxSessFltrParamsRowStatus
            SYNTAX  RowStatus {
                       active               (1),
                    -- notInService         (2)
                    -- notReady             (3)
                       createAndGo          (4),
                    -- createAndWait        (5)
                       destroy              (6)
                    }
            DESCRIPTION
                 "tmnxBsxSessFltrParamsRowStatus supports only 'active (1)',
                  'createAndGo (4)', and 'destroy (6)'."

        VARIATION   tmnxBsxSessFltrParamsSrcAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsSrcAddrType supports only the
                  InetAddressType values 'unknown (0)', 'ipv4 (1)', and 'ipv6
                  (2)'."

        VARIATION   tmnxBsxSessFltrParamsSrcPortOp
            SYNTAX  TmnxBsxOperator {
                       none                 (0),
                       eq                   (1),
                    -- neq                  (2)
                       lt                   (3),
                       gt                   (4)
                    -- range                (5)
                    }
            DESCRIPTION
                 "tmnxBsxSessFltrParamsSrcPortOp only supports the
                  TmnxBsxOperator values of 'none (0)', 'eq (1)', 'lt (3)' and
                  'gt (4)'."

        VARIATION   tmnxBsxSessFltrRowStatus
            SYNTAX  RowStatus {
                       active               (1),
                    -- notInService         (2)
                    -- notReady             (3)
                       createAndGo          (4),
                    -- createAndWait        (5)
                       destroy              (6)
                    }
            DESCRIPTION
                 "tmnxBsxSessFltrRowStatus supports only 'active (1)',
                  'createAndGo (4)', and 'destroy (6)'."

        VARIATION   tmnxBsxStatAaSubCfgEntry
            CREATION-REQUIRES {
                       tmnxBsxStatAaSubCfgRowStatus,
                       tmnxBsxStatAaSubCfgExportMethod
                    }
            DESCRIPTION
                 "Both tmnxBsxStatAaSubCfgRowStatus and
                  tmnxBsxStatAaSubCfgExportMethod must be set for row creation
                  to succeed."

        VARIATION   tmnxBsxStatAaSubCfgRowStatus
            SYNTAX  RowStatus {
                       active               (1),
                    -- notInService         (2)
                    -- notReady             (3)
                       createAndGo          (4),
                    -- createAndWait        (5)
                       destroy              (6)
                    }
            DESCRIPTION
                 "tmnxBsxStatAaSubCfgRowStatus supports only 'active (1)',
                  'createAndGo (4)', and 'destroy (6)'."

        VARIATION   tmnxBsxStatAaSubSdyRowStatus
            SYNTAX  RowStatus {
                       active               (1),
                    -- notInService         (2)
                    -- notReady             (3)
                       createAndGo          (4),
                    -- createAndWait        (5)
                       destroy              (6)
                    }
            DESCRIPTION
                 "tmnxBsxStatAaSubSdyRowStatus supports only 'active (1)',
                  'createAndGo (4)', and 'destroy (6)'."

        VARIATION   tmnxBsxStatTcaCfgRowStatus
            SYNTAX  RowStatus {
                       active               (1),
                    -- notInService         (2)
                    -- notReady             (3)
                       createAndGo          (4),
                    -- createAndWait        (5)
                       destroy              (6)
                    }
            DESCRIPTION
                 "tmnxBsxStatTcaCfgRowStatus supports only 'active (1)',
                  'createAndGo (4)', and 'destroy (6)'."

        VARIATION   tmnxBsxStatTcaFtrCfgRowStatus
            SYNTAX  RowStatus {
                       active               (1),
                    -- notInService         (2)
                    -- notReady             (3)
                       createAndGo          (4),
                    -- createAndWait        (5)
                       destroy              (6)
                    }
            DESCRIPTION
                 "tmnxBsxStatTcaFtrCfgRowStatus supports only 'active (1)',
                  'createAndGo (4)', and 'destroy (6)'."

        VARIATION   tmnxBsxStatTcaFtrEnCfgRowStatus
            SYNTAX  RowStatus {
                       active               (1),
                    -- notInService         (2)
                    -- notReady             (3)
                       createAndGo          (4),
                    -- createAndWait        (5)
                       destroy              (6)
                    }
            DESCRIPTION
                 "tmnxBsxStatTcaFtrEnCfgRowStatus supports only 'active (1)',
                  'createAndGo (4)', and 'destroy (6)'."

        VARIATION   tmnxBsxStatTcaPolcrCfgRowStatus
            SYNTAX  RowStatus {
                       active               (1),
                    -- notInService         (2)
                    -- notReady             (3)
                       createAndGo          (4),
                    -- createAndWait        (5)
                       destroy              (6)
                    }
            DESCRIPTION
                 "tmnxBsxStatTcaPolcrCfgRowStatus supports only 'active (1)',
                  'createAndGo (4)', and 'destroy (6)'."

        VARIATION   tmnxBsxTcpValRowStatus
            SYNTAX  RowStatus {
                       active               (1),
                    -- notInService         (2)
                    -- notReady             (3)
                       createAndGo          (4),
                    -- createAndWait        (5)
                       destroy              (6)
                    }
            DESCRIPTION
                 "tmnxBsxTcpValRowStatus supports only 'active (1)',
                  'createAndGo (4)', and 'destroy (6)'."

        VARIATION   tmnxBsxTcpValTcaRowStatus
            SYNTAX  RowStatus {
                       active               (1),
                    -- notInService         (2)
                    -- notReady             (3)
                       createAndGo          (4),
                    -- createAndWait        (5)
                       destroy              (6)
                    }
            DESCRIPTION
                 "tmnxBsxTcpValTcaRowStatus supports only 'active (1)',
                  'createAndGo (4)', and 'destroy (6)'."

        VARIATION   tmnxBsxTransIpPlcyAddrRowStatus
            SYNTAX  RowStatus {
                       active               (1),
                    -- notInService         (2)
                    -- notReady             (3)
                       createAndGo          (4),
                    -- createAndWait        (5)
                       destroy              (6)
                    }
            DESCRIPTION
                 "tmnxBsxTransIpPlcyAddrRowStatus supports only 'active (1)',
                  'createAndGo (4)', and 'destroy (6)'."

        VARIATION   tmnxBsxTransIpPlcySubRowStatus
            SYNTAX  RowStatus {
                       active               (1),
                    -- notInService         (2)
                    -- notReady             (3)
                       createAndGo          (4),
                    -- createAndWait        (5)
                       destroy              (6)
                    }
            DESCRIPTION
                 "tmnxBsxTransIpPlcySubRowStatus supports only 'active (1)',
                  'createAndGo (4)', and 'destroy (6)'."

        VARIATION   tmnxBsxTransPrefEntryNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntryNetAddrType supports only the
                  InetAddressType values 'unknown (0)' and 'ipv4 (1)'."

        VARIATION   tmnxBsxTransPrefEntryRowStatus
            SYNTAX  RowStatus {
                       active               (1),
                    -- notInService         (2)
                    -- notReady             (3)
                       createAndGo          (4),
                    -- createAndWait        (5)
                       destroy              (6)
                    }
            DESCRIPTION
                 "tmnxBsxTransPrefEntryRowStatus supports only 'active (1)',
                  'createAndGo (4)', and 'destroy (6)'."

        VARIATION   tmnxBsxTransPrefEntrySubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntrySubAddrType supports only the
                  InetAddressType values 'unknown (0)' and 'ipv4 (1)'."

        VARIATION   tmnxBsxTransPrefPolicyRowStatus
            SYNTAX  RowStatus {
                       active               (1),
                    -- notInService         (2)
                    -- notReady             (3)
                       createAndGo          (4),
                    -- createAndWait        (5)
                       destroy              (6)
                    }
            DESCRIPTION
                 "tmnxBsxTransPrefPolicyRowStatus supports only 'active (1)',
                  'createAndGo (4)', and 'destroy (6)'."

        VARIATION   tmnxBsxTransPrefSubRowStatus
            SYNTAX  RowStatus {
                       active               (1),
                    -- notInService         (2)
                    -- notReady             (3)
                       createAndGo          (4),
                    -- createAndWait        (5)
                       destroy              (6)
                    }
            DESCRIPTION
                 "tmnxBsxTransPrefSubRowStatus supports only 'active (1)',
                  'createAndGo (4)', and 'destroy (6)'."

        VARIATION   tmnxBsxTransPrefSumNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumNetAddrType supports only the
                  InetAddressType values 'unknown (0)' and 'ipv4 (1)'."

        VARIATION   tmnxBsxTransPrefSumSubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumSubAddrType supports only the
                  InetAddressType values 'unknown (0)' and 'ipv4 (1)'."

        VARIATION   tmnxBsxTransitIpPolicyAddrType
            SYNTAX  InetAddressType {
                    -- unknown              (0)
                       ipv4                 (1),
                       ipv6                 (2)
                    -- ipv4z                (3)
                    -- ipv6z                (4)
                    -- dns                  (16)
                    }
            DESCRIPTION
                 "tmnxBsxTransitIpPolicyAddrType supports only the
                  InetAddressType values 'ipv4 (1)', and 'ipv6 (2)'."

        VARIATION   tmnxBsxTransitIpPolicyIPv6PfxLen
            SYNTAX  InetAddressPrefixLength (32..64)
            DESCRIPTION
                 "tmnxBsxTransitIpPolicyIPv6PfxLen supports only the range from
                  32 to 64."

        VARIATION   tmnxBsxTransitIpPolicyRowStatus
            SYNTAX  RowStatus {
                       active               (1),
                    -- notInService         (2)
                    -- notReady             (3)
                       createAndGo          (4),
                    -- createAndWait        (5)
                       destroy              (6)
                    }
            DESCRIPTION
                 "tmnxBsxTransitIpPolicyRowStatus supports only 'active (1)',
                  'createAndGo (4)', and 'destroy (6)'."

        VARIATION   tmnxBsxTransitIpSumParentSubType
            SYNTAX  TmnxBsxAaSubscriberType {
                       unknown              (0),
                    -- esm                  (1)
                       sap                  (2),
                       spokeSdp             (3)
                    -- transit              (4)
                    }
            DESCRIPTION
                 "tmnxBsxTransitIpSumParentSubType supports only the values
                  'unknown(0)', 'sap(2)', and 'spokeSdp(3)'."

        VARIATION   tmnxBsxUrlFilterRowStatus
            SYNTAX  RowStatus {
                       active               (1),
                    -- notInService         (2)
                    -- notReady             (3)
                       createAndGo          (4),
                    -- createAndWait        (5)
                       destroy              (6)
                    }
            DESCRIPTION
                 "tmnxBsxUrlFilterRowStatus supports only 'active (1)',
                  'createAndGo (4)', and 'destroy (6)'."

        VARIATION   tmnxBsxUrlFltrUrlListRowStatus
            SYNTAX  RowStatus {
                       active               (1),
                    -- notInService         (2)
                    -- notReady             (3)
                       createAndGo          (4),
                    -- createAndWait        (5)
                       destroy              (6)
                    }
            DESCRIPTION
                 "tmnxBsxUrlFltrUrlListRowStatus supports only 'active (1)',
                  'createAndGo (4)', and 'destroy (6)'."

        VARIATION   tmnxBsxUrlListRowStatus
            SYNTAX  RowStatus {
                       active               (1),
                    -- notInService         (2)
                    -- notReady             (3)
                       createAndGo          (4),
                    -- createAndWait        (5)
                       destroy              (6)
                    }
            DESCRIPTION
                 "tmnxBsxUrlListRowStatus supports only 'active (1)',
                  'createAndGo (4)', and 'destroy (6)'."

    ::= { tmnx7750c12AgentV14v0  66 }

--
-- 7750c4 BSX CAPABILITIES
--
tmnx7750c4BsxV14v0                AGENT-CAPABILITIES
    PRODUCT-RELEASE "Nokia SROS"
    STATUS          current
    DESCRIPTION
         "Implementation of BSX capabilities for Nokia 7750 c4 systems release
          14.0."

    SUPPORTS        TIMETRA-BSX-NG-MIB
        INCLUDES {
           tmnxBsxCflowdDirectExportGroup,
           tmnxBsxCflowdGroup,
           tmnxBsxCflowdGroupV10v0,
           tmnxBsxCflowdGroupV9v0,
           tmnxBsxDnsIpCacheGroupV13v0,
           tmnxBsxEventLogSyslogObjGrp,
           tmnxBsxGtpGroupV13v0,
           tmnxBsxGtpUntunnelingObjGrp,
           tmnxBsxHttpEnAntiSpfStObGrpV11v0,
           tmnxBsxHttpEnrAntiSpfObjGrpV11v0,
           tmnxBsxHttpEnrEncObjGrpV11v0,
           tmnxBsxHttpEnrStStrObjGrpV12v0,
           tmnxBsxHttpEnrichObjGroup,
           tmnxBsxHttpEnrichStatObjGroup,
           tmnxBsxHttpNotifObjGrp,
           tmnxBsxHttpNotifObjGrpV13v0,
           tmnxBsxHttpRedirErrGroup,
           tmnxBsxHttpRedirGroup,
           tmnxBsxHttpRedirObjGrpV12v0,
           tmnxBsxHttpRedirObjGrpV13v0,
           tmnxBsxHttpsCaptiveRedirObjGrp,
           tmnxBsxIpPrefixListObjGrpV12v0,
           tmnxBsxIsa2ObjGroup,
           tmnxBsxLwObjGrpV12v0,
           tmnxBsxMdaGroupV10v0,
           tmnxBsxMdaGroupV11v0,
           tmnxBsxMdaGroupV12v0,
           tmnxBsxMdaGroupV7v0,
           tmnxBsxMdaGroupV8v0,
           tmnxBsxMgBillingExclusionsGroup,
           tmnxBsxMgTetherDetectGroup,
           tmnxBsxMobileGatewayGroup,
           tmnxBsxNotificationGroup,
           tmnxBsxNotificationGroupV10v0,
           tmnxBsxNotificationGroupV11v0,
           tmnxBsxNotificationGroupV12v0,
           tmnxBsxNotificationGroupV13v0,
           tmnxBsxNotificationGroupV14v0,
           tmnxBsxNotificationGroupV7v0,
           tmnxBsxNotificationGroupV8v0,
           tmnxBsxNotificationGroupV9v0,
           tmnxBsxNotifyObjsGroup,
           tmnxBsxNotifyObjsGroupV13v0,
           tmnxBsxNotifyObjsGroupV14v0,
           tmnxBsxNotifyObjsGroupV7v0,
           tmnxBsxNotifyObjsGroupV8v0,
           tmnxBsxOvrdGroup,
           tmnxBsxPolicyObjGrp12v0,
           tmnxBsxPolicyObjGrp13v0,
           tmnxBsxPolicyTimeStampExtObjGrp,
           tmnxBsxPolicyTodObjGrp,
           tmnxBsxRadApNotificationGroup,
           tmnxBsxRadApObjGroup,
           tmnxBsxRadApStatObjGroup,
           tmnxBsxRadiusAccountingObjGroup,
           tmnxBsxRadiusAcctObjGroupV11v0,
           tmnxBsxRedundancyEnhObjGroup,
           tmnxBsxRedundancyObjGroup,
           tmnxBsxSessionFilterObjGrp,
           tmnxBsxStaticObjGroup,
           tmnxBsxStatsGroup,
           tmnxBsxStatsGroupV9v0,
           tmnxBsxStflFwEnhacementsObjGrp,
           tmnxBsxTcpMssObjGrp,
           tmnxBsxTcpValObjGrp,
           tmnxBsxTrafficStatsObjGrpV12v0,
           tmnxBsxTrafficStatsObjGrpV13v0,
           tmnxBsxTransitGroup,
           tmnxBsxTransitGroupV10v0,
           tmnxBsxTransitIpPolicyDiamObjGrp,
           tmnxBsxTransitSeenIpGroup,
           tmnxBsxTrapPerfObjGrp,
           tmnxBsxUrlFilterObjGrp,
           tmnxBsxUrlFilterObjGrpV12v0,
           tmnxBsxUrlFilterStatsObjGrp,
           tmnxBsxUrlListExtendedGroup,
           tmnxBsxUrlListGroupV13v0,
           tmnxBsxUsageMonObjGrpV12v0,
           tmnxBsxXHeaderObjGroup
        }

        VARIATION   tmnxBsxAaGrpPartRowStatus
            SYNTAX  RowStatus {
                       active               (1),
                    -- notInService         (2)
                    -- notReady             (3)
                       createAndGo          (4),
                    -- createAndWait        (5)
                       destroy              (6)
                    }
            DESCRIPTION
                 "tmnxBsxAaGrpPartRowStatus supports only 'active (1)',
                  'createAndGo (4)', and 'destroy (6)'."

        VARIATION   tmnxBsxAaIfAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfAddrType supports only the InetAddressType values
                  'unknown (0)' and 'ipv4 (1)'."

        VARIATION   tmnxBsxAaIfIsaAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfIsaAddrType supports only the InetAddressType
                  values 'unknown (0)' and 'ipv4 (1)'."

        VARIATION   tmnxBsxAarpInstPeerEPSapEncType
            SYNTAX  INTEGER {
                       unknown              (0),
                       nullEncap            (1),
                    -- qEncap               (2)
                    -- mplsEncap            (3)
                    -- bcpNullEncap         (4)
                       bcpDot1qEncap        (5),
                    -- ipcpEncap            (6)
                    -- frEncap              (7)
                    -- pppAutoEncap         (8)
                    -- atmEncap             (9)
                       qinqEncap            (10)
                    -- wanMirrorEncap       (11)
                    -- ciscoHDLCEncap       (12)
                    -- cemEncap             (13)
                    }
            DESCRIPTION
                 "tmnxBsxAarpInstPeerEPSapEncType supports only
                  TmnxPortEncapType 'unknown(0)', 'nullEncap(1)',
                  'bcpDot1qEncap(5)', and 'qinqEncap(10)'."

        VARIATION   tmnxBsxAarpInstPeerIpType
            SYNTAX  InetAddressType {
                       unknown              (0),
                       ipv4                 (1)
                    -- ipv6                 (2)
                    -- ipv4z                (3)
                    -- ipv6z                (4)
                    -- dns                  (16)
                    }
            DESCRIPTION
                 "tmnxBsxAarpInstPeerIpType supports only the InetAddressType
                  values 'unknown (0)' and 'ipv4 (1)'."

        VARIATION   tmnxBsxAarpInstRowStatus
            SYNTAX  RowStatus {
                       active               (1),
                    -- notInService         (2)
                    -- notReady             (3)
                       createAndGo          (4),
                    -- createAndWait        (5)
                       destroy              (6)
                    }
            DESCRIPTION
                 "tmnxBsxAarpInstRowStatus supports only 'active (1)',
                  'createAndGo (4)', and 'destroy (6)'."

        VARIATION   tmnxBsxAppFilterExprIndex
            SYNTAX  Integer32 (1..4)
            DESCRIPTION
                 "tmnxBsxAppFilterExprIndex supports a range from 1 to 4
                  expressions."

        VARIATION   tmnxBsxAppFilterExprOperator
            SYNTAX  TmnxBsxOperator {
                       none                 (0),
                       eq                   (1),
                       neq                  (2)
                    -- lt                   (3)
                    -- gt                   (4)
                    -- range                (5)
                    }
            DESCRIPTION
                 "tmnxBsxAppFilterExprOperator only supports TmnxBsxOperator
                  values of 'none (0)', 'eq (1)' and 'neq (2)."

        VARIATION   tmnxBsxAppFilterNetworkAddrOp
            SYNTAX  TmnxBsxOperator {
                       none                 (0),
                       eq                   (1),
                       neq                  (2)
                    -- lt                   (3)
                    -- gt                   (4)
                    -- range                (5)
                    }
            DESCRIPTION
                 "tmnxBsxAppFilterNetworkAddrOp only supports TmnxBsxOperator
                  values of 'none (0)', 'eq (1)' and 'neq (2)."

        VARIATION   tmnxBsxAppFilterNetworkAddrType
            SYNTAX  InetAddressType {
                       unknown              (0),
                       ipv4                 (1),
                       ipv6                 (2)
                    -- ipv4z                (3)
                    -- ipv6z                (4)
                    -- dns                  (16)
                    }
            DESCRIPTION
                 "tmnxBsxAppFilterNetworkAddrType supports only the
                  InetAddressType values 'unknown (0)', 'ipv4 (1)', and 'ipv6
                  (2)'."

        VARIATION   tmnxBsxAppFilterServerAddrOp
            SYNTAX  TmnxBsxOperator {
                       none                 (0),
                       eq                   (1),
                       neq                  (2)
                    -- lt                   (3)
                    -- gt                   (4)
                    -- range                (5)
                    }
            DESCRIPTION
                 "tmnxBsxAppFilterServerAddrOp only supports TmnxBsxOperator
                  values of 'none (0)', 'eq (1)' and 'neq (2)."

        VARIATION   tmnxBsxAppFilterServerAddrType
            SYNTAX  InetAddressType {
                       unknown              (0),
                       ipv4                 (1),
                       ipv6                 (2)
                    -- ipv4z                (3)
                    -- ipv6z                (4)
                    -- dns                  (16)
                    }
            DESCRIPTION
                 "tmnxBsxAppFilterServerAddrType supports only the
                  InetAddressType values 'unknown (0)', 'ipv4 (1)', and 'ipv6
                  (2)'."

        VARIATION   tmnxBsxAppFilterServerPortOp
            SYNTAX  TmnxBsxOperator {
                       none                 (0),
                       eq                   (1),
                       neq                  (2),
                       lt                   (3),
                       gt                   (4)
                    -- range                (5)
                    }
            DESCRIPTION
                 "tmnxBsxAppFilterServerPortOp only supports TmnxBsxOperator
                  values of 'none (0)', 'eq (1)', 'neq (2)', 'lt (3)' and 'gt
                  (4)."

        VARIATION   tmnxBsxAppGrpRowStatus
            SYNTAX  RowStatus {
                       active               (1),
                    -- notInService         (2)
                    -- notReady             (3)
                       createAndGo          (4),
                    -- createAndWait        (5)
                       destroy              (6)
                    }
            DESCRIPTION
                 "tmnxBsxAppGrpRowStatus supports only 'active (1)',
                  'createAndGo (4)', and 'destroy (6)'."

        VARIATION   tmnxBsxAppGrpStorageType
            SYNTAX  StorageType {
                    -- other(1)
                    -- volatile(2)
                       nonVolatile(3),
                       permanent(4)
                    -- readOnly(5)
                    }
            DESCRIPTION
                 "tmnxBsxAppGrpStorageType supports only the values 'nonVolatile
                  (3)' and 'permanent (4)'."

        VARIATION   tmnxBsxAppProfRowStatus
            SYNTAX  RowStatus {
                       active               (1),
                    -- notInService         (2)
                    -- notReady             (3)
                       createAndGo          (4),
                    -- createAndWait        (5)
                       destroy              (6)
                    }
            DESCRIPTION
                 "tmnxBsxAppProfRowStatus supports only 'active (1)',
                  'createAndGo (4)', and 'destroy (6)'."

        VARIATION   tmnxBsxAppRowStatus
            SYNTAX  RowStatus {
                       active               (1),
                    -- notInService         (2)
                    -- notReady             (3)
                       createAndGo          (4),
                    -- createAndWait        (5)
                       destroy              (6)
                    }
            DESCRIPTION
                 "tmnxBsxAppRowStatus supports only 'active (1)', 'createAndGo
                  (4)', and 'destroy (6)'."

        VARIATION   tmnxBsxAppStorageType
            SYNTAX  StorageType {
                    -- other(1)
                    -- volatile(2)
                       nonVolatile(3),
                       permanent(4)
                    -- readOnly(5)
                    }
            DESCRIPTION
                 "tmnxBsxAppStorageType supports only the values 'nonVolatile
                  (3)' and 'permanent (4)'."

        VARIATION   tmnxBsxAqpBaseRowStatus
            SYNTAX  RowStatus {
                       active               (1),
                    -- notInService         (2)
                    -- notReady             (3)
                       createAndGo          (4),
                    -- createAndWait        (5)
                       destroy              (6)
                    }
            DESCRIPTION
                 "tmnxBsxAqpBaseRowStatus supports only 'active (1)',
                  'createAndGo (4)', and 'destroy (6)'."

        VARIATION   tmnxBsxAqpCharOperator
            SYNTAX  TmnxBsxOperator {
                    -- none                 (0)
                       eq                   (1)
                    -- neq                  (2)
                    -- lt                   (3)
                    -- gt                   (4)
                    -- range                (5)
                    }
            DESCRIPTION
                 "tmnxBsxAqpCharOperator only supports the TmnxBsxOperator value
                  of 'eq (1)'."

        VARIATION   tmnxBsxAqpCharRowStatus
            SYNTAX  RowStatus {
                       active               (1),
                    -- notInService         (2)
                    -- notReady             (3)
                       createAndGo          (4),
                    -- createAndWait        (5)
                       destroy              (6)
                    }
            DESCRIPTION
                 "tmnxBsxAqpCharRowStatus supports only 'active (1)',
                  'createAndGo (4)', and 'destroy (6)'."

        VARIATION   tmnxBsxAqpChargeGrpOp
            SYNTAX  TmnxBsxOperator {
                       none                 (0),
                       eq                   (1),
                       neq                  (2)
                    -- lt                   (3)
                    -- gt                   (4)
                    -- range                (5)
                    }
            DESCRIPTION
                 "tmnxBsxAqpChargeGrpOp only supports TmnxBsxOperator values of
                  'none (0)', 'eq (1)' and 'neq (2)."

        VARIATION   tmnxBsxAqpDstAddress
            SYNTAX  InetAddress (SIZE (0|4))
            DESCRIPTION
                 "tmnxBsxAqpDstAddress only supports InetAddressType 'unknown
                  (0)' and 'ipv4 (1)'."

        VARIATION   tmnxBsxAqpDstAddressOp
            SYNTAX  TmnxBsxOperator {
                       none                 (0),
                       eq                   (1),
                       neq                  (2)
                    -- lt                   (3)
                    -- gt                   (4)
                    -- range                (5)
                    }
            DESCRIPTION
                 "tmnxBsxAqpDstAddressOp only supports TmnxBsxOperator values of
                  'none (0)', 'eq (1)' and 'neq (2)."

        VARIATION   tmnxBsxAqpDstAddressType
            SYNTAX  InetAddressType {
                       unknown              (0),
                       ipv4                 (1)
                    -- ipv6                 (2)
                    -- ipv4z                (3)
                    -- ipv6z                (4)
                    -- dns                  (16)
                    }
            DESCRIPTION
                 "tmnxBsxAqpDstAddressType supports only the InetAddressType
                  values 'unknown (0)' and 'ipv4 (1)'."

        VARIATION   tmnxBsxAqpDstPortOp
            SYNTAX  TmnxBsxOperator {
                       none                 (0),
                       eq                   (1),
                       neq                  (2)
                    -- lt                   (3)
                    -- gt                   (4)
                    -- range                (5)
                    }
            DESCRIPTION
                 "tmnxBsxAqpDstPortOp only supports TmnxBsxOperator values of
                  'none (0)', 'eq (1)' and 'neq (2)."

        VARIATION   tmnxBsxAqpIpProtocolNumOp
            SYNTAX  TmnxBsxOperator {
                       none                 (0),
                       eq                   (1),
                       neq                  (2)
                    -- lt                   (3)
                    -- gt                   (4)
                    -- range                (5)
                    }
            DESCRIPTION
                 "tmnxBsxAqpIpProtocolNumOp only supports TmnxBsxOperator values
                  of 'none (0)', 'eq (1)' and 'neq (2)."

        VARIATION   tmnxBsxAqpOutOfOrderFrags
            ACCESS  not-implemented
            DESCRIPTION
                 "tmnxBsxAqpOutOfOrderFrags is not implemented on Nokia 7750 c4
                  in release 14.0."

        VARIATION   tmnxBsxAqpSapSubscrOp
            SYNTAX  TmnxBsxOperator {
                       none                 (0),
                       eq                   (1),
                       neq                  (2)
                    -- lt                   (3)
                    -- gt                   (4)
                    -- range                (5)
                    }
            DESCRIPTION
                 "tmnxBsxAqpSapSubscrOp only supports TmnxBsxOperator values of
                  'none (0)', 'eq (1)' and 'neq (2)."

        VARIATION   tmnxBsxAqpSrcAddress
            SYNTAX  InetAddress (SIZE (0|4))
            DESCRIPTION
                 "tmnxBsxAqpSrcAddress only supports InetAddressType 'unknown
                  (0)' and 'ipv4 (1)'."

        VARIATION   tmnxBsxAqpSrcAddressOp
            SYNTAX  TmnxBsxOperator {
                       none                 (0),
                       eq                   (1),
                       neq                  (2)
                    -- lt                   (3)
                    -- gt                   (4)
                    -- range                (5)
                    }
            DESCRIPTION
                 "tmnxBsxAqpSrcAddressOp only supports TmnxBsxOperator values of
                  'none (0)', 'eq (1)' and 'neq (2)."

        VARIATION   tmnxBsxAqpSrcAddressType
            SYNTAX  InetAddressType {
                       unknown              (0),
                       ipv4                 (1)
                    -- ipv6                 (2)
                    -- ipv4z                (3)
                    -- ipv6z                (4)
                    -- dns                  (16)
                    }
            DESCRIPTION
                 "tmnxBsxAqpSrcAddressType supports only the InetAddressType
                  values 'unknown (0)' and 'ipv4 (1)'."

        VARIATION   tmnxBsxAqpSrcPortOp
            SYNTAX  TmnxBsxOperator {
                       none                 (0),
                       eq                   (1),
                       neq                  (2)
                    -- lt                   (3)
                    -- gt                   (4)
                    -- range                (5)
                    }
            DESCRIPTION
                 "tmnxBsxAqpSrcPortOp only supports TmnxBsxOperator values of
                  'none (0)', 'eq (1)' and 'neq (2)."

        VARIATION   tmnxBsxAsoPersistId
            ACCESS  not-implemented
            DESCRIPTION
                 "tmnxBsxAsoPersistId is not implemented on Nokia 7750 c4 in
                  release 14.0."

        VARIATION   tmnxBsxAsoRowStatus
            SYNTAX  RowStatus {
                       active               (1),
                    -- notInService         (2)
                    -- notReady             (3)
                       createAndGo          (4),
                    -- createAndWait        (5)
                       destroy              (6)
                    }
            DESCRIPTION
                 "tmnxBsxAsoRowStatus supports only 'active (1)', 'createAndGo
                  (4)', and 'destroy (6)'."

        VARIATION   tmnxBsxAsoValPersistId
            ACCESS  not-implemented
            DESCRIPTION
                 "tmnxBsxAsoValPersistId is not implemented on Nokia 7750 c4 in
                  release 14.0."

        VARIATION   tmnxBsxAsoValRowStatus
            SYNTAX  RowStatus {
                       active               (1),
                    -- notInService         (2)
                    -- notReady             (3)
                       createAndGo          (4),
                    -- createAndWait        (5)
                       destroy              (6)
                    }
            DESCRIPTION
                 "tmnxBsxAsoValRowStatus supports only 'active (1)',
                  'createAndGo (4)', and 'destroy (6)'."

        VARIATION   tmnxBsxCflowdCollAddress
            SYNTAX  InetAddress (SIZE (0|4))
            DESCRIPTION
                 "tmnxBsxCflowdCollAddress only supports InetAddressType
                  'unknown (0)' and 'ipv4 (1)'."

        VARIATION   tmnxBsxCflowdCollAddressType
            SYNTAX  InetAddressType {
                       unknown              (0),
                       ipv4                 (1)
                    -- ipv6                 (2)
                    -- ipv4z                (3)
                    -- ipv6z                (4)
                    -- dns                  (16)
                    }
            DESCRIPTION
                 "tmnxBsxCflowdCollAddressType supports only the InetAddressType
                  values 'unknown (0)' and 'ipv4 (1)'."

        VARIATION   tmnxBsxCflowdCollRowStatus
            SYNTAX  RowStatus {
                       active               (1),
                    -- notInService         (2)
                    -- notReady             (3)
                       createAndGo          (4),
                    -- createAndWait        (5)
                       destroy              (6)
                    }
            DESCRIPTION
                 "tmnxBsxCflowdCollRowStatus supports only 'active (1)',
                  'createAndGo (4)', and 'destroy (6)'."

        VARIATION   tmnxBsxCflowdDirExpAddrRowStatus
            SYNTAX  RowStatus {
                       active               (1),
                    -- notInService         (2)
                    -- notReady             (3)
                       createAndGo          (4),
                    -- createAndWait        (5)
                       destroy              (6)
                    }
            DESCRIPTION
                 "tmnxBsxCflowdDirExpAddrRowStatus supports only 'active (1)',
                  'createAndGo (4)', and 'destroy (6)'."

        VARIATION   tmnxBsxCflowdDirectExpRowStatus
            SYNTAX  RowStatus {
                       active               (1),
                    -- notInService         (2)
                    -- notReady             (3)
                       createAndGo          (4),
                    -- createAndWait        (5)
                       destroy              (6)
                    }
            DESCRIPTION
                 "tmnxBsxCflowdDirectExpRowStatus supports only 'active (1)',
                  'createAndGo (4)', and 'destroy (6)'."

        VARIATION   tmnxBsxCflowdPerfExpRowStatus
            SYNTAX  RowStatus {
                       active               (1),
                    -- notInService         (2)
                    -- notReady             (3)
                       createAndGo          (4),
                    -- createAndWait        (5)
                       destroy              (6)
                    }
            DESCRIPTION
                 "tmnxBsxCflowdPerfExpRowStatus supports only 'active (1)',
                  'createAndGo (4)', and 'destroy (6)'."

        VARIATION   tmnxBsxChargeGrpRowStatus
            SYNTAX  RowStatus {
                       active               (1),
                    -- notInService         (2)
                    -- notReady             (3)
                       createAndGo          (4),
                    -- createAndWait        (5)
                       destroy              (6)
                    }
            DESCRIPTION
                 "tmnxBsxChargeGrpRowStatus supports only 'active (1)',
                  'createAndGo (4)', and 'destroy (6)'."

        VARIATION   tmnxBsxCustProtEntryId
            SYNTAX  TEntryId (1..10)
            DESCRIPTION
                 "tmnxBsxCustProtEntryId supports a range from 1 to 10 custom
                  protocol entries."

        VARIATION   tmnxBsxCustProtExprIndex
            SYNTAX  Integer32 (1)
            DESCRIPTION
                 "tmnxBsxCustProtExprIndex only supports 1 custom protocol
                  expression."

        VARIATION   tmnxBsxCustProtExprOperator
            SYNTAX  TmnxBsxOperator {
                    -- none                 (0)
                       eq                   (1)
                    -- neq                  (2)
                    -- lt                   (3)
                    -- gt                   (4)
                    -- range                (5)
                    }
            DESCRIPTION
                 "tmnxBsxCustProtExprOperator only supports the TmnxBsxOperator
                  value of 'eq (1)'."

        VARIATION   tmnxBsxCustProtExprRowStatus
            SYNTAX  RowStatus {
                       active               (1),
                    -- notInService         (2)
                    -- notReady             (3)
                       createAndGo          (4),
                    -- createAndWait        (5)
                       destroy              (6)
                    }
            DESCRIPTION
                 "tmnxBsxCustProtExprRowStatus supports only 'active (1)',
                  'createAndGo (4)', and 'destroy (6)'."

        VARIATION   tmnxBsxCustProtIpProtocolNum
            DESCRIPTION
                 "tmnxBsxCustProtIpProtocolNum supports only the values not set
                  (-1), tcp (6) and udp (17)."

        VARIATION   tmnxBsxCustProtRowStatus
            SYNTAX  RowStatus {
                       active               (1),
                    -- notInService         (2)
                    -- notReady             (3)
                       createAndGo          (4),
                    -- createAndWait        (5)
                       destroy              (6)
                    }
            DESCRIPTION
                 "tmnxBsxCustProtRowStatus supports only 'active (1)',
                  'createAndGo (4)', and 'destroy (6)'."

        VARIATION   tmnxBsxDnsIpCacheDomainRowStatus
            SYNTAX  RowStatus {
                       active               (1),
                    -- notInService         (2)
                    -- notReady             (3)
                       createAndGo          (4),
                    -- createAndWait        (5)
                       destroy              (6)
                    }
            DESCRIPTION
                 "tmnxBsxDnsIpCacheDomainRowStatus supports only 'active (1)',
                  'createAndGo (4)', and 'destroy (6)'."

        VARIATION   tmnxBsxDnsIpCacheRowStatus
            SYNTAX  RowStatus {
                       active               (1),
                    -- notInService         (2)
                    -- notReady             (3)
                       createAndGo          (4),
                    -- createAndWait        (5)
                       destroy              (6)
                    }
            DESCRIPTION
                 "tmnxBsxDnsIpCacheRowStatus supports only 'active (1)',
                  'createAndGo (4)', and 'destroy (6)'."

        VARIATION   tmnxBsxDnsIpCacheServerAddrType
            SYNTAX  InetAddressType {
                    -- unknown              (0)
                       ipv4                 (1),
                       ipv6                 (2)
                    -- ipv4z                (3)
                    -- ipv6z                (4)
                    -- dns                  (16)
                    }
            DESCRIPTION
                 "tmnxBsxDnsIpCacheServerAddrType supports only the
                  InetAddressType values 'ipv4 (1)', and 'ipv6 (2)'."

        VARIATION   tmnxBsxDnsIpCacheServerRowStatus
            SYNTAX  RowStatus {
                       active               (1),
                    -- notInService         (2)
                    -- notReady             (3)
                       createAndGo          (4),
                    -- createAndWait        (5)
                       destroy              (6)
                    }
            DESCRIPTION
                 "tmnxBsxDnsIpCacheServerRowStatus supports only 'active (1)',
                  'createAndGo (4)', and 'destroy (6)'."

        VARIATION   tmnxBsxEventLogRowStatus
            SYNTAX  RowStatus {
                       active               (1),
                    -- notInService         (2)
                    -- notReady             (3)
                       createAndGo          (4),
                    -- createAndWait        (5)
                       destroy              (6)
                    }
            DESCRIPTION
                 "tmnxBsxEventLogRowStatus supports only 'active (1)',
                  'createAndGo (4)', and 'destroy (6)'."

        VARIATION   tmnxBsxGtpFltrMsgRowStatus
            SYNTAX  RowStatus {
                       active               (1),
                    -- notInService         (2)
                    -- notReady             (3)
                       createAndGo          (4),
                    -- createAndWait        (5)
                       destroy              (6)
                    }
            DESCRIPTION
                 "tmnxBsxGtpFltrMsgRowStatus supports only 'active (1)',
                  'createAndGo (4)', and 'destroy (6)'."

        VARIATION   tmnxBsxGtpFltrRowStatus
            SYNTAX  RowStatus {
                       active               (1),
                    -- notInService         (2)
                    -- notReady             (3)
                       createAndGo          (4),
                    -- createAndWait        (5)
                       destroy              (6)
                    }
            DESCRIPTION
                 "tmnxBsxGtpFltrRowStatus supports only 'active (1)',
                  'createAndGo (4)', and 'destroy (6)'."

        VARIATION   tmnxBsxHttpEnrichFieldRowStatus
            SYNTAX  RowStatus {
                       active               (1),
                    -- notInService         (2)
                    -- notReady             (3)
                       createAndGo          (4),
                    -- createAndWait        (5)
                       destroy              (6)
                    }
            DESCRIPTION
                 "tmnxBsxHttpEnrichFieldRowStatus supports only 'active (1)',
                  'createAndGo (4)', and 'destroy (6)'."

        VARIATION   tmnxBsxHttpEnrichRowStatus
            SYNTAX  RowStatus {
                       active               (1),
                    -- notInService         (2)
                    -- notReady             (3)
                       createAndGo          (4),
                    -- createAndWait        (5)
                       destroy              (6)
                    }
            DESCRIPTION
                 "tmnxBsxHttpEnrichRowStatus supports only 'active (1)',
                  'createAndGo (4)', and 'destroy (6)'."

        VARIATION   tmnxBsxHttpNotifRowStatus
            SYNTAX  RowStatus {
                       active               (1),
                    -- notInService         (2)
                    -- notReady             (3)
                       createAndGo          (4),
                    -- createAndWait        (5)
                       destroy              (6)
                    }
            DESCRIPTION
                 "tmnxBsxHttpNotifRowStatus supports only 'active (1)',
                  'createAndGo (4)', and 'destroy (6)'."

        VARIATION   tmnxBsxHttpRedirErrCodeRowStatus
            SYNTAX  RowStatus {
                       active               (1),
                    -- notInService         (2)
                    -- notReady             (3)
                       createAndGo          (4),
                    -- createAndWait        (5)
                       destroy              (6)
                    }
            DESCRIPTION
                 "tmnxBsxHttpRedirErrCodeRowStatus supports only 'active (1)',
                  'createAndGo (4)', and 'destroy (6)'."

        VARIATION   tmnxBsxHttpRedirErrRowStatus
            SYNTAX  RowStatus {
                       active               (1),
                    -- notInService         (2)
                    -- notReady             (3)
                       createAndGo          (4),
                    -- createAndWait        (5)
                       destroy              (6)
                    }
            DESCRIPTION
                 "tmnxBsxHttpRedirErrRowStatus supports only 'active (1)',
                  'createAndGo (4)', and 'destroy (6)'."

        VARIATION   tmnxBsxHttpRedirRowStatus
            SYNTAX  RowStatus {
                       active               (1),
                    -- notInService         (2)
                    -- notReady             (3)
                       createAndGo          (4),
                    -- createAndWait        (5)
                       destroy              (6)
                    }
            DESCRIPTION
                 "tmnxBsxHttpRedirRowStatus supports only 'active (1)',
                  'createAndGo (4)', and 'destroy (6)'."

        VARIATION   tmnxBsxIcapServerAddrType
            SYNTAX  InetAddressType {
                       unknown              (0),
                       ipv4                 (1)
                    -- ipv6                 (2)
                    -- ipv4z                (3)
                    -- ipv6z                (4)
                    -- dns                  (16)
                    }
            DESCRIPTION
                 "tmnxBsxIcapServerAddrType supports only the InetAddressType
                  values 'unknown (0)' and 'ipv4 (1)'."

        VARIATION   tmnxBsxIcapServerRowStatus
            SYNTAX  RowStatus {
                       active               (1),
                    -- notInService         (2)
                    -- notReady             (3)
                       createAndGo          (4),
                    -- createAndWait        (5)
                       destroy              (6)
                    }
            DESCRIPTION
                 "tmnxBsxIcapServerRowStatus supports only 'active (1)',
                  'createAndGo (4)', and 'destroy (6)'."

        VARIATION   tmnxBsxIsaAaGrpTransPrefV4NmEntr
            SYNTAX  Unsigned32 (0..4095)
            DESCRIPTION
                 "tmnxBsxIsaAaGrpTransPrefV4NmEntr supports the range from 0 to
                  4095."

        VARIATION   tmnxBsxIsaAaGrpTransPrefV4RmEntr
            SYNTAX  Unsigned32 (0..511)
            DESCRIPTION
                 "tmnxBsxIsaAaGrpTransPrefV4RmEntr supports the range from 0 to
                  511."

        VARIATION   tmnxBsxNotifyActionStatus
            SYNTAX  TmnxBsxActionStatus {
                    -- none                 (0)
                       start                (1),
                       stop                 (2)
                    }
            DESCRIPTION
                 "tmnxBsxNotifyActionStatus only supports TmnxBsxActionStatus
                  values of 'start (1)' and 'stop (2)."

        VARIATION   tmnxBsxPolicerOvrdRowStatus
            SYNTAX  RowStatus {
                       active               (1),
                    -- notInService         (2)
                    -- notReady             (3)
                       createAndGo          (4),
                    -- createAndWait        (5)
                       destroy              (6)
                    }
            DESCRIPTION
                 "tmnxBsxPolicerOvrdRowStatus supports only 'active (1)',
                  'createAndGo (4)', and 'destroy (6)'."

        VARIATION   tmnxBsxPolicerRowStatus
            SYNTAX  RowStatus {
                       active               (1),
                    -- notInService         (2)
                    -- notReady             (3)
                       createAndGo          (4),
                    -- createAndWait        (5)
                       destroy              (6)
                    }
            DESCRIPTION
                 "tmnxBsxPolicerRowStatus supports only 'active (1)',
                  'createAndGo (4)', and 'destroy (6)'."

        VARIATION   tmnxBsxPrefixListRowStatus
            SYNTAX  RowStatus {
                       active               (1),
                    -- notInService         (2)
                    -- notReady             (3)
                       createAndGo          (4),
                    -- createAndWait        (5)
                       destroy              (6)
                    }
            DESCRIPTION
                 "tmnxBsxPrefixListRowStatus supports only 'active (1)',
                  'createAndGo (4)', and 'destroy (6)'."

        VARIATION   tmnxBsxPrefixRowStatus
            SYNTAX  RowStatus {
                       active               (1),
                    -- notInService         (2)
                    -- notReady             (3)
                       createAndGo          (4),
                    -- createAndWait        (5)
                       destroy              (6)
                    }
            DESCRIPTION
                 "tmnxBsxPrefixRowStatus supports only 'active (1)',
                  'createAndGo (4)', and 'destroy (6)'."

        VARIATION   tmnxBsxRadApRowStatus
            SYNTAX  RowStatus {
                       active               (1),
                    -- notInService         (2)
                    -- notReady             (3)
                       createAndGo          (4),
                    -- createAndWait        (5)
                       destroy              (6)
                    }
            DESCRIPTION
                 "tmnxBsxRadApRowStatus supports only 'active (1)', 'createAndGo
                  (4)', and 'destroy (6)'."

        VARIATION   tmnxBsxRadApServAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServAddrType supports only the InetAddressType
                  values 'unknown (0)' and 'ipv4 (1)'."

        VARIATION   tmnxBsxRadApServRowStatus
            SYNTAX  RowStatus {
                       active               (1),
                    -- notInService         (2)
                    -- notReady             (3)
                       createAndGo          (4),
                    -- createAndWait        (5)
                       destroy              (6)
                    }
            DESCRIPTION
                 "tmnxBsxRadApServRowStatus supports only 'active (1)',
                  'createAndGo (4)', and 'destroy (6)'."

        VARIATION   tmnxBsxRadApServerAlgorithm
            SYNTAX  TmnxSubRadServAlgorithm {
                       direct               (1),
                       roundRobin           (2)
                    }
            DESCRIPTION
                 "tmnxBsxRadApServerAlgorithm supports only the values 'direct
                  (1)' and 'roundRobin (2)'."

        VARIATION   tmnxBsxRadApServerSrcAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServerSrcAddrType supports only the
                  InetAddressType values 'unknown (0)' and 'ipv4 (1)'."

        VARIATION   tmnxBsxSctpFltrPpidRowStatus
            SYNTAX  RowStatus {
                       active               (1),
                    -- notInService         (2)
                    -- notReady             (3)
                       createAndGo          (4),
                    -- createAndWait        (5)
                       destroy              (6)
                    }
            DESCRIPTION
                 "tmnxBsxSctpFltrPpidRowStatus supports only 'active (1)',
                  'createAndGo (4)', and 'destroy (6)'."

        VARIATION   tmnxBsxSctpFltrRowStatus
            SYNTAX  RowStatus {
                       active               (1),
                    -- notInService         (2)
                    -- notReady             (3)
                       createAndGo          (4),
                    -- createAndWait        (5)
                       destroy              (6)
                    }
            DESCRIPTION
                 "tmnxBsxSctpFltrRowStatus supports only 'active (1)',
                  'createAndGo (4)', and 'destroy (6)'."

        VARIATION   tmnxBsxSessFltrParamsDstAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsDstAddrType supports only the
                  InetAddressType values 'unknown (0)', 'ipv4 (1)', and 'ipv6
                  (2)'."

        VARIATION   tmnxBsxSessFltrParamsDstPortOp
            SYNTAX  TmnxBsxOperator {
                       none                 (0),
                       eq                   (1),
                    -- neq                  (2)
                       lt                   (3),
                       gt                   (4)
                    -- range                (5)
                    }
            DESCRIPTION
                 "tmnxBsxSessFltrParamsDstPortOp only supports the
                  TmnxBsxOperator values of 'none (0)', 'eq (1)', 'lt (3)' and
                  'gt (4)'."

        VARIATION   tmnxBsxSessFltrParamsRowStatus
            SYNTAX  RowStatus {
                       active               (1),
                    -- notInService         (2)
                    -- notReady             (3)
                       createAndGo          (4),
                    -- createAndWait        (5)
                       destroy              (6)
                    }
            DESCRIPTION
                 "tmnxBsxSessFltrParamsRowStatus supports only 'active (1)',
                  'createAndGo (4)', and 'destroy (6)'."

        VARIATION   tmnxBsxSessFltrParamsSrcAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsSrcAddrType supports only the
                  InetAddressType values 'unknown (0)', 'ipv4 (1)', and 'ipv6
                  (2)'."

        VARIATION   tmnxBsxSessFltrParamsSrcPortOp
            SYNTAX  TmnxBsxOperator {
                       none                 (0),
                       eq                   (1),
                    -- neq                  (2)
                       lt                   (3),
                       gt                   (4)
                    -- range                (5)
                    }
            DESCRIPTION
                 "tmnxBsxSessFltrParamsSrcPortOp only supports the
                  TmnxBsxOperator values of 'none (0)', 'eq (1)', 'lt (3)' and
                  'gt (4)'."

        VARIATION   tmnxBsxSessFltrRowStatus
            SYNTAX  RowStatus {
                       active               (1),
                    -- notInService         (2)
                    -- notReady             (3)
                       createAndGo          (4),
                    -- createAndWait        (5)
                       destroy              (6)
                    }
            DESCRIPTION
                 "tmnxBsxSessFltrRowStatus supports only 'active (1)',
                  'createAndGo (4)', and 'destroy (6)'."

        VARIATION   tmnxBsxStatAaSubCfgEntry
            CREATION-REQUIRES {
                       tmnxBsxStatAaSubCfgRowStatus,
                       tmnxBsxStatAaSubCfgExportMethod
                    }
            DESCRIPTION
                 "Both tmnxBsxStatAaSubCfgRowStatus and
                  tmnxBsxStatAaSubCfgExportMethod must be set for row creation
                  to succeed."

        VARIATION   tmnxBsxStatAaSubCfgRowStatus
            SYNTAX  RowStatus {
                       active               (1),
                    -- notInService         (2)
                    -- notReady             (3)
                       createAndGo          (4),
                    -- createAndWait        (5)
                       destroy              (6)
                    }
            DESCRIPTION
                 "tmnxBsxStatAaSubCfgRowStatus supports only 'active (1)',
                  'createAndGo (4)', and 'destroy (6)'."

        VARIATION   tmnxBsxStatAaSubSdyRowStatus
            SYNTAX  RowStatus {
                       active               (1),
                    -- notInService         (2)
                    -- notReady             (3)
                       createAndGo          (4),
                    -- createAndWait        (5)
                       destroy              (6)
                    }
            DESCRIPTION
                 "tmnxBsxStatAaSubSdyRowStatus supports only 'active (1)',
                  'createAndGo (4)', and 'destroy (6)'."

        VARIATION   tmnxBsxStatTcaCfgRowStatus
            SYNTAX  RowStatus {
                       active               (1),
                    -- notInService         (2)
                    -- notReady             (3)
                       createAndGo          (4),
                    -- createAndWait        (5)
                       destroy              (6)
                    }
            DESCRIPTION
                 "tmnxBsxStatTcaCfgRowStatus supports only 'active (1)',
                  'createAndGo (4)', and 'destroy (6)'."

        VARIATION   tmnxBsxStatTcaFtrCfgRowStatus
            SYNTAX  RowStatus {
                       active               (1),
                    -- notInService         (2)
                    -- notReady             (3)
                       createAndGo          (4),
                    -- createAndWait        (5)
                       destroy              (6)
                    }
            DESCRIPTION
                 "tmnxBsxStatTcaFtrCfgRowStatus supports only 'active (1)',
                  'createAndGo (4)', and 'destroy (6)'."

        VARIATION   tmnxBsxStatTcaFtrEnCfgRowStatus
            SYNTAX  RowStatus {
                       active               (1),
                    -- notInService         (2)
                    -- notReady             (3)
                       createAndGo          (4),
                    -- createAndWait        (5)
                       destroy              (6)
                    }
            DESCRIPTION
                 "tmnxBsxStatTcaFtrEnCfgRowStatus supports only 'active (1)',
                  'createAndGo (4)', and 'destroy (6)'."

        VARIATION   tmnxBsxStatTcaPolcrCfgRowStatus
            SYNTAX  RowStatus {
                       active               (1),
                    -- notInService         (2)
                    -- notReady             (3)
                       createAndGo          (4),
                    -- createAndWait        (5)
                       destroy              (6)
                    }
            DESCRIPTION
                 "tmnxBsxStatTcaPolcrCfgRowStatus supports only 'active (1)',
                  'createAndGo (4)', and 'destroy (6)'."

        VARIATION   tmnxBsxTcpValRowStatus
            SYNTAX  RowStatus {
                       active               (1),
                    -- notInService         (2)
                    -- notReady             (3)
                       createAndGo          (4),
                    -- createAndWait        (5)
                       destroy              (6)
                    }
            DESCRIPTION
                 "tmnxBsxTcpValRowStatus supports only 'active (1)',
                  'createAndGo (4)', and 'destroy (6)'."

        VARIATION   tmnxBsxTcpValTcaRowStatus
            SYNTAX  RowStatus {
                       active               (1),
                    -- notInService         (2)
                    -- notReady             (3)
                       createAndGo          (4),
                    -- createAndWait        (5)
                       destroy              (6)
                    }
            DESCRIPTION
                 "tmnxBsxTcpValTcaRowStatus supports only 'active (1)',
                  'createAndGo (4)', and 'destroy (6)'."

        VARIATION   tmnxBsxTransIpPlcyAddrRowStatus
            SYNTAX  RowStatus {
                       active               (1),
                    -- notInService         (2)
                    -- notReady             (3)
                       createAndGo          (4),
                    -- createAndWait        (5)
                       destroy              (6)
                    }
            DESCRIPTION
                 "tmnxBsxTransIpPlcyAddrRowStatus supports only 'active (1)',
                  'createAndGo (4)', and 'destroy (6)'."

        VARIATION   tmnxBsxTransIpPlcySubRowStatus
            SYNTAX  RowStatus {
                       active               (1),
                    -- notInService         (2)
                    -- notReady             (3)
                       createAndGo          (4),
                    -- createAndWait        (5)
                       destroy              (6)
                    }
            DESCRIPTION
                 "tmnxBsxTransIpPlcySubRowStatus supports only 'active (1)',
                  'createAndGo (4)', and 'destroy (6)'."

        VARIATION   tmnxBsxTransPrefEntryNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntryNetAddrType supports only the
                  InetAddressType values 'unknown (0)' and 'ipv4 (1)'."

        VARIATION   tmnxBsxTransPrefEntryRowStatus
            SYNTAX  RowStatus {
                       active               (1),
                    -- notInService         (2)
                    -- notReady             (3)
                       createAndGo          (4),
                    -- createAndWait        (5)
                       destroy              (6)
                    }
            DESCRIPTION
                 "tmnxBsxTransPrefEntryRowStatus supports only 'active (1)',
                  'createAndGo (4)', and 'destroy (6)'."

        VARIATION   tmnxBsxTransPrefEntrySubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntrySubAddrType supports only the
                  InetAddressType values 'unknown (0)' and 'ipv4 (1)'."

        VARIATION   tmnxBsxTransPrefPolicyRowStatus
            SYNTAX  RowStatus {
                       active               (1),
                    -- notInService         (2)
                    -- notReady             (3)
                       createAndGo          (4),
                    -- createAndWait        (5)
                       destroy              (6)
                    }
            DESCRIPTION
                 "tmnxBsxTransPrefPolicyRowStatus supports only 'active (1)',
                  'createAndGo (4)', and 'destroy (6)'."

        VARIATION   tmnxBsxTransPrefSubRowStatus
            SYNTAX  RowStatus {
                       active               (1),
                    -- notInService         (2)
                    -- notReady             (3)
                       createAndGo          (4),
                    -- createAndWait        (5)
                       destroy              (6)
                    }
            DESCRIPTION
                 "tmnxBsxTransPrefSubRowStatus supports only 'active (1)',
                  'createAndGo (4)', and 'destroy (6)'."

        VARIATION   tmnxBsxTransPrefSumNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumNetAddrType supports only the
                  InetAddressType values 'unknown (0)' and 'ipv4 (1)'."

        VARIATION   tmnxBsxTransPrefSumSubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumSubAddrType supports only the
                  InetAddressType values 'unknown (0)' and 'ipv4 (1)'."

        VARIATION   tmnxBsxTransitIpPolicyAddrType
            SYNTAX  InetAddressType {
                    -- unknown              (0)
                       ipv4                 (1),
                       ipv6                 (2)
                    -- ipv4z                (3)
                    -- ipv6z                (4)
                    -- dns                  (16)
                    }
            DESCRIPTION
                 "tmnxBsxTransitIpPolicyAddrType supports only the
                  InetAddressType values 'ipv4 (1)', and 'ipv6 (2)'."

        VARIATION   tmnxBsxTransitIpPolicyIPv6PfxLen
            SYNTAX  InetAddressPrefixLength (32..64)
            DESCRIPTION
                 "tmnxBsxTransitIpPolicyIPv6PfxLen supports only the range from
                  32 to 64."

        VARIATION   tmnxBsxTransitIpPolicyRowStatus
            SYNTAX  RowStatus {
                       active               (1),
                    -- notInService         (2)
                    -- notReady             (3)
                       createAndGo          (4),
                    -- createAndWait        (5)
                       destroy              (6)
                    }
            DESCRIPTION
                 "tmnxBsxTransitIpPolicyRowStatus supports only 'active (1)',
                  'createAndGo (4)', and 'destroy (6)'."

        VARIATION   tmnxBsxTransitIpSumParentSubType
            SYNTAX  TmnxBsxAaSubscriberType {
                       unknown              (0),
                    -- esm                  (1)
                       sap                  (2),
                       spokeSdp             (3)
                    -- transit              (4)
                    }
            DESCRIPTION
                 "tmnxBsxTransitIpSumParentSubType supports only the values
                  'unknown(0)', 'sap(2)', and 'spokeSdp(3)'."

        VARIATION   tmnxBsxUrlFilterRowStatus
            SYNTAX  RowStatus {
                       active               (1),
                    -- notInService         (2)
                    -- notReady             (3)
                       createAndGo          (4),
                    -- createAndWait        (5)
                       destroy              (6)
                    }
            DESCRIPTION
                 "tmnxBsxUrlFilterRowStatus supports only 'active (1)',
                  'createAndGo (4)', and 'destroy (6)'."

        VARIATION   tmnxBsxUrlFltrUrlListRowStatus
            SYNTAX  RowStatus {
                       active               (1),
                    -- notInService         (2)
                    -- notReady             (3)
                       createAndGo          (4),
                    -- createAndWait        (5)
                       destroy              (6)
                    }
            DESCRIPTION
                 "tmnxBsxUrlFltrUrlListRowStatus supports only 'active (1)',
                  'createAndGo (4)', and 'destroy (6)'."

        VARIATION   tmnxBsxUrlListRowStatus
            SYNTAX  RowStatus {
                       active               (1),
                    -- notInService         (2)
                    -- notReady             (3)
                       createAndGo          (4),
                    -- createAndWait        (5)
                       destroy              (6)
                    }
            DESCRIPTION
                 "tmnxBsxUrlListRowStatus supports only 'active (1)',
                  'createAndGo (4)', and 'destroy (6)'."

    ::= { tmnx7750c4AgentV14v0  66 }

--
-- 7450 BSX CAPABILITIES
--
tmnx7450BsxV14v0                  AGENT-CAPABILITIES
    PRODUCT-RELEASE "Nokia SROS"
    STATUS          current
    DESCRIPTION
         "Implementation of BSX capabilities for Nokia 7450 systems release
          14.0."

    SUPPORTS        TIMETRA-BSX-NG-MIB
        INCLUDES {
           tmnxBsxCflowdDirectExportGroup,
           tmnxBsxCflowdGroup,
           tmnxBsxCflowdGroupV10v0,
           tmnxBsxCflowdGroupV9v0,
           tmnxBsxDnsIpCacheGroupV13v0,
           tmnxBsxEventLogSyslogObjGrp,
           tmnxBsxGtpGroupV13v0,
           tmnxBsxGtpUntunnelingObjGrp,
           tmnxBsxHttpEnAntiSpfStObGrpV11v0,
           tmnxBsxHttpEnrAntiSpfObjGrpV11v0,
           tmnxBsxHttpEnrEncObjGrpV11v0,
           tmnxBsxHttpEnrStStrObjGrpV12v0,
           tmnxBsxHttpEnrichObjGroup,
           tmnxBsxHttpEnrichStatObjGroup,
           tmnxBsxHttpNotifObjGrp,
           tmnxBsxHttpNotifObjGrpV13v0,
           tmnxBsxHttpRedirErrGroup,
           tmnxBsxHttpRedirGroup,
           tmnxBsxHttpRedirObjGrpV12v0,
           tmnxBsxHttpRedirObjGrpV13v0,
           tmnxBsxHttpsCaptiveRedirObjGrp,
           tmnxBsxIpPrefixListObjGrpV12v0,
           tmnxBsxIsa2ObjGroup,
           tmnxBsxLwObjGrpV12v0,
           tmnxBsxMdaGroupV10v0,
           tmnxBsxMdaGroupV11v0,
           tmnxBsxMdaGroupV12v0,
           tmnxBsxMdaGroupV7v0,
           tmnxBsxMdaGroupV8v0,
           tmnxBsxMgBillingExclusionsGroup,
           tmnxBsxMgTetherDetectGroup,
           tmnxBsxMobileGatewayGroup,
           tmnxBsxNotificationGroup,
           tmnxBsxNotificationGroupV10v0,
           tmnxBsxNotificationGroupV11v0,
           tmnxBsxNotificationGroupV12v0,
           tmnxBsxNotificationGroupV13v0,
           tmnxBsxNotificationGroupV14v0,
           tmnxBsxNotificationGroupV7v0,
           tmnxBsxNotificationGroupV8v0,
           tmnxBsxNotificationGroupV9v0,
           tmnxBsxNotifyObjsGroup,
           tmnxBsxNotifyObjsGroupV13v0,
           tmnxBsxNotifyObjsGroupV14v0,
           tmnxBsxNotifyObjsGroupV7v0,
           tmnxBsxNotifyObjsGroupV8v0,
           tmnxBsxOvrdGroup,
           tmnxBsxPolicyObjGrp12v0,
           tmnxBsxPolicyObjGrp13v0,
           tmnxBsxPolicyTimeStampExtObjGrp,
           tmnxBsxPolicyTodObjGrp,
           tmnxBsxRadApNotificationGroup,
           tmnxBsxRadApObjGroup,
           tmnxBsxRadApStatObjGroup,
           tmnxBsxRadiusAccountingObjGroup,
           tmnxBsxRadiusAcctObjGroupV11v0,
           tmnxBsxRedundancyEnhObjGroup,
           tmnxBsxRedundancyObjGroup,
           tmnxBsxSessionFilterObjGrp,
           tmnxBsxStaticObjGroup,
           tmnxBsxStatsGroup,
           tmnxBsxStatsGroupV9v0,
           tmnxBsxStflFwEnhacementsObjGrp,
           tmnxBsxTcpMssObjGrp,
           tmnxBsxTcpValObjGrp,
           tmnxBsxTrafficStatsObjGrpV12v0,
           tmnxBsxTrafficStatsObjGrpV13v0,
           tmnxBsxTransitGroup,
           tmnxBsxTransitGroupV10v0,
           tmnxBsxTransitIpPolicyDiamObjGrp,
           tmnxBsxTransitSeenIpGroup,
           tmnxBsxTrapPerfObjGrp,
           tmnxBsxUrlFilterObjGrp,
           tmnxBsxUrlFilterObjGrpV12v0,
           tmnxBsxUrlFilterStatsObjGrp,
           tmnxBsxUrlListExtendedGroup,
           tmnxBsxUrlListGroupV13v0,
           tmnxBsxUsageMonObjGrpV12v0,
           tmnxBsxXHeaderObjGroup
        }

        VARIATION   tmnxBsxAaGrpPartRowStatus
            SYNTAX  RowStatus {
                       active               (1),
                    -- notInService         (2)
                    -- notReady             (3)
                       createAndGo          (4),
                    -- createAndWait        (5)
                       destroy              (6)
                    }
            DESCRIPTION
                 "tmnxBsxAaGrpPartRowStatus supports only 'active (1)',
                  'createAndGo (4)', and 'destroy (6)'."

        VARIATION   tmnxBsxAaIfAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfAddrType supports only the InetAddressType values
                  'unknown (0)' and 'ipv4 (1)'."

        VARIATION   tmnxBsxAaIfIsaAddrType
            SYNTAX  InetAddressType {
                       unknown              (0),
                       ipv4                 (1)
                    -- ipv6                 (2)
                    -- ipv4z                (3)
                    -- ipv6z                (4)
                    -- dns                  (16)
                    }
            DESCRIPTION
                 "tmnxBsxAaIfIsaAddrType supports only the InetAddressType
                  values 'unknown (0)' and 'ipv4 (1)'."

        VARIATION   tmnxBsxAarpInstPeerEPSapEncType
            SYNTAX  INTEGER {
                       unknown              (0),
                       nullEncap            (1),
                    -- qEncap               (2)
                    -- mplsEncap            (3)
                    -- bcpNullEncap         (4)
                       bcpDot1qEncap        (5),
                    -- ipcpEncap            (6)
                    -- frEncap              (7)
                    -- pppAutoEncap         (8)
                    -- atmEncap             (9)
                       qinqEncap            (10)
                    -- wanMirrorEncap       (11)
                    -- ciscoHDLCEncap       (12)
                    -- cemEncap             (13)
                    }
            DESCRIPTION
                 "tmnxBsxAarpInstPeerEPSapEncType supports only
                  TmnxPortEncapType 'unknown(0)', 'nullEncap(1)',
                  'bcpDot1qEncap(5)', and 'qinqEncap(10)'."

        VARIATION   tmnxBsxAarpInstPeerIpType
            SYNTAX  InetAddressType {
                       unknown              (0),
                       ipv4                 (1)
                    -- ipv6                 (2)
                    -- ipv4z                (3)
                    -- ipv6z                (4)
                    -- dns                  (16)
                    }
            DESCRIPTION
                 "tmnxBsxAarpInstPeerIpType supports only the InetAddressType
                  values 'unknown (0)' and 'ipv4 (1)'."

        VARIATION   tmnxBsxAarpInstRowStatus
            SYNTAX  RowStatus {
                       active               (1),
                    -- notInService         (2)
                    -- notReady             (3)
                       createAndGo          (4),
                    -- createAndWait        (5)
                       destroy              (6)
                    }
            DESCRIPTION
                 "tmnxBsxAarpInstRowStatus supports only 'active (1)',
                  'createAndGo (4)', and 'destroy (6)'."

        VARIATION   tmnxBsxAppFilterExprIndex
            SYNTAX  Integer32 (1..4)
            DESCRIPTION
                 "tmnxBsxAppFilterExprIndex supports a range from 1 to 4
                  expressions."

        VARIATION   tmnxBsxAppFilterExprOperator
            SYNTAX  TmnxBsxOperator {
                       none                 (0),
                       eq                   (1),
                       neq                  (2)
                    -- lt                   (3)
                    -- gt                   (4)
                    -- range                (5)
                    }
            DESCRIPTION
                 "tmnxBsxAppFilterExprOperator only supports TmnxBsxOperator
                  values of 'none (0)', 'eq (1)' and 'neq (2)."

        VARIATION   tmnxBsxAppFilterNetworkAddrOp
            SYNTAX  TmnxBsxOperator {
                       none                 (0),
                       eq                   (1),
                       neq                  (2)
                    -- lt                   (3)
                    -- gt                   (4)
                    -- range                (5)
                    }
            DESCRIPTION
                 "tmnxBsxAppFilterNetworkAddrOp only supports TmnxBsxOperator
                  values of 'none (0)', 'eq (1)' and 'neq (2)."

        VARIATION   tmnxBsxAppFilterNetworkAddrType
            SYNTAX  InetAddressType {
                       unknown              (0),
                       ipv4                 (1),
                       ipv6                 (2)
                    -- ipv4z                (3)
                    -- ipv6z                (4)
                    -- dns                  (16)
                    }
            DESCRIPTION
                 "tmnxBsxAppFilterNetworkAddrType supports only the
                  InetAddressType values 'unknown (0)', 'ipv4 (1)', and 'ipv6
                  (2)'."

        VARIATION   tmnxBsxAppFilterServerAddrOp
            SYNTAX  TmnxBsxOperator {
                       none                 (0),
                       eq                   (1),
                       neq                  (2)
                    -- lt                   (3)
                    -- gt                   (4)
                    -- range                (5)
                    }
            DESCRIPTION
                 "tmnxBsxAppFilterServerAddrOp only supports TmnxBsxOperator
                  values of 'none (0)', 'eq (1)' and 'neq (2)."

        VARIATION   tmnxBsxAppFilterServerAddrType
            SYNTAX  InetAddressType {
                       unknown              (0),
                       ipv4                 (1),
                       ipv6                 (2)
                    -- ipv4z                (3)
                    -- ipv6z                (4)
                    -- dns                  (16)
                    }
            DESCRIPTION
                 "tmnxBsxAppFilterServerAddrType supports only the
                  InetAddressType values 'unknown (0)', 'ipv4 (1)', and 'ipv6
                  (2)'."

        VARIATION   tmnxBsxAppFilterServerPortOp
            SYNTAX  TmnxBsxOperator {
                       none                 (0),
                       eq                   (1),
                       neq                  (2),
                       lt                   (3),
                       gt                   (4)
                    -- range                (5)
                    }
            DESCRIPTION
                 "tmnxBsxAppFilterServerPortOp only supports TmnxBsxOperator
                  values of 'none (0)', 'eq (1)', 'neq (2)', 'lt (3)' and 'gt
                  (4)."

        VARIATION   tmnxBsxAppGrpRowStatus
            SYNTAX  RowStatus {
                       active               (1),
                    -- notInService         (2)
                    -- notReady             (3)
                       createAndGo          (4),
                    -- createAndWait        (5)
                       destroy              (6)
                    }
            DESCRIPTION
                 "tmnxBsxAppGrpRowStatus supports only 'active (1)',
                  'createAndGo (4)', and 'destroy (6)'."

        VARIATION   tmnxBsxAppGrpStorageType
            SYNTAX  StorageType {
                    -- other(1)
                    -- volatile(2)
                       nonVolatile(3),
                       permanent(4)
                    -- readOnly(5)
                    }
            DESCRIPTION
                 "tmnxBsxAppGrpStorageType supports only the values 'nonVolatile
                  (3)' and 'permanent (4)'."

        VARIATION   tmnxBsxAppProfRowStatus
            SYNTAX  RowStatus {
                       active               (1),
                    -- notInService         (2)
                    -- notReady             (3)
                       createAndGo          (4),
                    -- createAndWait        (5)
                       destroy              (6)
                    }
            DESCRIPTION
                 "tmnxBsxAppProfRowStatus supports only 'active (1)',
                  'createAndGo (4)', and 'destroy (6)'."

        VARIATION   tmnxBsxAppRowStatus
            SYNTAX  RowStatus {
                       active               (1),
                    -- notInService         (2)
                    -- notReady             (3)
                       createAndGo          (4),
                    -- createAndWait        (5)
                       destroy              (6)
                    }
            DESCRIPTION
                 "tmnxBsxAppRowStatus supports only 'active (1)', 'createAndGo
                  (4)', and 'destroy (6)'."

        VARIATION   tmnxBsxAppStorageType
            SYNTAX  StorageType {
                    -- other(1)
                    -- volatile(2)
                       nonVolatile(3),
                       permanent(4)
                    -- readOnly(5)
                    }
            DESCRIPTION
                 "tmnxBsxAppStorageType supports only the values 'nonVolatile
                  (3)' and 'permanent (4)'."

        VARIATION   tmnxBsxAqpBaseRowStatus
            SYNTAX  RowStatus {
                       active               (1),
                    -- notInService         (2)
                    -- notReady             (3)
                       createAndGo          (4),
                    -- createAndWait        (5)
                       destroy              (6)
                    }
            DESCRIPTION
                 "tmnxBsxAqpBaseRowStatus supports only 'active (1)',
                  'createAndGo (4)', and 'destroy (6)'."

        VARIATION   tmnxBsxAqpCharOperator
            SYNTAX  TmnxBsxOperator {
                    -- none                 (0)
                       eq                   (1)
                    -- neq                  (2)
                    -- lt                   (3)
                    -- gt                   (4)
                    -- range                (5)
                    }
            DESCRIPTION
                 "tmnxBsxAqpCharOperator only supports the TmnxBsxOperator value
                  of 'eq (1)'."

        VARIATION   tmnxBsxAqpCharRowStatus
            SYNTAX  RowStatus {
                       active               (1),
                    -- notInService         (2)
                    -- notReady             (3)
                       createAndGo          (4),
                    -- createAndWait        (5)
                       destroy              (6)
                    }
            DESCRIPTION
                 "tmnxBsxAqpCharRowStatus supports only 'active (1)',
                  'createAndGo (4)', and 'destroy (6)'."

        VARIATION   tmnxBsxAqpChargeGrpOp
            SYNTAX  TmnxBsxOperator {
                       none                 (0),
                       eq                   (1),
                       neq                  (2)
                    -- lt                   (3)
                    -- gt                   (4)
                    -- range                (5)
                    }
            DESCRIPTION
                 "tmnxBsxAqpChargeGrpOp only supports TmnxBsxOperator values of
                  'none (0)', 'eq (1)' and 'neq (2)."

        VARIATION   tmnxBsxAqpDstAddress
            SYNTAX  InetAddress (SIZE (0|4))
            DESCRIPTION
                 "tmnxBsxAqpDstAddress only supports InetAddressType 'unknown
                  (0)' and 'ipv4 (1)'."

        VARIATION   tmnxBsxAqpDstAddressOp
            SYNTAX  TmnxBsxOperator {
                       none                 (0),
                       eq                   (1),
                       neq                  (2)
                    -- lt                   (3)
                    -- gt                   (4)
                    -- range                (5)
                    }
            DESCRIPTION
                 "tmnxBsxAqpDstAddressOp only supports TmnxBsxOperator values of
                  'none (0)', 'eq (1)' and 'neq (2)."

        VARIATION   tmnxBsxAqpDstAddressType
            SYNTAX  InetAddressType {
                       unknown              (0),
                       ipv4                 (1)
                    -- ipv6                 (2)
                    -- ipv4z                (3)
                    -- ipv6z                (4)
                    -- dns                  (16)
                    }
            DESCRIPTION
                 "tmnxBsxAqpDstAddressType supports only the InetAddressType
                  values 'unknown (0)' and 'ipv4 (1)'."

        VARIATION   tmnxBsxAqpDstPortOp
            SYNTAX  TmnxBsxOperator {
                       none                 (0),
                       eq                   (1),
                       neq                  (2)
                    -- lt                   (3)
                    -- gt                   (4)
                    -- range                (5)
                    }
            DESCRIPTION
                 "tmnxBsxAqpDstPortOp only supports TmnxBsxOperator values of
                  'none (0)', 'eq (1)' and 'neq (2)."

        VARIATION   tmnxBsxAqpIpProtocolNumOp
            SYNTAX  TmnxBsxOperator {
                       none                 (0),
                       eq                   (1),
                       neq                  (2)
                    -- lt                   (3)
                    -- gt                   (4)
                    -- range                (5)
                    }
            DESCRIPTION
                 "tmnxBsxAqpIpProtocolNumOp only supports TmnxBsxOperator values
                  of 'none (0)', 'eq (1)' and 'neq (2)."

        VARIATION   tmnxBsxAqpOutOfOrderFrags
            ACCESS  not-implemented
            DESCRIPTION
                 "tmnxBsxAqpOutOfOrderFrags is not implemented on Nokia 7450 in
                  release 14.0."

        VARIATION   tmnxBsxAqpSapSubscrOp
            SYNTAX  TmnxBsxOperator {
                       none                 (0),
                       eq                   (1),
                       neq                  (2)
                    -- lt                   (3)
                    -- gt                   (4)
                    -- range                (5)
                    }
            DESCRIPTION
                 "tmnxBsxAqpSapSubscrOp only supports TmnxBsxOperator values of
                  'none (0)', 'eq (1)' and 'neq (2)."

        VARIATION   tmnxBsxAqpSrcAddress
            SYNTAX  InetAddress (SIZE (0|4))
            DESCRIPTION
                 "tmnxBsxAqpSrcAddress only supports InetAddressType 'unknown
                  (0)' and 'ipv4 (1)'."

        VARIATION   tmnxBsxAqpSrcAddressOp
            SYNTAX  TmnxBsxOperator {
                       none                 (0),
                       eq                   (1),
                       neq                  (2)
                    -- lt                   (3)
                    -- gt                   (4)
                    -- range                (5)
                    }
            DESCRIPTION
                 "tmnxBsxAqpSrcAddressOp only supports TmnxBsxOperator values of
                  'none (0)', 'eq (1)' and 'neq (2)."

        VARIATION   tmnxBsxAqpSrcAddressType
            SYNTAX  InetAddressType {
                       unknown              (0),
                       ipv4                 (1)
                    -- ipv6                 (2)
                    -- ipv4z                (3)
                    -- ipv6z                (4)
                    -- dns                  (16)
                    }
            DESCRIPTION
                 "tmnxBsxAqpSrcAddressType supports only the InetAddressType
                  values 'unknown (0)' and 'ipv4 (1)'."

        VARIATION   tmnxBsxAqpSrcPortOp
            SYNTAX  TmnxBsxOperator {
                       none                 (0),
                       eq                   (1),
                       neq                  (2)
                    -- lt                   (3)
                    -- gt                   (4)
                    -- range                (5)
                    }
            DESCRIPTION
                 "tmnxBsxAqpSrcPortOp only supports TmnxBsxOperator values of
                  'none (0)', 'eq (1)' and 'neq (2)."

        VARIATION   tmnxBsxAsoPersistId
            ACCESS  not-implemented
            DESCRIPTION
                 "tmnxBsxAsoPersistId is not implemented on Nokia 7450 in
                  release 14.0."

        VARIATION   tmnxBsxAsoRowStatus
            SYNTAX  RowStatus {
                       active               (1),
                    -- notInService         (2)
                    -- notReady             (3)
                       createAndGo          (4),
                    -- createAndWait        (5)
                       destroy              (6)
                    }
            DESCRIPTION
                 "tmnxBsxAsoRowStatus supports only 'active (1)', 'createAndGo
                  (4)', and 'destroy (6)'."

        VARIATION   tmnxBsxAsoValPersistId
            ACCESS  not-implemented
            DESCRIPTION
                 "tmnxBsxAsoValPersistId is not implemented on Nokia 7450 in
                  release 14.0."

        VARIATION   tmnxBsxAsoValRowStatus
            SYNTAX  RowStatus {
                       active               (1),
                    -- notInService         (2)
                    -- notReady             (3)
                       createAndGo          (4),
                    -- createAndWait        (5)
                       destroy              (6)
                    }
            DESCRIPTION
                 "tmnxBsxAsoValRowStatus supports only 'active (1)',
                  'createAndGo (4)', and 'destroy (6)'."

        VARIATION   tmnxBsxCflowdCollAddress
            SYNTAX  InetAddress (SIZE (0|4))
            DESCRIPTION
                 "tmnxBsxCflowdCollAddress only supports InetAddressType
                  'unknown (0)' and 'ipv4 (1)'."

        VARIATION   tmnxBsxCflowdCollAddressType
            SYNTAX  InetAddressType {
                       unknown              (0),
                       ipv4                 (1)
                    -- ipv6                 (2)
                    -- ipv4z                (3)
                    -- ipv6z                (4)
                    -- dns                  (16)
                    }
            DESCRIPTION
                 "tmnxBsxCflowdCollAddressType supports only the InetAddressType
                  values 'unknown (0)' and 'ipv4 (1)'."

        VARIATION   tmnxBsxCflowdCollRowStatus
            SYNTAX  RowStatus {
                       active               (1),
                    -- notInService         (2)
                    -- notReady             (3)
                       createAndGo          (4),
                    -- createAndWait        (5)
                       destroy              (6)
                    }
            DESCRIPTION
                 "tmnxBsxCflowdCollRowStatus supports only 'active (1)',
                  'createAndGo (4)', and 'destroy (6)'."

        VARIATION   tmnxBsxCflowdDirExpAddrRowStatus
            SYNTAX  RowStatus {
                       active               (1),
                    -- notInService         (2)
                    -- notReady             (3)
                       createAndGo          (4),
                    -- createAndWait        (5)
                       destroy              (6)
                    }
            DESCRIPTION
                 "tmnxBsxCflowdDirExpAddrRowStatus supports only 'active (1)',
                  'createAndGo (4)', and 'destroy (6)'."

        VARIATION   tmnxBsxCflowdDirectExpRowStatus
            SYNTAX  RowStatus {
                       active               (1),
                    -- notInService         (2)
                    -- notReady             (3)
                       createAndGo          (4),
                    -- createAndWait        (5)
                       destroy              (6)
                    }
            DESCRIPTION
                 "tmnxBsxCflowdDirectExpRowStatus supports only 'active (1)',
                  'createAndGo (4)', and 'destroy (6)'."

        VARIATION   tmnxBsxCflowdPerfExpRowStatus
            SYNTAX  RowStatus {
                       active               (1),
                    -- notInService         (2)
                    -- notReady             (3)
                       createAndGo          (4),
                    -- createAndWait        (5)
                       destroy              (6)
                    }
            DESCRIPTION
                 "tmnxBsxCflowdPerfExpRowStatus supports only 'active (1)',
                  'createAndGo (4)', and 'destroy (6)'."

        VARIATION   tmnxBsxChargeGrpRowStatus
            SYNTAX  RowStatus {
                       active               (1),
                    -- notInService         (2)
                    -- notReady             (3)
                       createAndGo          (4),
                    -- createAndWait        (5)
                       destroy              (6)
                    }
            DESCRIPTION
                 "tmnxBsxChargeGrpRowStatus supports only 'active (1)',
                  'createAndGo (4)', and 'destroy (6)'."

        VARIATION   tmnxBsxCustProtEntryId
            SYNTAX  TEntryId (1..10)
            DESCRIPTION
                 "tmnxBsxCustProtEntryId supports a range from 1 to 10 custom
                  protocol entries."

        VARIATION   tmnxBsxCustProtExprIndex
            SYNTAX  Integer32 (1)
            DESCRIPTION
                 "tmnxBsxCustProtExprIndex only supports 1 custom protocol
                  expression."

        VARIATION   tmnxBsxCustProtExprOperator
            SYNTAX  TmnxBsxOperator {
                    -- none                 (0)
                       eq                   (1)
                    -- neq                  (2)
                    -- lt                   (3)
                    -- gt                   (4)
                    -- range                (5)
                    }
            DESCRIPTION
                 "tmnxBsxCustProtExprOperator only supports the TmnxBsxOperator
                  value of 'eq (1)'."

        VARIATION   tmnxBsxCustProtExprRowStatus
            SYNTAX  RowStatus {
                       active               (1),
                    -- notInService         (2)
                    -- notReady             (3)
                       createAndGo          (4),
                    -- createAndWait        (5)
                       destroy              (6)
                    }
            DESCRIPTION
                 "tmnxBsxCustProtExprRowStatus supports only 'active (1)',
                  'createAndGo (4)', and 'destroy (6)'."

        VARIATION   tmnxBsxCustProtIpProtocolNum
            DESCRIPTION
                 "tmnxBsxCustProtIpProtocolNum supports only the values not set
                  (-1), tcp (6) and udp (17)."

        VARIATION   tmnxBsxCustProtRowStatus
            SYNTAX  RowStatus {
                       active               (1),
                    -- notInService         (2)
                    -- notReady             (3)
                       createAndGo          (4),
                    -- createAndWait        (5)
                       destroy              (6)
                    }
            DESCRIPTION
                 "tmnxBsxCustProtRowStatus supports only 'active (1)',
                  'createAndGo (4)', and 'destroy (6)'."

        VARIATION   tmnxBsxDnsIpCacheDomainRowStatus
            SYNTAX  RowStatus {
                       active               (1),
                    -- notInService         (2)
                    -- notReady             (3)
                       createAndGo          (4),
                    -- createAndWait        (5)
                       destroy              (6)
                    }
            DESCRIPTION
                 "tmnxBsxDnsIpCacheDomainRowStatus supports only 'active (1)',
                  'createAndGo (4)', and 'destroy (6)'."

        VARIATION   tmnxBsxDnsIpCacheRowStatus
            SYNTAX  RowStatus {
                       active               (1),
                    -- notInService         (2)
                    -- notReady             (3)
                       createAndGo          (4),
                    -- createAndWait        (5)
                       destroy              (6)
                    }
            DESCRIPTION
                 "tmnxBsxDnsIpCacheRowStatus supports only 'active (1)',
                  'createAndGo (4)', and 'destroy (6)'."

        VARIATION   tmnxBsxDnsIpCacheServerAddrType
            SYNTAX  InetAddressType {
                    -- unknown              (0)
                       ipv4                 (1),
                       ipv6                 (2)
                    -- ipv4z                (3)
                    -- ipv6z                (4)
                    -- dns                  (16)
                    }
            DESCRIPTION
                 "tmnxBsxDnsIpCacheServerAddrType supports only the
                  InetAddressType values 'ipv4 (1)', and 'ipv6 (2)'."

        VARIATION   tmnxBsxDnsIpCacheServerRowStatus
            SYNTAX  RowStatus {
                       active               (1),
                    -- notInService         (2)
                    -- notReady             (3)
                       createAndGo          (4),
                    -- createAndWait        (5)
                       destroy              (6)
                    }
            DESCRIPTION
                 "tmnxBsxDnsIpCacheServerRowStatus supports only 'active (1)',
                  'createAndGo (4)', and 'destroy (6)'."

        VARIATION   tmnxBsxEventLogRowStatus
            SYNTAX  RowStatus {
                       active               (1),
                    -- notInService         (2)
                    -- notReady             (3)
                       createAndGo          (4),
                    -- createAndWait        (5)
                       destroy              (6)
                    }
            DESCRIPTION
                 "tmnxBsxEventLogRowStatus supports only 'active (1)',
                  'createAndGo (4)', and 'destroy (6)'."

        VARIATION   tmnxBsxGtpFltrMsgRowStatus
            SYNTAX  RowStatus {
                       active               (1),
                    -- notInService         (2)
                    -- notReady             (3)
                       createAndGo          (4),
                    -- createAndWait        (5)
                       destroy              (6)
                    }
            DESCRIPTION
                 "tmnxBsxGtpFltrMsgRowStatus supports only 'active (1)',
                  'createAndGo (4)', and 'destroy (6)'."

        VARIATION   tmnxBsxGtpFltrRowStatus
            SYNTAX  RowStatus {
                       active               (1),
                    -- notInService         (2)
                    -- notReady             (3)
                       createAndGo          (4),
                    -- createAndWait        (5)
                       destroy              (6)
                    }
            DESCRIPTION
                 "tmnxBsxGtpFltrRowStatus supports only 'active (1)',
                  'createAndGo (4)', and 'destroy (6)'."

        VARIATION   tmnxBsxHttpEnrichFieldRowStatus
            SYNTAX  RowStatus {
                       active               (1),
                    -- notInService         (2)
                    -- notReady             (3)
                       createAndGo          (4),
                    -- createAndWait        (5)
                       destroy              (6)
                    }
            DESCRIPTION
                 "tmnxBsxHttpEnrichFieldRowStatus supports only 'active (1)',
                  'createAndGo (4)', and 'destroy (6)'."

        VARIATION   tmnxBsxHttpEnrichRowStatus
            SYNTAX  RowStatus {
                       active               (1),
                    -- notInService         (2)
                    -- notReady             (3)
                       createAndGo          (4),
                    -- createAndWait        (5)
                       destroy              (6)
                    }
            DESCRIPTION
                 "tmnxBsxHttpEnrichRowStatus supports only 'active (1)',
                  'createAndGo (4)', and 'destroy (6)'."

        VARIATION   tmnxBsxHttpNotifRowStatus
            SYNTAX  RowStatus {
                       active               (1),
                    -- notInService         (2)
                    -- notReady             (3)
                       createAndGo          (4),
                    -- createAndWait        (5)
                       destroy              (6)
                    }
            DESCRIPTION
                 "tmnxBsxHttpNotifRowStatus supports only 'active (1)',
                  'createAndGo (4)', and 'destroy (6)'."

        VARIATION   tmnxBsxHttpRedirErrCodeRowStatus
            SYNTAX  RowStatus {
                       active               (1),
                    -- notInService         (2)
                    -- notReady             (3)
                       createAndGo          (4),
                    -- createAndWait        (5)
                       destroy              (6)
                    }
            DESCRIPTION
                 "tmnxBsxHttpRedirErrCodeRowStatus supports only 'active (1)',
                  'createAndGo (4)', and 'destroy (6)'."

        VARIATION   tmnxBsxHttpRedirErrRowStatus
            SYNTAX  RowStatus {
                       active               (1),
                    -- notInService         (2)
                    -- notReady             (3)
                       createAndGo          (4),
                    -- createAndWait        (5)
                       destroy              (6)
                    }
            DESCRIPTION
                 "tmnxBsxHttpRedirErrRowStatus supports only 'active (1)',
                  'createAndGo (4)', and 'destroy (6)'."

        VARIATION   tmnxBsxHttpRedirRowStatus
            SYNTAX  RowStatus {
                       active               (1),
                    -- notInService         (2)
                    -- notReady             (3)
                       createAndGo          (4),
                    -- createAndWait        (5)
                       destroy              (6)
                    }
            DESCRIPTION
                 "tmnxBsxHttpRedirRowStatus supports only 'active (1)',
                  'createAndGo (4)', and 'destroy (6)'."

        VARIATION   tmnxBsxIcapServerAddrType
            SYNTAX  InetAddressType {
                       unknown              (0),
                       ipv4                 (1)
                    -- ipv6                 (2)
                    -- ipv4z                (3)
                    -- ipv6z                (4)
                    -- dns                  (16)
                    }
            DESCRIPTION
                 "tmnxBsxIcapServerAddrType supports only the InetAddressType
                  values 'unknown (0)' and 'ipv4 (1)'."

        VARIATION   tmnxBsxIcapServerRowStatus
            SYNTAX  RowStatus {
                       active               (1),
                    -- notInService         (2)
                    -- notReady             (3)
                       createAndGo          (4),
                    -- createAndWait        (5)
                       destroy              (6)
                    }
            DESCRIPTION
                 "tmnxBsxIcapServerRowStatus supports only 'active (1)',
                  'createAndGo (4)', and 'destroy (6)'."

        VARIATION   tmnxBsxIsaAaGrpTransPrefV4NmEntr
            SYNTAX  Unsigned32 (0..16383)
            DESCRIPTION
                 "tmnxBsxIsaAaGrpTransPrefV4NmEntr supports the range from 0 to
                  16383."

        VARIATION   tmnxBsxNotifyActionStatus
            SYNTAX  TmnxBsxActionStatus {
                    -- none                 (0)
                       start                (1),
                       stop                 (2)
                    }
            DESCRIPTION
                 "tmnxBsxNotifyActionStatus only supports TmnxBsxActionStatus
                  values of 'start (1)' and 'stop (2)."

        VARIATION   tmnxBsxPolicerOvrdRowStatus
            SYNTAX  RowStatus {
                       active               (1),
                    -- notInService         (2)
                    -- notReady             (3)
                       createAndGo          (4),
                    -- createAndWait        (5)
                       destroy              (6)
                    }
            DESCRIPTION
                 "tmnxBsxPolicerOvrdRowStatus supports only 'active (1)',
                  'createAndGo (4)', and 'destroy (6)'."

        VARIATION   tmnxBsxPolicerRowStatus
            SYNTAX  RowStatus {
                       active               (1),
                    -- notInService         (2)
                    -- notReady             (3)
                       createAndGo          (4),
                    -- createAndWait        (5)
                       destroy              (6)
                    }
            DESCRIPTION
                 "tmnxBsxPolicerRowStatus supports only 'active (1)',
                  'createAndGo (4)', and 'destroy (6)'."

        VARIATION   tmnxBsxPrefixListRowStatus
            SYNTAX  RowStatus {
                       active               (1),
                    -- notInService         (2)
                    -- notReady             (3)
                       createAndGo          (4),
                    -- createAndWait        (5)
                       destroy              (6)
                    }
            DESCRIPTION
                 "tmnxBsxPrefixListRowStatus supports only 'active (1)',
                  'createAndGo (4)', and 'destroy (6)'."

        VARIATION   tmnxBsxPrefixRowStatus
            SYNTAX  RowStatus {
                       active               (1),
                    -- notInService         (2)
                    -- notReady             (3)
                       createAndGo          (4),
                    -- createAndWait        (5)
                       destroy              (6)
                    }
            DESCRIPTION
                 "tmnxBsxPrefixRowStatus supports only 'active (1)',
                  'createAndGo (4)', and 'destroy (6)'."

        VARIATION   tmnxBsxRadApRowStatus
            SYNTAX  RowStatus {
                       active               (1),
                    -- notInService         (2)
                    -- notReady             (3)
                       createAndGo          (4),
                    -- createAndWait        (5)
                       destroy              (6)
                    }
            DESCRIPTION
                 "tmnxBsxRadApRowStatus supports only 'active (1)', 'createAndGo
                  (4)', and 'destroy (6)'."

        VARIATION   tmnxBsxRadApServAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServAddrType supports only the InetAddressType
                  values 'unknown (0)' and 'ipv4 (1)'."

        VARIATION   tmnxBsxRadApServRowStatus
            SYNTAX  RowStatus {
                       active               (1),
                    -- notInService         (2)
                    -- notReady             (3)
                       createAndGo          (4),
                    -- createAndWait        (5)
                       destroy              (6)
                    }
            DESCRIPTION
                 "tmnxBsxRadApServRowStatus supports only 'active (1)',
                  'createAndGo (4)', and 'destroy (6)'."

        VARIATION   tmnxBsxRadApServerAlgorithm
            SYNTAX  TmnxSubRadServAlgorithm {
                       direct               (1),
                       roundRobin           (2)
                    }
            DESCRIPTION
                 "tmnxBsxRadApServerAlgorithm supports only the values 'direct
                  (1)' and 'roundRobin (2)'."

        VARIATION   tmnxBsxRadApServerSrcAddrType
            SYNTAX  InetAddressType {
                       unknown              (0),
                       ipv4                 (1)
                    -- ipv6                 (2)
                    -- ipv4z                (3)
                    -- ipv6z                (4)
                    -- dns                  (16)
                    }
            DESCRIPTION
                 "tmnxBsxRadApServerSrcAddrType supports only the
                  InetAddressType values 'unknown (0)' and 'ipv4 (1)'."

        VARIATION   tmnxBsxSctpFltrPpidRowStatus
            SYNTAX  RowStatus {
                       active               (1),
                    -- notInService         (2)
                    -- notReady             (3)
                       createAndGo          (4),
                    -- createAndWait        (5)
                       destroy              (6)
                    }
            DESCRIPTION
                 "tmnxBsxSctpFltrPpidRowStatus supports only 'active (1)',
                  'createAndGo (4)', and 'destroy (6)'."

        VARIATION   tmnxBsxSctpFltrRowStatus
            SYNTAX  RowStatus {
                       active               (1),
                    -- notInService         (2)
                    -- notReady             (3)
                       createAndGo          (4),
                    -- createAndWait        (5)
                       destroy              (6)
                    }
            DESCRIPTION
                 "tmnxBsxSctpFltrRowStatus supports only 'active (1)',
                  'createAndGo (4)', and 'destroy (6)'."

        VARIATION   tmnxBsxSessFltrParamsDstAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsDstAddrType supports only the
                  InetAddressType values 'unknown (0)', 'ipv4 (1)', and 'ipv6
                  (2)'."

        VARIATION   tmnxBsxSessFltrParamsDstPortOp
            SYNTAX  TmnxBsxOperator {
                       none                 (0),
                       eq                   (1),
                    -- neq                  (2)
                       lt                   (3),
                       gt                   (4)
                    -- range                (5)
                    }
            DESCRIPTION
                 "tmnxBsxSessFltrParamsDstPortOp only supports the
                  TmnxBsxOperator values of 'none (0)', 'eq (1)', 'lt (3)' and
                  'gt (4)'."

        VARIATION   tmnxBsxSessFltrParamsRowStatus
            SYNTAX  RowStatus {
                       active               (1),
                    -- notInService         (2)
                    -- notReady             (3)
                       createAndGo          (4),
                    -- createAndWait        (5)
                       destroy              (6)
                    }
            DESCRIPTION
                 "tmnxBsxSessFltrParamsRowStatus supports only 'active (1)',
                  'createAndGo (4)', and 'destroy (6)'."

        VARIATION   tmnxBsxSessFltrParamsSrcAddrType
            SYNTAX  InetAddressType {
                       unknown              (0),
                       ipv4                 (1),
                       ipv6                 (2)
                    -- ipv4z                (3)
                    -- ipv6z                (4)
                    -- dns                  (16)
                    }
            DESCRIPTION
                 "tmnxBsxSessFltrParamsSrcAddrType supports only the
                  InetAddressType values 'unknown (0)', 'ipv4 (1)', and 'ipv6
                  (2)'."

        VARIATION   tmnxBsxSessFltrParamsSrcPortOp
            SYNTAX  TmnxBsxOperator {
                       none                 (0),
                       eq                   (1),
                    -- neq                  (2)
                       lt                   (3),
                       gt                   (4)
                    -- range                (5)
                    }
            DESCRIPTION
                 "tmnxBsxSessFltrParamsSrcPortOp only supports the
                  TmnxBsxOperator values of 'none (0)', 'eq (1)', 'lt (3)' and
                  'gt (4)'."

        VARIATION   tmnxBsxSessFltrRowStatus
            SYNTAX  RowStatus {
                       active               (1),
                    -- notInService         (2)
                    -- notReady             (3)
                       createAndGo          (4),
                    -- createAndWait        (5)
                       destroy              (6)
                    }
            DESCRIPTION
                 "tmnxBsxSessFltrRowStatus supports only 'active (1)',
                  'createAndGo (4)', and 'destroy (6)'."

        VARIATION   tmnxBsxStatAaSubCfgEntry
            CREATION-REQUIRES {
                       tmnxBsxStatAaSubCfgRowStatus,
                       tmnxBsxStatAaSubCfgExportMethod
                    }
            DESCRIPTION
                 "Both tmnxBsxStatAaSubCfgRowStatus and
                  tmnxBsxStatAaSubCfgExportMethod must be set for row creation
                  to succeed."

        VARIATION   tmnxBsxStatAaSubCfgRowStatus
            SYNTAX  RowStatus {
                       active               (1),
                    -- notInService         (2)
                    -- notReady             (3)
                       createAndGo          (4),
                    -- createAndWait        (5)
                       destroy              (6)
                    }
            DESCRIPTION
                 "tmnxBsxStatAaSubCfgRowStatus supports only 'active (1)',
                  'createAndGo (4)', and 'destroy (6)'."

        VARIATION   tmnxBsxStatAaSubSdyRowStatus
            SYNTAX  RowStatus {
                       active               (1),
                    -- notInService         (2)
                    -- notReady             (3)
                       createAndGo          (4),
                    -- createAndWait        (5)
                       destroy              (6)
                    }
            DESCRIPTION
                 "tmnxBsxStatAaSubSdyRowStatus supports only 'active (1)',
                  'createAndGo (4)', and 'destroy (6)'."

        VARIATION   tmnxBsxStatTcaCfgRowStatus
            SYNTAX  RowStatus {
                       active               (1),
                    -- notInService         (2)
                    -- notReady             (3)
                       createAndGo          (4),
                    -- createAndWait        (5)
                       destroy              (6)
                    }
            DESCRIPTION
                 "tmnxBsxStatTcaCfgRowStatus supports only 'active (1)',
                  'createAndGo (4)', and 'destroy (6)'."

        VARIATION   tmnxBsxStatTcaFtrCfgRowStatus
            SYNTAX  RowStatus {
                       active               (1),
                    -- notInService         (2)
                    -- notReady             (3)
                       createAndGo          (4),
                    -- createAndWait        (5)
                       destroy              (6)
                    }
            DESCRIPTION
                 "tmnxBsxStatTcaFtrCfgRowStatus supports only 'active (1)',
                  'createAndGo (4)', and 'destroy (6)'."

        VARIATION   tmnxBsxStatTcaFtrEnCfgRowStatus
            SYNTAX  RowStatus {
                       active               (1),
                    -- notInService         (2)
                    -- notReady             (3)
                       createAndGo          (4),
                    -- createAndWait        (5)
                       destroy              (6)
                    }
            DESCRIPTION
                 "tmnxBsxStatTcaFtrEnCfgRowStatus supports only 'active (1)',
                  'createAndGo (4)', and 'destroy (6)'."

        VARIATION   tmnxBsxStatTcaPolcrCfgRowStatus
            SYNTAX  RowStatus {
                       active               (1),
                    -- notInService         (2)
                    -- notReady             (3)
                       createAndGo          (4),
                    -- createAndWait        (5)
                       destroy              (6)
                    }
            DESCRIPTION
                 "tmnxBsxStatTcaPolcrCfgRowStatus supports only 'active (1)',
                  'createAndGo (4)', and 'destroy (6)'."

        VARIATION   tmnxBsxTcpValRowStatus
            SYNTAX  RowStatus {
                       active               (1),
                    -- notInService         (2)
                    -- notReady             (3)
                       createAndGo          (4),
                    -- createAndWait        (5)
                       destroy              (6)
                    }
            DESCRIPTION
                 "tmnxBsxTcpValRowStatus supports only 'active (1)',
                  'createAndGo (4)', and 'destroy (6)'."

        VARIATION   tmnxBsxTcpValTcaRowStatus
            SYNTAX  RowStatus {
                       active               (1),
                    -- notInService         (2)
                    -- notReady             (3)
                       createAndGo          (4),
                    -- createAndWait        (5)
                       destroy              (6)
                    }
            DESCRIPTION
                 "tmnxBsxTcpValTcaRowStatus supports only 'active (1)',
                  'createAndGo (4)', and 'destroy (6)'."

        VARIATION   tmnxBsxTransIpPlcyAddrRowStatus
            SYNTAX  RowStatus {
                       active               (1),
                    -- notInService         (2)
                    -- notReady             (3)
                       createAndGo          (4),
                    -- createAndWait        (5)
                       destroy              (6)
                    }
            DESCRIPTION
                 "tmnxBsxTransIpPlcyAddrRowStatus supports only 'active (1)',
                  'createAndGo (4)', and 'destroy (6)'."

        VARIATION   tmnxBsxTransIpPlcySubRowStatus
            SYNTAX  RowStatus {
                       active               (1),
                    -- notInService         (2)
                    -- notReady             (3)
                       createAndGo          (4),
                    -- createAndWait        (5)
                       destroy              (6)
                    }
            DESCRIPTION
                 "tmnxBsxTransIpPlcySubRowStatus supports only 'active (1)',
                  'createAndGo (4)', and 'destroy (6)'."

        VARIATION   tmnxBsxTransPrefEntryNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntryNetAddrType supports only the
                  InetAddressType values 'unknown (0)' and 'ipv4 (1)'."

        VARIATION   tmnxBsxTransPrefEntryRowStatus
            SYNTAX  RowStatus {
                       active               (1),
                    -- notInService         (2)
                    -- notReady             (3)
                       createAndGo          (4),
                    -- createAndWait        (5)
                       destroy              (6)
                    }
            DESCRIPTION
                 "tmnxBsxTransPrefEntryRowStatus supports only 'active (1)',
                  'createAndGo (4)', and 'destroy (6)'."

        VARIATION   tmnxBsxTransPrefEntrySubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefEntrySubAddrType supports only the
                  InetAddressType values 'unknown (0)' and 'ipv4 (1)'."

        VARIATION   tmnxBsxTransPrefPolicyRowStatus
            SYNTAX  RowStatus {
                       active               (1),
                    -- notInService         (2)
                    -- notReady             (3)
                       createAndGo          (4),
                    -- createAndWait        (5)
                       destroy              (6)
                    }
            DESCRIPTION
                 "tmnxBsxTransPrefPolicyRowStatus supports only 'active (1)',
                  'createAndGo (4)', and 'destroy (6)'."

        VARIATION   tmnxBsxTransPrefSubRowStatus
            SYNTAX  RowStatus {
                       active               (1),
                    -- notInService         (2)
                    -- notReady             (3)
                       createAndGo          (4),
                    -- createAndWait        (5)
                       destroy              (6)
                    }
            DESCRIPTION
                 "tmnxBsxTransPrefSubRowStatus supports only 'active (1)',
                  'createAndGo (4)', and 'destroy (6)'."

        VARIATION   tmnxBsxTransPrefSumNetAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumNetAddrType supports only the
                  InetAddressType values 'unknown (0)' and 'ipv4 (1)'."

        VARIATION   tmnxBsxTransPrefSumSubAddrType
            SYNTAX  InetAddressType {
                       unknown              (0),
                       ipv4                 (1)
                    -- ipv6                 (2)
                    -- ipv4z                (3)
                    -- ipv6z                (4)
                    -- dns                  (16)
                    }
            DESCRIPTION
                 "tmnxBsxTransPrefSumSubAddrType supports only the
                  InetAddressType values 'unknown (0)' and 'ipv4 (1)'."

        VARIATION   tmnxBsxTransitIpPolicyAddrType
            SYNTAX  InetAddressType {
                    -- unknown              (0)
                       ipv4                 (1),
                       ipv6                 (2)
                    -- ipv4z                (3)
                    -- ipv6z                (4)
                    -- dns                  (16)
                    }
            DESCRIPTION
                 "tmnxBsxTransitIpPolicyAddrType supports only the
                  InetAddressType values 'ipv4 (1)', and 'ipv6 (2)'."

        VARIATION   tmnxBsxTransitIpPolicyIPv6PfxLen
            SYNTAX  InetAddressPrefixLength (32..64)
            DESCRIPTION
                 "tmnxBsxTransitIpPolicyIPv6PfxLen supports only the range from
                  32 to 64."

        VARIATION   tmnxBsxTransitIpPolicyRowStatus
            SYNTAX  RowStatus {
                       active               (1),
                    -- notInService         (2)
                    -- notReady             (3)
                       createAndGo          (4),
                    -- createAndWait        (5)
                       destroy              (6)
                    }
            DESCRIPTION
                 "tmnxBsxTransitIpPolicyRowStatus supports only 'active (1)',
                  'createAndGo (4)', and 'destroy (6)'."

        VARIATION   tmnxBsxTransitIpSumParentSubType
            SYNTAX  TmnxBsxAaSubscriberType {
                       unknown              (0),
                    -- esm                  (1)
                       sap                  (2),
                       spokeSdp             (3)
                    -- transit              (4)
                    }
            DESCRIPTION
                 "tmnxBsxTransitIpSumParentSubType supports only the values
                  'unknown(0)', 'sap(2)', and 'spokeSdp(3)'."

        VARIATION   tmnxBsxUrlFilterRowStatus
            SYNTAX  RowStatus {
                       active               (1),
                    -- notInService         (2)
                    -- notReady             (3)
                       createAndGo          (4),
                    -- createAndWait        (5)
                       destroy              (6)
                    }
            DESCRIPTION
                 "tmnxBsxUrlFilterRowStatus supports only 'active (1)',
                  'createAndGo (4)', and 'destroy (6)'."

        VARIATION   tmnxBsxUrlFltrUrlListRowStatus
            SYNTAX  RowStatus {
                       active               (1),
                    -- notInService         (2)
                    -- notReady             (3)
                       createAndGo          (4),
                    -- createAndWait        (5)
                       destroy              (6)
                    }
            DESCRIPTION
                 "tmnxBsxUrlFltrUrlListRowStatus supports only 'active (1)',
                  'createAndGo (4)', and 'destroy (6)'."

        VARIATION   tmnxBsxUrlListRowStatus
            SYNTAX  RowStatus {
                       active               (1),
                    -- notInService         (2)
                    -- notReady             (3)
                       createAndGo          (4),
                    -- createAndWait        (5)
                       destroy              (6)
                    }
            DESCRIPTION
                 "tmnxBsxUrlListRowStatus supports only 'active (1)',
                  'createAndGo (4)', and 'destroy (6)'."

    ::= { tmnx7450AgentV14v0  66 }

--
-- SROS CFLOWD CAPABILITIES
--
tmnxSROSCflowdV14v0               AGENT-CAPABILITIES
    PRODUCT-RELEASE "Nokia SROS"
    STATUS          current
    DESCRIPTION
         "Implementation of CFLOWD functions for Nokia SROS systems release
          14.0."

    SUPPORTS        TIMETRA-CFLOWD-MIB
        INCLUDES {
           tmnxCflowdEnhancedDistGrpV13v0,
           tmnxCflowdExportGroup,
           tmnxCflowdGlobalGroup,
           tmnxCflowdGlobalGroupV6v0,
           tmnxCflowdGroupV12v0,
           tmnxCflowdGroupV8v0,
           tmnxCflowdHostGroup,
           tmnxCflowdNotificationV8v0Group,
           tmnxCflowdStatisticsV10v0Group,
           tmnxCflowdV2HostCfgGroup,
           tmnxCflowdV2HostStatisticsGroup,
           tmnxCflowdVRtrGroupV13v0
        }

        VARIATION   tmnxCFHostCollRowStatus
            SYNTAX  RowStatus {
                       active               (1),
                    -- notInService         (2)
                    -- notReady             (3)
                       createAndGo          (4),
                    -- createAndWait        (5)
                       destroy              (6)
                    }
            DESCRIPTION
                 "tmnxCFHostCollRowStatus supports only 'active (1)',
                  'createAndGo (4)', and 'destroy (6)'."

        VARIATION   tmnxCFHostCollTemplateSet
            DESCRIPTION
                 "tmnxCFHostCollTemplateSet does not support the value 'l2Ip
                  (3)' on cards that do not have SMP processors."

        VARIATION   tmnxCFHostRowStatus
            SYNTAX  RowStatus {
                       active               (1),
                    -- notInService         (2)
                    -- notReady             (3)
                       createAndGo          (4),
                    -- createAndWait        (5)
                       destroy              (6)
                    }
            DESCRIPTION
                 "tmnxCFHostRowStatus supports only 'active (1)', 'createAndGo
                  (4)', and 'destroy (6)'."

        VARIATION   tmnxCflowdFlowUnsuppProto
            ACCESS  not-implemented
            DESCRIPTION
                 "tmnxCflowdFlowUnsuppProto is not implemented on Nokia SROS in
                  release 14.0."

        VARIATION   tmnxCflowdMaxCollectors
            ACCESS  read-only
            DESCRIPTION
                 "tmnxCflowdMaxCollectors is implemented as read-only on Nokia
                  SROS in release 14.0."

        VARIATION   tmnxCflowdTemplateFlowIndex
            DESCRIPTION
                 "tmnxCflowdTemplateFlowIndex does not support the value 'l2
                  (4)' on cards that do not have SMP processors."

        VARIATION   tmnxCflowdVRtrIfRowStatus
            SYNTAX  RowStatus {
                       active               (1),
                    -- notInService         (2)
                    -- notReady             (3)
                       createAndGo          (4),
                    -- createAndWait        (5)
                       destroy              (6)
                    }
            DESCRIPTION
                 "tmnxCflowdVRtrIfRowStatus supports only 'active (1)',
                  'createAndGo (4)', and 'destroy (6)'."

    ::= { tmnxSROSAgentV14v0   5 }

--
-- 7950 CFLOWD CAPABILITIES
--
tmnx7950CflowdV14v0               AGENT-CAPABILITIES
    PRODUCT-RELEASE "Nokia SROS"
    STATUS          current
    DESCRIPTION
         "Implementation of CFLOWD functions for Nokia 7950 systems release
          14.0."

    SUPPORTS        TIMETRA-CFLOWD-MIB
        INCLUDES {
           tmnxCflowdEnhancedDistGrpV13v0,
           tmnxCflowdExportGroup,
           tmnxCflowdGlobalGroup,
           tmnxCflowdGlobalGroupV6v0,
           tmnxCflowdGroupV12v0,
           tmnxCflowdGroupV8v0,
           tmnxCflowdHostGroup,
           tmnxCflowdNotificationV8v0Group,
           tmnxCflowdStatisticsV10v0Group,
           tmnxCflowdV2HostCfgGroup,
           tmnxCflowdV2HostStatisticsGroup,
           tmnxCflowdVRtrGroupV13v0
        }

        VARIATION   tmnxCFHostCollRowStatus
            SYNTAX  RowStatus {
                       active               (1),
                    -- notInService         (2)
                    -- notReady             (3)
                       createAndGo          (4),
                    -- createAndWait        (5)
                       destroy              (6)
                    }
            DESCRIPTION
                 "tmnxCFHostCollRowStatus supports only 'active (1)',
                  'createAndGo (4)', and 'destroy (6)'."

        VARIATION   tmnxCFHostCollTemplateSet
            DESCRIPTION
                 "tmnxCFHostCollTemplateSet does not support the value 'l2Ip
                  (3)' on cards that do not have SMP processors."

        VARIATION   tmnxCFHostRowStatus
            SYNTAX  RowStatus {
                       active               (1),
                    -- notInService         (2)
                    -- notReady             (3)
                       createAndGo          (4),
                    -- createAndWait        (5)
                       destroy              (6)
                    }
            DESCRIPTION
                 "tmnxCFHostRowStatus supports only 'active (1)', 'createAndGo
                  (4)', and 'destroy (6)'."

        VARIATION   tmnxCflowdCacheSize
            DEFVAL  { 500000  }
            DESCRIPTION
                 "The default value on the Nokia 7950 is 500,000"

        VARIATION   tmnxCflowdFlowUnsuppProto
            ACCESS  not-implemented
            DESCRIPTION
                 "tmnxCflowdFlowUnsuppProto is not implemented on Nokia 7950 in
                  release 14.0."

        VARIATION   tmnxCflowdMaxCollectors
            ACCESS  read-only
            DESCRIPTION
                 "tmnxCflowdMaxCollectors is implemented as read-only on Nokia
                  7950 in release 14.0."

        VARIATION   tmnxCflowdTemplateFlowIndex
            DESCRIPTION
                 "tmnxCflowdTemplateFlowIndex does not support the value 'l2
                  (4)' on cards that do not have SMP processors."

        VARIATION   tmnxCflowdVRtrIfRowStatus
            SYNTAX  RowStatus {
                       active               (1),
                    -- notInService         (2)
                    -- notReady             (3)
                       createAndGo          (4),
                    -- createAndWait        (5)
                       destroy              (6)
                    }
            DESCRIPTION
                 "tmnxCflowdVRtrIfRowStatus supports only 'active (1)',
                  'createAndGo (4)', and 'destroy (6)'."

    ::= { tmnx7950AgentV14v0   5 }

--
-- SROS CHASSIS CAPABILITIES
--
tmnxSROSChassisV14v0              AGENT-CAPABILITIES
    PRODUCT-RELEASE "Nokia SROS"
    STATUS          current
    DESCRIPTION
         "Implementation of CHASSIS functions for Nokia SROS systems release
          14.0."

    SUPPORTS        TIMETRA-CHASSIS-MIB
        INCLUDES {
           tFPFwdEngStatsGroup,
-- EXCLUDE tmnx7710HwV3v0Group
-- EXCLUDE tmnx7710SETSRefSrcHwV6v0Group
-- EXCLUDE tmnx77x0CESMDAV6v0Group
           tmnxAtmGroup,
           tmnxCardCamErrorV6v1Group,
           tmnxCardCmplChipIfErrV9v0Group,
           tmnxCardCmplQChipMemErrV9v0Group,
           tmnxCardPchipV5v0Group,
           tmnxCardPchipV8v0Group,
-- EXCLUDE tmnxCardResetOnRecoverErGrp
           tmnxCardV10v0Group,
           tmnxCardV3v0Group,
-- EXCLUDE tmnxCardV6v0NamedPoolPlcyGroup
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
-- EXCLUDE tmnxChassisV7v0Group
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
-- EXCLUDE tmnxFPMcPathMgmtV6v1Group
           tmnxFPPlcyAcctV12v0Group,
           tmnxFPPoolSizingV11v0Group,
           tmnxFPQGrpGroup,
-- EXCLUDE tmnxFPQGrpV10v0R4Group
           tmnxFPV13v0Group,
-- EXCLUDE tmnxFPWredV7v0Group
-- EXCLUDE tmnxIPsecIsaGrpV6v0Group
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
-- EXCLUDE tmnxMDACcagV6v1Group
-- EXCLUDE tmnxMDAMcPathMgmtV6v0Group
-- EXCLUDE tmnxMDAResetOnRecoverErGrp
           tmnxMDAV6v1Group,
           tmnxMDAV9v0Group,
           tmnxMdaHsmdaPoolV10v0Group,
-- EXCLUDE tmnxMdaV10v0Group
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
-- EXCLUDE tmnxSyncIfTimingV9v0Group
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tmnxCardAllowedTypes
            ACCESS  not-implemented
            DESCRIPTION
                 "tmnxCardAllowedTypes is not implemented on Nokia SROS in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  SROS in release 14.0.

                  tmnxChassisAdminLastSetTimeout was obsoleted in release
                  12.0."

        VARIATION   tmnxChassisAdminLastSetTimer
            ACCESS  not-implemented
            DESCRIPTION
                 "tmnxChassisAdminLastSetTimer is not implemented on Nokia SROS
                  in release 14.0.

                  tmnxChassisAdminLastSetTimer was obsoleted in release 12.0."

        VARIATION   tmnxChassisRowStatus
            ACCESS  read-only
            DESCRIPTION
                 "tmnxChassisRowStatus is implemented as read-only on Nokia SROS
                  in release 14.0.

                  Row entries cannot be created by SNMP SET requests. Multiple
                  chassis's are not supported on Nokia SROS."

        VARIATION   tmnxCpmCardAllowedTypes
            ACCESS  not-implemented
            DESCRIPTION
                 "tmnxCpmCardAllowedTypes is not implemented on Nokia SROS in
                  release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  SROS in release 14.0.

                  Multiple CPM card types are not supported on Nokia SROS."

        VARIATION   tmnxEqBackdoorBusFailure
            ACCESS  not-implemented
            DESCRIPTION
                 "tmnxEqBackdoorBusFailure is not implemented on Nokia SROS in
                  release 14.0.

                  This notification was made obsolete in the 2.1 release."

        VARIATION   tmnxEqCpuFailure
            ACCESS  not-implemented
            DESCRIPTION
                 "tmnxEqCpuFailure is not implemented on Nokia SROS in release
                  14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia SROS in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxHwConfigChange
            ACCESS  not-implemented
            DESCRIPTION
                 "tmnxHwConfigChange is not implemented on Nokia SROS in release
                  14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia SROS in
                  release 14.0."

        VARIATION   tmnxHwLastAlarmEvent
            DESCRIPTION
                 "tmnxHwLastAlarmEvent is not supported on Nokia SROS. The value
                  of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxMDAAllowedTypes
            ACCESS  not-implemented
            DESCRIPTION
                 "tmnxMDAAllowedTypes is not implemented on Nokia SROS in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia SROS in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia SROS in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

    ::= { tmnxSROSAgentV14v0   6 }

--
-- 7750 CHASSIS CAPABILITIES
--
tmnx7750ChassisV14v0              AGENT-CAPABILITIES
    PRODUCT-RELEASE "Nokia SROS"
    STATUS          current
    DESCRIPTION
         "Implementation of CHASSIS functions for Nokia 7750 systems release
          14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  with an active CPM/SFM that supports PTP. Otherwise, this
                  object is not-implemented."

        VARIATION   tSyncIfTimingAdmPTPCfgQltyLevel
            DESCRIPTION
                 "tSyncIfTimingAdmPTPCfgQltyLevel is only supported on Nokia
                  7750 with an active CPM/SFM that supports PTP. Otherwise, this
                  object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750 with
                  an active CPM/SFM that supports PTP. Otherwise, this object is
                  not-implemented."

        VARIATION   tmnxCardAllowedTypes
            ACCESS  not-implemented
            DESCRIPTION
                 "tmnxCardAllowedTypes is not implemented on Nokia 7750 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  in release 14.0.

                  tmnxChassisAdminLastSetTimer was obsoleted in release 12.0."

        VARIATION   tmnxChassisRowStatus
            ACCESS  read-only
            DESCRIPTION
                 "tmnxChassisRowStatus is implemented as read-only on Nokia 7750
                  in release 14.0.

                  Row entries cannot be created by SNMP SET requests. Multiple
                  chassis's are not supported on Nokia 7750."

        VARIATION   tmnxCpmCardAllowedTypes
            ACCESS  not-implemented
            DESCRIPTION
                 "tmnxCpmCardAllowedTypes is not implemented on Nokia 7750 in
                  release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 in release 14.0.

                  Multiple CPM card types are not supported on Nokia 7750."

        VARIATION   tmnxEqBackdoorBusFailure
            ACCESS  not-implemented
            DESCRIPTION
                 "tmnxEqBackdoorBusFailure is not implemented on Nokia 7750 in
                  release 14.0.

                  This notification was made obsolete in the 2.1 release."

        VARIATION   tmnxEqCpuFailure
            ACCESS  not-implemented
            DESCRIPTION
                 "tmnxEqCpuFailure is not implemented on Nokia 7750 in release
                  14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  with an active CPM/SFM that supports PTP. Otherwise, this
                  object is not-implemented."

        VARIATION   tmnxEqSyncIfTimingPTPAlarmClear
            DESCRIPTION
                 "tmnxEqSyncIfTimingPTPAlarmClear is only supported on Nokia
                  7750 with an active CPM/SFM that supports PTP. Otherwise, this
                  object is not-implemented."

        VARIATION   tmnxEqSyncIfTimingPTPQuality
            DESCRIPTION
                 "tmnxEqSyncIfTimingPTPQuality is only supported on Nokia 7750
                  with an active CPM/SFM that supports PTP. Otherwise, this
                  object is not-implemented."

        VARIATION   tmnxHwConfigChange
            ACCESS  not-implemented
            DESCRIPTION
                 "tmnxHwConfigChange is not implemented on Nokia 7750 in release
                  14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 in
                  release 14.0."

        VARIATION   tmnxHwLastAlarmEvent
            DESCRIPTION
                 "tmnxHwLastAlarmEvent is not supported on Nokia 7750. The value
                  of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7750 in release 14.0."

        VARIATION   tmnxSyncIfTimingBITS2Alarm
            ACCESS  not-implemented
            DESCRIPTION
                 "tmnxSyncIfTimingBITS2Alarm is not implemented on Nokia 7750 in
                  release 14.0."

        VARIATION   tmnxSyncIfTimingBITS2InUse
            ACCESS  not-implemented
            DESCRIPTION
                 "tmnxSyncIfTimingBITS2InUse is not implemented on Nokia 7750 in
                  release 14.0."

        VARIATION   tmnxSyncIfTimingBITS2Qualified
            ACCESS  not-implemented
            DESCRIPTION
                 "tmnxSyncIfTimingBITS2Qualified is not implemented on Nokia
                  7750 in release 14.0."

        VARIATION   tmnxSyncIfTimingBITS2RxQltyLevel
            ACCESS  not-implemented
            DESCRIPTION
                 "tmnxSyncIfTimingBITS2RxQltyLevel is not implemented on Nokia
                  7750 in release 14.0."

        VARIATION   tmnxSyncIfTimingBITS2State
            ACCESS  not-implemented
            DESCRIPTION
                 "tmnxSyncIfTimingBITS2State is not implemented on Nokia 7750 in
                  release 14.0."

        VARIATION   tmnxSyncIfTimingPTPAdminStatus
            DESCRIPTION
                 "tmnxSyncIfTimingPTPAdminStatus is only supported on Nokia 7750
                  with an active CPM/SFM that supports PTP. Otherwise, this
                  object is not-implemented."

        VARIATION   tmnxSyncIfTimingPTPAlarm
            DESCRIPTION
                 "tmnxSyncIfTimingPTPAlarm is only supported on Nokia 7750 with
                  an active CPM/SFM that supports PTP. Otherwise, this object is
                  not-implemented."

        VARIATION   tmnxSyncIfTimingPTPCfgQltyLevel
            DESCRIPTION
                 "tmnxSyncIfTimingPTPCfgQltyLevel is only supported on Nokia
                  7750 with an active CPM/SFM that supports PTP. Otherwise, this
                  object is not-implemented."

        VARIATION   tmnxSyncIfTimingPTPInUse
            DESCRIPTION
                 "tmnxSyncIfTimingPTPInUse is only supported on Nokia 7750 with
                  an active CPM/SFM that supports PTP. Otherwise, this object is
                  not-implemented."

        VARIATION   tmnxSyncIfTimingPTPQualified
            DESCRIPTION
                 "tmnxSyncIfTimingPTPQualified is only supported on Nokia 7750
                  with an active CPM/SFM that supports PTP. Otherwise, this
                  object is not-implemented."

        VARIATION   tmnxSyncIfTimingPTPRxQltyLevel
            DESCRIPTION
                 "tmnxSyncIfTimingPTPRxQltyLevel is only supported on Nokia 7750
                  with an active CPM/SFM that supports PTP. Otherwise, this
                  object is not-implemented."

        VARIATION   tmnxSyncIfTimingPTPState
            DESCRIPTION
                 "tmnxSyncIfTimingPTPState is only supported on Nokia 7750 with
                  an active CPM/SFM that supports PTP. Otherwise, this object is
                  not-implemented."

        VARIATION   tmnxSyncIfTimingRef1NationalUse
            ACCESS  not-implemented
            DESCRIPTION
                 "tmnxSyncIfTimingRef1NationalUse is not implemented on Nokia
                  7750 in release 14.0."

        VARIATION   tmnxSyncIfTimingRef2NationalUse
            ACCESS  not-implemented
            DESCRIPTION
                 "tmnxSyncIfTimingRef2NationalUse is not implemented on Nokia
                  7750 in release 14.0."

        VARIATION   tmnxSyncIfTimingRefOrder4
            DESCRIPTION
                 "tmnxSyncIfTimingRefOrder4 is only supported on Nokia 7750 with
                  an active CPM/SFM that supports PTP. Otherwise, this object is
                  not-implemented."

    ::= { tmnx7750AgentV14v0   6 }

--
-- 7750c12 CHASSIS CAPABILITIES
--
tmnx7750c12ChassisV14v0           AGENT-CAPABILITIES
    PRODUCT-RELEASE "Nokia SROS"
    STATUS          current
    DESCRIPTION
         "Implementation of CHASSIS functions for Nokia 7750 c12 systems release
          14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
-- EXCLUDE tmnxMdaHsmdaPoolV10v0Group
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmBITSNationalUse
            ACCESS  not-implemented
            DESCRIPTION
                 "tSyncIfTimingAdmBITSNationalUse is not implemented on Nokia
                  7750 c12 in release 14.0."

        VARIATION   tSyncIfTimingAdmPTPAdminStatus
            DESCRIPTION
                 "tSyncIfTimingAdmPTPAdminStatus is only supported on Nokia 7750
                  c12 with an active CPM/SFM that supports PTP. Otherwise, this
                  object is not-implemented.

                  tSyncIfTimingAdmPTPAdminStatus is not implemented on Nokia
                  7750 c12 in release 14.0."

        VARIATION   tSyncIfTimingAdmPTPCfgQltyLevel
            DESCRIPTION
                 "tSyncIfTimingAdmPTPCfgQltyLevel is only supported on Nokia
                  7750 c12 with an active CPM/SFM that supports PTP. Otherwise,
                  this object is not-implemented.

                  tSyncIfTimingAdmPTPCfgQltyLevel is not implemented on Nokia
                  7750 c12 in release 14.0."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 c12 in release 14.0."

        VARIATION   tSyncIfTimingAdmRef1SrcHw
            ACCESS  not-implemented
            DESCRIPTION
                 "tSyncIfTimingAdmRef1SrcHw is not implemented on Nokia 7750 c12
                  in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 c12 in release 14.0."

        VARIATION   tSyncIfTimingAdmRef2SrcHw
            ACCESS  not-implemented
            DESCRIPTION
                 "tSyncIfTimingAdmRef2SrcHw is not implemented on Nokia 7750 c12
                  in release 14.0."

        VARIATION   tSyncIfTimingAdmRefOrder1
            SYNTAX  INTEGER {
                    -- otherCPM             (0)
                       reference1           (1),
                       reference2           (2)
                    -- bits                 (3)
                    -- bits2                (4)
                    -- ptp                  (5)
                    -- noReference          (6)
                    }
            DEFVAL  { reference1  }
            DESCRIPTION
                 "The only values supported for tSyncIfTimingAdmRefOrder1 on
                  Nokia 7750 c12 are 'reference1 (1)' and 'reference2 (2)'.

                  An attempt to set tSyncIfTimingAdmRefOrder1 to the value
                  'bits (3)' will result in a 'wrongValue' error. The default
                  Value is 'reference1' instead of 'bits'."

        VARIATION   tSyncIfTimingAdmRefOrder2
            SYNTAX  INTEGER {
                    -- otherCPM             (0)
                       reference1           (1),
                       reference2           (2)
                    -- bits                 (3)
                    -- bits2                (4)
                    -- ptp                  (5)
                    -- noReference          (6)
                    }
            DEFVAL  { reference2  }
            DESCRIPTION
                 "The only values supported for tSyncIfTimingAdmRefOrder2 on
                  Nokia 7750 c12 are 'reference1 (1)' and 'reference2 (2)'.

                  An attempt to set tSyncIfTimingAdmRefOrder2 to the value
                  'bits (3)' will result in a 'wrongValue' error. The default
                  value is 'reference2' instead of 'bits'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750 c12
                  with an active CPM/SFM that supports PTP. Otherwise, this
                  object is not-implemented."

        VARIATION   tmnxCardAllowedTypes
            ACCESS  not-implemented
            DESCRIPTION
                 "tmnxCardAllowedTypes is not implemented on Nokia 7750 c12 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 c12 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  c12 in release 14.0.

                  tmnxChassisAdminLastSetTimer was obsoleted in release 12.0."

        VARIATION   tmnxChassisAdminMode
            SYNTAX  TmnxChassisMode {
                    -- modeA                (1)
                    -- modeB                (2)
                    -- modeC                (3)
                       modeD                (4)
                    }
            DESCRIPTION
                 "The only value supported for tmnxChassisAdminMode on Nokia
                  7750 c12 is 'modeD(4)'."

        VARIATION   tmnxChassisRowStatus
            ACCESS  read-only
            DESCRIPTION
                 "tmnxChassisRowStatus is implemented as read-only on Nokia 7750
                  c12 in release 14.0.

                  Row entries cannot be created by SNMP SET requests. Multiple
                  chassis's are not supported on Nokia 7750 c12."

        VARIATION   tmnxCpmCardAllowedTypes
            ACCESS  not-implemented
            DESCRIPTION
                 "tmnxCpmCardAllowedTypes is not implemented on Nokia 7750 c12
                  in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 c12 in release 14.0.

                  Multiple CPM card types are not supported on Nokia 7750 c12."

        VARIATION   tmnxEqBackdoorBusFailure
            ACCESS  not-implemented
            DESCRIPTION
                 "tmnxEqBackdoorBusFailure is not implemented on Nokia 7750 c12
                  in release 14.0.

                  This notification was made obsolete in the 2.1 release."

        VARIATION   tmnxEqCpuFailure
            ACCESS  not-implemented
            DESCRIPTION
                 "tmnxEqCpuFailure is not implemented on Nokia 7750 c12 in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 c12 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750 c12
                  with an active CPM/SFM that supports PTP. Otherwise, this
                  object is not-implemented.

                  tmnxEqSyncIfTimingPTPAlarm is not implemented on Nokia 7750
                  c12 in release 14.0."

        VARIATION   tmnxEqSyncIfTimingPTPAlarmClear
            DESCRIPTION
                 "tmnxEqSyncIfTimingPTPAlarmClear is only supported on Nokia
                  7750 c12 with an active CPM/SFM that supports PTP. Otherwise,
                  this object is not-implemented.

                  tmnxEqSyncIfTimingPTPAlarmClear is not implemented on Nokia
                  7750 c12 in release 14.0."

        VARIATION   tmnxEqSyncIfTimingPTPQuality
            DESCRIPTION
                 "tmnxEqSyncIfTimingPTPQuality is only supported on Nokia 7750
                  c12 with an active CPM/SFM that supports PTP. Otherwise, this
                  object is not-implemented.

                  tmnxEqSyncIfTimingPTPQuality is not implemented on Nokia 7750
                  c12 in release 14.0."

        VARIATION   tmnxHwConfigChange
            ACCESS  not-implemented
            DESCRIPTION
                 "tmnxHwConfigChange is not implemented on Nokia 7750 c12 in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 c12 in
                  release 14.0."

        VARIATION   tmnxHwLastAlarmEvent
            DESCRIPTION
                 "tmnxHwLastAlarmEvent is not supported on Nokia 7750 c12. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 c12 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEgrNamedPoolPolicy
            ACCESS  not-implemented
            DESCRIPTION
                 "tmnxMDAEgrNamedPoolPolicy is not implemented on Nokia 7750 c12
                  in release 14.0."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxMDAIngNamedPoolPolicy
            ACCESS  not-implemented
            DESCRIPTION
                 "tmnxMDAIngNamedPoolPolicy is not implemented on Nokia 7750 c12
                  in release 14.0."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  c12 in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 c12 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7750 c12 in release 14.0.

                  tmnxSyncIfTimingBITS2AdminStatus is not implemented on Nokia
                  7750 c12 in release 14.0."

        VARIATION   tmnxSyncIfTimingBITS2Alarm
            ACCESS  not-implemented
            DESCRIPTION
                 "tmnxSyncIfTimingBITS2Alarm is not implemented on Nokia 7750
                  c12 in release 14.0.

                  tmnxSyncIfTimingBITS2Alarm is not implemented on Nokia 7750
                  c12 in release 14.0."

        VARIATION   tmnxSyncIfTimingBITS2InUse
            ACCESS  not-implemented
            DESCRIPTION
                 "tmnxSyncIfTimingBITS2InUse is not implemented on Nokia 7750
                  c12 in release 14.0.

                  tmnxSyncIfTimingBITS2InUse is not implemented on Nokia 7750
                  c12 in release 14.0."

        VARIATION   tmnxSyncIfTimingBITS2Qualified
            ACCESS  not-implemented
            DESCRIPTION
                 "tmnxSyncIfTimingBITS2Qualified is not implemented on Nokia
                  7750 c12 in release 14.0.

                  tmnxSyncIfTimingBITS2Qualified is not implemented on Nokia
                  7750 c12 in release 14.0."

        VARIATION   tmnxSyncIfTimingBITS2RxQltyLevel
            ACCESS  not-implemented
            DESCRIPTION
                 "tmnxSyncIfTimingBITS2RxQltyLevel is not implemented on Nokia
                  7750 c12 in release 14.0.

                  tmnxSyncIfTimingBITS2RxQltyLevel is not implemented on Nokia
                  7750 c12 in release 14.0."

        VARIATION   tmnxSyncIfTimingBITS2State
            ACCESS  not-implemented
            DESCRIPTION
                 "tmnxSyncIfTimingBITS2State is not implemented on Nokia 7750
                  c12 in release 14.0.

                  tmnxSyncIfTimingBITS2State is not implemented on Nokia 7750
                  c12 in release 14.0."

        VARIATION   tmnxSyncIfTimingBITSNationalUse
            ACCESS  not-implemented
            DESCRIPTION
                 "tmnxSyncIfTimingBITSNationalUse is not implemented on Nokia
                  7750 c12 in release 14.0."

        VARIATION   tmnxSyncIfTimingBITSTxQltyLevel
            ACCESS  not-implemented
            DESCRIPTION
                 "tmnxSyncIfTimingBITSTxQltyLevel is not implemented on Nokia
                  7750 c12 in release 14.0."

        VARIATION   tmnxSyncIfTimingPTPAdminStatus
            DESCRIPTION
                 "tmnxSyncIfTimingPTPAdminStatus is only supported on Nokia 7750
                  c12 with an active CPM/SFM that supports PTP. Otherwise, this
                  object is not-implemented.

                  tmnxSyncIfTimingPTPAdminStatus is not implemented on Nokia
                  7750 c12 in release 14.0."

        VARIATION   tmnxSyncIfTimingPTPAlarm
            DESCRIPTION
                 "tmnxSyncIfTimingPTPAlarm is only supported on Nokia 7750 c12
                  with an active CPM/SFM that supports PTP. Otherwise, this
                  object is not-implemented.

                  tmnxSyncIfTimingPTPAlarm is not implemented on Nokia 7750 c12
                  in release 14.0."

        VARIATION   tmnxSyncIfTimingPTPCfgQltyLevel
            DESCRIPTION
                 "tmnxSyncIfTimingPTPCfgQltyLevel is only supported on Nokia
                  7750 c12 with an active CPM/SFM that supports PTP. Otherwise,
                  this object is not-implemented.

                  tmnxSyncIfTimingPTPCfgQltyLevel is not implemented on Nokia
                  7750 c12 in release 14.0."

        VARIATION   tmnxSyncIfTimingPTPInUse
            DESCRIPTION
                 "tmnxSyncIfTimingPTPInUse is only supported on Nokia 7750 c12
                  with an active CPM/SFM that supports PTP. Otherwise, this
                  object is not-implemented.

                  tmnxSyncIfTimingPTPInUse is not implemented on Nokia 7750 c12
                  in release 14.0."

        VARIATION   tmnxSyncIfTimingPTPQualified
            DESCRIPTION
                 "tmnxSyncIfTimingPTPQualified is only supported on Nokia 7750
                  c12 with an active CPM/SFM that supports PTP. Otherwise, this
                  object is not-implemented.

                  tmnxSyncIfTimingPTPQualified is not implemented on Nokia 7750
                  c12 in release 14.0."

        VARIATION   tmnxSyncIfTimingPTPRxQltyLevel
            DESCRIPTION
                 "tmnxSyncIfTimingPTPRxQltyLevel is only supported on Nokia 7750
                  c12 with an active CPM/SFM that supports PTP. Otherwise, this
                  object is not-implemented.

                  tmnxSyncIfTimingPTPRxQltyLevel is not implemented on Nokia
                  7750 c12 in release 14.0."

        VARIATION   tmnxSyncIfTimingPTPState
            DESCRIPTION
                 "tmnxSyncIfTimingPTPState is only supported on Nokia 7750 c12
                  with an active CPM/SFM that supports PTP. Otherwise, this
                  object is not-implemented.

                  tmnxSyncIfTimingPTPState is not implemented on Nokia 7750 c12
                  in release 14.0."

        VARIATION   tmnxSyncIfTimingRef1BITSIfType
            ACCESS  not-implemented
            DESCRIPTION
                 "tmnxSyncIfTimingRef1BITSIfType is not implemented on Nokia
                  7750 c12 in release 14.0."

        VARIATION   tmnxSyncIfTimingRef1NationalUse
            ACCESS  not-implemented
            DESCRIPTION
                 "tmnxSyncIfTimingRef1NationalUse is not implemented on Nokia
                  7750 c12 in release 14.0."

        VARIATION   tmnxSyncIfTimingRef1SrcHw
            ACCESS  not-implemented
            DESCRIPTION
                 "tmnxSyncIfTimingRef1SrcHw is not implemented on Nokia 7750 c12
                  in release 14.0."

        VARIATION   tmnxSyncIfTimingRef2BITSIfType
            ACCESS  not-implemented
            DESCRIPTION
                 "tmnxSyncIfTimingRef2BITSIfType is not implemented on Nokia
                  7750 c12 in release 14.0."

        VARIATION   tmnxSyncIfTimingRef2NationalUse
            ACCESS  not-implemented
            DESCRIPTION
                 "tmnxSyncIfTimingRef2NationalUse is not implemented on Nokia
                  7750 c12 in release 14.0."

        VARIATION   tmnxSyncIfTimingRef2SrcHw
            ACCESS  not-implemented
            DESCRIPTION
                 "tmnxSyncIfTimingRef2SrcHw is not implemented on Nokia 7750 c12
                  in release 14.0."

        VARIATION   tmnxSyncIfTimingRefOrder4
            ACCESS  not-implemented
            DESCRIPTION
                 "tmnxSyncIfTimingRefOrder4 is not implemented on Nokia 7750 c12
                  in release 14.0.

                  tmnxSyncIfTimingRefOrder4 is only supported on Nokia 7750 c12
                  with an active CPM/SFM that supports PTP. Otherwise, this
                  object is not-implemented."

    ::= { tmnx7750c12AgentV14v0   6 }

--
-- 7750c4 CHASSIS CAPABILITIES
--
tmnx7750c4ChassisV14v0            AGENT-CAPABILITIES
    PRODUCT-RELEASE "Nokia SROS"
    STATUS          current
    DESCRIPTION
         "Implementation of CHASSIS functions for Nokia 7750 c4 systems release
          14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
-- EXCLUDE tmnxMdaHsmdaPoolV10v0Group
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  c4 with an active CPM/SFM that supports PTP. Otherwise, this
                  object is not-implemented."

        VARIATION   tSyncIfTimingAdmPTPCfgQltyLevel
            DESCRIPTION
                 "tSyncIfTimingAdmPTPCfgQltyLevel is only supported on Nokia
                  7750 c4 with an active CPM/SFM that supports PTP. Otherwise,
                  this object is not-implemented."

        VARIATION   tSyncIfTimingAdmRef1BITSIfType
            ACCESS  not-implemented
            DESCRIPTION
                 "tSyncIfTimingAdmRef1BITSIfType is not implemented on Nokia
                  7750 c4 in release 14.0."

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 c4 in release 14.0."

        VARIATION   tSyncIfTimingAdmRef2BITSIfType
            ACCESS  not-implemented
            DESCRIPTION
                 "tSyncIfTimingAdmRef2BITSIfType is not implemented on Nokia
                  7750 c4 in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 c4 in release 14.0."

        VARIATION   tSyncIfTimingAdmRefOrder1
            SYNTAX  INTEGER {
                    -- otherCPM             (0)
                       reference1           (1),
                       reference2           (2)
                    -- bits                 (3)
                    -- bits2                (4)
                    -- ptp                  (5)
                    -- noReference          (6)
                    }
            DEFVAL  { reference1  }
            DESCRIPTION
                 "The only values supported for tSyncIfTimingAdmRefOrder1 on
                  Nokia 7750 c4 are 'reference1 (1)' and 'reference2 (2)'.

                  An attempt to set tSyncIfTimingAdmRefOrder1 to the value
                  'bits (3)' will result in a 'wrongValue' error. The default
                  Value is 'reference1' instead of 'bits'."

        VARIATION   tSyncIfTimingAdmRefOrder2
            SYNTAX  INTEGER {
                    -- otherCPM             (0)
                       reference1           (1),
                       reference2           (2)
                    -- bits                 (3)
                    -- bits2                (4)
                    -- ptp                  (5)
                    -- noReference          (6)
                    }
            DEFVAL  { reference2  }
            DESCRIPTION
                 "The only values supported for tSyncIfTimingAdmRefOrder2 on
                  Nokia 7750 c4 are 'reference1 (1)' and 'reference2 (2)'.

                  An attempt to set tSyncIfTimingAdmRefOrder2 to the value
                  'bits (3)' will result in a 'wrongValue' error. The default
                  value is 'reference2' instead of 'bits'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750 c4
                  with an active CPM/SFM that supports PTP. Otherwise, this
                  object is not-implemented."

        VARIATION   tmnxCardAllowedTypes
            ACCESS  not-implemented
            DESCRIPTION
                 "tmnxCardAllowedTypes is not implemented on Nokia 7750 c4 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 c4 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  c4 in release 14.0.

                  tmnxChassisAdminLastSetTimer was obsoleted in release 12.0."

        VARIATION   tmnxChassisAdminMode
            SYNTAX  TmnxChassisMode {
                    -- modeA                (1)
                    -- modeB                (2)
                    -- modeC                (3)
                       modeD                (4)
                    }
            DESCRIPTION
                 "The only value supported for tmnxChassisAdminMode on Nokia
                  7750 c4 is 'modeD(4)'."

        VARIATION   tmnxChassisRowStatus
            ACCESS  read-only
            DESCRIPTION
                 "tmnxChassisRowStatus is implemented as read-only on Nokia 7750
                  c4 in release 14.0.

                  Row entries cannot be created by SNMP SET requests. Multiple
                  chassis's are not supported on Nokia 7750 c4."

        VARIATION   tmnxCpmCardAllowedTypes
            ACCESS  not-implemented
            DESCRIPTION
                 "tmnxCpmCardAllowedTypes is not implemented on Nokia 7750 c4 in
                  release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 c4 in release 14.0.

                  Multiple CPM card types are not supported on Nokia 7750 c4."

        VARIATION   tmnxEqBackdoorBusFailure
            ACCESS  not-implemented
            DESCRIPTION
                 "tmnxEqBackdoorBusFailure is not implemented on Nokia 7750 c4
                  in release 14.0.

                  This notification was made obsolete in the 2.1 release."

        VARIATION   tmnxEqCpuFailure
            ACCESS  not-implemented
            DESCRIPTION
                 "tmnxEqCpuFailure is not implemented on Nokia 7750 c4 in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 c4 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750 c4
                  with an active CPM/SFM that supports PTP. Otherwise, this
                  object is not-implemented."

        VARIATION   tmnxEqSyncIfTimingPTPAlarmClear
            DESCRIPTION
                 "tmnxEqSyncIfTimingPTPAlarmClear is only supported on Nokia
                  7750 c4 with an active CPM/SFM that supports PTP. Otherwise,
                  this object is not-implemented."

        VARIATION   tmnxEqSyncIfTimingPTPQuality
            DESCRIPTION
                 "tmnxEqSyncIfTimingPTPQuality is only supported on Nokia 7750
                  c4 with an active CPM/SFM that supports PTP. Otherwise, this
                  object is not-implemented."

        VARIATION   tmnxHwConfigChange
            ACCESS  not-implemented
            DESCRIPTION
                 "tmnxHwConfigChange is not implemented on Nokia 7750 c4 in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 c4 in
                  release 14.0."

        VARIATION   tmnxHwLastAlarmEvent
            DESCRIPTION
                 "tmnxHwLastAlarmEvent is not supported on Nokia 7750 c4. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 c4 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEgrNamedPoolPolicy
            ACCESS  not-implemented
            DESCRIPTION
                 "tmnxMDAEgrNamedPoolPolicy is not implemented on Nokia 7750 c4
                  in release 14.0."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxMDAIngNamedPoolPolicy
            ACCESS  not-implemented
            DESCRIPTION
                 "tmnxMDAIngNamedPoolPolicy is not implemented on Nokia 7750 c4
                  in release 14.0."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750 c4
                  in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 c4 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7750 c4 in release 14.0."

        VARIATION   tmnxSyncIfTimingBITS2Alarm
            ACCESS  not-implemented
            DESCRIPTION
                 "tmnxSyncIfTimingBITS2Alarm is not implemented on Nokia 7750 c4
                  in release 14.0."

        VARIATION   tmnxSyncIfTimingBITS2InUse
            ACCESS  not-implemented
            DESCRIPTION
                 "tmnxSyncIfTimingBITS2InUse is not implemented on Nokia 7750 c4
                  in release 14.0."

        VARIATION   tmnxSyncIfTimingBITS2Qualified
            ACCESS  not-implemented
            DESCRIPTION
                 "tmnxSyncIfTimingBITS2Qualified is not implemented on Nokia
                  7750 c4 in release 14.0."

        VARIATION   tmnxSyncIfTimingBITS2RxQltyLevel
            ACCESS  not-implemented
            DESCRIPTION
                 "tmnxSyncIfTimingBITS2RxQltyLevel is not implemented on Nokia
                  7750 c4 in release 14.0."

        VARIATION   tmnxSyncIfTimingBITS2State
            ACCESS  not-implemented
            DESCRIPTION
                 "tmnxSyncIfTimingBITS2State is not implemented on Nokia 7750 c4
                  in release 14.0."

        VARIATION   tmnxSyncIfTimingPTPAdminStatus
            DESCRIPTION
                 "tmnxSyncIfTimingPTPAdminStatus is only supported on Nokia 7750
                  c4 with an active CPM/SFM that supports PTP. Otherwise, this
                  object is not-implemented."

        VARIATION   tmnxSyncIfTimingPTPAlarm
            DESCRIPTION
                 "tmnxSyncIfTimingPTPAlarm is only supported on Nokia 7750 c4
                  with an active CPM/SFM that supports PTP. Otherwise, this
                  object is not-implemented."

        VARIATION   tmnxSyncIfTimingPTPCfgQltyLevel
            DESCRIPTION
                 "tmnxSyncIfTimingPTPCfgQltyLevel is only supported on Nokia
                  7750 c4 with an active CPM/SFM that supports PTP. Otherwise,
                  this object is not-implemented."

        VARIATION   tmnxSyncIfTimingPTPInUse
            DESCRIPTION
                 "tmnxSyncIfTimingPTPInUse is only supported on Nokia 7750 c4
                  with an active CPM/SFM that supports PTP. Otherwise, this
                  object is not-implemented."

        VARIATION   tmnxSyncIfTimingPTPQualified
            DESCRIPTION
                 "tmnxSyncIfTimingPTPQualified is only supported on Nokia 7750
                  c4 with an active CPM/SFM that supports PTP. Otherwise, this
                  object is not-implemented."

        VARIATION   tmnxSyncIfTimingPTPRxQltyLevel
            DESCRIPTION
                 "tmnxSyncIfTimingPTPRxQltyLevel is only supported on Nokia 7750
                  c4 with an active CPM/SFM that supports PTP. Otherwise, this
                  object is not-implemented."

        VARIATION   tmnxSyncIfTimingPTPState
            DESCRIPTION
                 "tmnxSyncIfTimingPTPState is only supported on Nokia 7750 c4
                  with an active CPM/SFM that supports PTP. Otherwise, this
                  object is not-implemented."

        VARIATION   tmnxSyncIfTimingRef1NationalUse
            ACCESS  not-implemented
            DESCRIPTION
                 "tmnxSyncIfTimingRef1NationalUse is not implemented on Nokia
                  7750 c4 in release 14.0."

        VARIATION   tmnxSyncIfTimingRef2NationalUse
            ACCESS  not-implemented
            DESCRIPTION
                 "tmnxSyncIfTimingRef2NationalUse is not implemented on Nokia
                  7750 c4 in release 14.0."

        VARIATION   tmnxSyncIfTimingRefOrder4
            DESCRIPTION
                 "tmnxSyncIfTimingRefOrder4 is only supported on Nokia 7750 c4
                  with an active CPM/SFM that supports PTP. Otherwise, this
                  object is not-implemented."

    ::= { tmnx7750c4AgentV14v0   6 }

--
-- 7750SR-12e CHASSIS CAPABILITIES
--
tmnx7750SR12eChassisV14v0         AGENT-CAPABILITIES
    PRODUCT-RELEASE "Nokia SROS"
    STATUS          current
    DESCRIPTION
         "Implementation of CHASSIS functions for Nokia 7750 SR-12e systems
          release 14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
           tmnxChassisFabricV11v0Group,
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  SR-12e with an active CPM/SFM that supports PTP. Otherwise,
                  this object is not-implemented."

        VARIATION   tSyncIfTimingAdmPTPCfgQltyLevel
            DESCRIPTION
                 "tSyncIfTimingAdmPTPCfgQltyLevel is only supported on Nokia
                  7750 SR-12e with an active CPM/SFM that supports PTP.
                  Otherwise, this object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 SR-12e in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 SR-12e in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750
                  SR-12e with an active CPM/SFM that supports PTP. Otherwise,
                  this object is not-implemented."

        VARIATION   tmnxCardAllowedTypes
            ACCESS  not-implemented
            DESCRIPTION
                 "tmnxCardAllowedTypes is not implemented on Nokia 7750 SR-12e
                  in release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 SR-12e in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  SR-12e in release 14.0.

                  tmnxChassisAdminLastSetTimer was obsoleted in release 12.0."

        VARIATION   tmnxChassisAdminMode
            SYNTAX  TmnxChassisMode {
                    -- modeA                (1)
                    -- modeB                (2)
                    -- modeC                (3)
                       modeD                (4)
                    }
            DESCRIPTION
                 "The only value supported for tmnxChassisAdminMode on Nokia
                  7750 SR-12e is 'modeD(4)'."

        VARIATION   tmnxChassisRowStatus
            ACCESS  read-only
            DESCRIPTION
                 "tmnxChassisRowStatus is implemented as read-only on Nokia 7750
                  SR-12e in release 14.0.

                  Row entries cannot be created by SNMP SET requests. Multiple
                  chassis's are not supported on Nokia 7750 SR-12e."

        VARIATION   tmnxCpmCardAllowedTypes
            ACCESS  not-implemented
            DESCRIPTION
                 "tmnxCpmCardAllowedTypes is not implemented on Nokia 7750
                  SR-12e in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 SR-12e in release 14.0.

                  Multiple CPM card types are not supported on Nokia 7750
                  SR-12e."

        VARIATION   tmnxEqBackdoorBusFailure
            ACCESS  not-implemented
            DESCRIPTION
                 "tmnxEqBackdoorBusFailure is not implemented on Nokia 7750
                  SR-12e in release 14.0.

                  This notification was made obsolete in the 2.1 release."

        VARIATION   tmnxEqCpuFailure
            ACCESS  not-implemented
            DESCRIPTION
                 "tmnxEqCpuFailure is not implemented on Nokia 7750 SR-12e in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 SR-12e in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  SR-12e with an active CPM/SFM that supports PTP. Otherwise,
                  this object is not-implemented."

        VARIATION   tmnxEqSyncIfTimingPTPAlarmClear
            DESCRIPTION
                 "tmnxEqSyncIfTimingPTPAlarmClear is only supported on Nokia
                  7750 SR-12e with an active CPM/SFM that supports PTP.
                  Otherwise, this object is not-implemented."

        VARIATION   tmnxEqSyncIfTimingPTPQuality
            DESCRIPTION
                 "tmnxEqSyncIfTimingPTPQuality is only supported on Nokia 7750
                  SR-12e with an active CPM/SFM that supports PTP. Otherwise,
                  this object is not-implemented."

        VARIATION   tmnxHwConfigChange
            ACCESS  not-implemented
            DESCRIPTION
                 "tmnxHwConfigChange is not implemented on Nokia 7750 SR-12e in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 SR-12e
                  in release 14.0."

        VARIATION   tmnxHwLastAlarmEvent
            DESCRIPTION
                 "tmnxHwLastAlarmEvent is not supported on Nokia 7750 SR-12e.
                  The value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 SR-12e in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  SR-12e in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 SR-12e in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7750 SR-12e in release 14.0."

        VARIATION   tmnxSyncIfTimingBITS2Alarm
            ACCESS  not-implemented
            DESCRIPTION
                 "tmnxSyncIfTimingBITS2Alarm is not implemented on Nokia 7750
                  SR-12e in release 14.0."

        VARIATION   tmnxSyncIfTimingBITS2InUse
            ACCESS  not-implemented
            DESCRIPTION
                 "tmnxSyncIfTimingBITS2InUse is not implemented on Nokia 7750
                  SR-12e in release 14.0."

        VARIATION   tmnxSyncIfTimingBITS2Qualified
            ACCESS  not-implemented
            DESCRIPTION
                 "tmnxSyncIfTimingBITS2Qualified is not implemented on Nokia
                  7750 SR-12e in release 14.0."

        VARIATION   tmnxSyncIfTimingBITS2RxQltyLevel
            ACCESS  not-implemented
            DESCRIPTION
                 "tmnxSyncIfTimingBITS2RxQltyLevel is not implemented on Nokia
                  7750 SR-12e in release 14.0."

        VARIATION   tmnxSyncIfTimingBITS2State
            ACCESS  not-implemented
            DESCRIPTION
                 "tmnxSyncIfTimingBITS2State is not implemented on Nokia 7750
                  SR-12e in release 14.0."

        VARIATION   tmnxSyncIfTimingPTPAdminStatus
            DESCRIPTION
                 "tmnxSyncIfTimingPTPAdminStatus is only supported on Nokia 7750
                  SR-12e with an active CPM/SFM that supports PTP. Otherwise,
                  this object is not-implemented."

        VARIATION   tmnxSyncIfTimingPTPAlarm
            DESCRIPTION
                 "tmnxSyncIfTimingPTPAlarm is only supported on Nokia 7750
                  SR-12e with an active CPM/SFM that supports PTP. Otherwise,
                  this object is not-implemented."

        VARIATION   tmnxSyncIfTimingPTPCfgQltyLevel
            DESCRIPTION
                 "tmnxSyncIfTimingPTPCfgQltyLevel is only supported on Nokia
                  7750 SR-12e with an active CPM/SFM that supports PTP.
                  Otherwise, this object is not-implemented."

        VARIATION   tmnxSyncIfTimingPTPInUse
            DESCRIPTION
                 "tmnxSyncIfTimingPTPInUse is only supported on Nokia 7750
                  SR-12e with an active CPM/SFM that supports PTP. Otherwise,
                  this object is not-implemented."

        VARIATION   tmnxSyncIfTimingPTPQualified
            DESCRIPTION
                 "tmnxSyncIfTimingPTPQualified is only supported on Nokia 7750
                  SR-12e with an active CPM/SFM that supports PTP. Otherwise,
                  this object is not-implemented."

        VARIATION   tmnxSyncIfTimingPTPRxQltyLevel
            DESCRIPTION
                 "tmnxSyncIfTimingPTPRxQltyLevel is only supported on Nokia 7750
                  SR-12e with an active CPM/SFM that supports PTP. Otherwise,
                  this object is not-implemented."

        VARIATION   tmnxSyncIfTimingPTPState
            DESCRIPTION
                 "tmnxSyncIfTimingPTPState is only supported on Nokia 7750
                  SR-12e with an active CPM/SFM that supports PTP. Otherwise,
                  this object is not-implemented."

        VARIATION   tmnxSyncIfTimingRef1NationalUse
            ACCESS  not-implemented
            DESCRIPTION
                 "tmnxSyncIfTimingRef1NationalUse is not implemented on Nokia
                  7750 SR-12e in release 14.0."

        VARIATION   tmnxSyncIfTimingRef2NationalUse
            ACCESS  not-implemented
            DESCRIPTION
                 "tmnxSyncIfTimingRef2NationalUse is not implemented on Nokia
                  7750 SR-12e in release 14.0."

        VARIATION   tmnxSyncIfTimingRefOrder4
            DESCRIPTION
                 "tmnxSyncIfTimingRefOrder4 is only supported on Nokia 7750
                  SR-12e with an active CPM/SFM that supports PTP. Otherwise,
                  this object is not-implemented."

    ::= { tmnx7750SR12eAgentV14v0   6 }

--
-- 7750SR-a4 CHASSIS CAPABILITIES
--
tmnx7750SRa4ChassisV14v0          AGENT-CAPABILITIES
    PRODUCT-RELEASE "Nokia SROS"
    STATUS          current
    DESCRIPTION
         "Implementation of CHASSIS functions for Nokia 7750 SR-a4 systems
          release 14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  SR-a4 with an active CPM/SFM that supports PTP. Otherwise,
                  this object is not-implemented."

        VARIATION   tSyncIfTimingAdmPTPCfgQltyLevel
            DESCRIPTION
                 "tSyncIfTimingAdmPTPCfgQltyLevel is only supported on Nokia
                  7750 SR-a4 with an active CPM/SFM that supports PTP.
                  Otherwise, this object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 SR-a4 in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 SR-a4 in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750
                  SR-a4 with an active CPM/SFM that supports PTP. Otherwise,
                  this object is not-implemented."

        VARIATION   tmnxCardAllowedTypes
            ACCESS  not-implemented
            DESCRIPTION
                 "tmnxCardAllowedTypes is not implemented on Nokia 7750 SR-a4 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 SR-a4 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  SR-a4 in release 14.0.

                  tmnxChassisAdminLastSetTimer was obsoleted in release 12.0."

        VARIATION   tmnxChassisPowerSupplyFanDir
            DESCRIPTION
                 "The tmnxChassisPowerSupplyFanDir object is only supported on
                  Nokia 7750 SR-a4."

        VARIATION   tmnxChassisRowStatus
            ACCESS  read-only
            DESCRIPTION
                 "tmnxChassisRowStatus is implemented as read-only on Nokia 7750
                  SR-a4 in release 14.0.

                  Row entries cannot be created by SNMP SET requests. Multiple
                  chassis's are not supported on Nokia 7750 SR-a4."

        VARIATION   tmnxCpmCardAllowedTypes
            ACCESS  not-implemented
            DESCRIPTION
                 "tmnxCpmCardAllowedTypes is not implemented on Nokia 7750 SR-a4
                  in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 SR-a4 in release 14.0.

                  Multiple CPM card types are not supported on Nokia 7750
                  SR-a4."

        VARIATION   tmnxEqBackdoorBusFailure
            ACCESS  not-implemented
            DESCRIPTION
                 "tmnxEqBackdoorBusFailure is not implemented on Nokia 7750
                  SR-a4 in release 14.0.

                  This notification was made obsolete in the 2.1 release."

        VARIATION   tmnxEqCpuFailure
            ACCESS  not-implemented
            DESCRIPTION
                 "tmnxEqCpuFailure is not implemented on Nokia 7750 SR-a4 in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 SR-a4 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  SR-a4 with an active CPM/SFM that supports PTP. Otherwise,
                  this object is not-implemented."

        VARIATION   tmnxEqSyncIfTimingPTPAlarmClear
            DESCRIPTION
                 "tmnxEqSyncIfTimingPTPAlarmClear is only supported on Nokia
                  7750 SR-a4 with an active CPM/SFM that supports PTP.
                  Otherwise, this object is not-implemented."

        VARIATION   tmnxEqSyncIfTimingPTPQuality
            DESCRIPTION
                 "tmnxEqSyncIfTimingPTPQuality is only supported on Nokia 7750
                  SR-a4 with an active CPM/SFM that supports PTP. Otherwise,
                  this object is not-implemented."

        VARIATION   tmnxHwConfigChange
            ACCESS  not-implemented
            DESCRIPTION
                 "tmnxHwConfigChange is not implemented on Nokia 7750 SR-a4 in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 SR-a4 in
                  release 14.0."

        VARIATION   tmnxHwLastAlarmEvent
            DESCRIPTION
                 "tmnxHwLastAlarmEvent is not supported on Nokia 7750 SR-a4. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 SR-a4 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  SR-a4 in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 SR-a4 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxPowerSupplyWrongFanDir
            DESCRIPTION
                 "The tmnxPowerSupplyWrongFanDir notification is only supported
                  on Nokia 7750 SR-a4."

        VARIATION   tmnxPowerSupplyWrongFanDirClear
            DESCRIPTION
                 "The tmnxPowerSupplyWrongFanDirClear notification is only
                  supported on Nokia 7750 SR-a4."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7750 SR-a4 in release 14.0."

        VARIATION   tmnxSyncIfTimingBITS2Alarm
            ACCESS  not-implemented
            DESCRIPTION
                 "tmnxSyncIfTimingBITS2Alarm is not implemented on Nokia 7750
                  SR-a4 in release 14.0."

        VARIATION   tmnxSyncIfTimingBITS2InUse
            ACCESS  not-implemented
            DESCRIPTION
                 "tmnxSyncIfTimingBITS2InUse is not implemented on Nokia 7750
                  SR-a4 in release 14.0."

        VARIATION   tmnxSyncIfTimingBITS2Qualified
            ACCESS  not-implemented
            DESCRIPTION
                 "tmnxSyncIfTimingBITS2Qualified is not implemented on Nokia
                  7750 SR-a4 in release 14.0."

        VARIATION   tmnxSyncIfTimingBITS2RxQltyLevel
            ACCESS  not-implemented
            DESCRIPTION
                 "tmnxSyncIfTimingBITS2RxQltyLevel is not implemented on Nokia
                  7750 SR-a4 in release 14.0."

        VARIATION   tmnxSyncIfTimingBITS2State
            ACCESS  not-implemented
            DESCRIPTION
                 "tmnxSyncIfTimingBITS2State is not implemented on Nokia 7750
                  SR-a4 in release 14.0."

        VARIATION   tmnxSyncIfTimingPTPAdminStatus
            DESCRIPTION
                 "tmnxSyncIfTimingPTPAdminStatus is only supported on Nokia 7750
                  SR-a4 with an active CPM/SFM that supports PTP. Otherwise,
                  this object is not-implemented."

        VARIATION   tmnxSyncIfTimingPTPAlarm
            DESCRIPTION
                 "tmnxSyncIfTimingPTPAlarm is only supported on Nokia 7750 SR-a4
                  with an active CPM/SFM that supports PTP. Otherwise, this
                  object is not-implemented."

        VARIATION   tmnxSyncIfTimingPTPCfgQltyLevel
            DESCRIPTION
                 "tmnxSyncIfTimingPTPCfgQltyLevel is only supported on Nokia
                  7750 SR-a4 with an active CPM/SFM that supports PTP.
                  Otherwise, this object is not-implemented."

        VARIATION   tmnxSyncIfTimingPTPInUse
            DESCRIPTION
                 "tmnxSyncIfTimingPTPInUse is only supported on Nokia 7750 SR-a4
                  with an active CPM/SFM that supports PTP. Otherwise, this
                  object is not-implemented."

        VARIATION   tmnxSyncIfTimingPTPQualified
            DESCRIPTION
                 "tmnxSyncIfTimingPTPQualified is only supported on Nokia 7750
                  SR-a4 with an active CPM/SFM that supports PTP. Otherwise,
                  this object is not-implemented."

        VARIATION   tmnxSyncIfTimingPTPRxQltyLevel
            DESCRIPTION
                 "tmnxSyncIfTimingPTPRxQltyLevel is only supported on Nokia 7750
                  SR-a4 with an active CPM/SFM that supports PTP. Otherwise,
                  this object is not-implemented."

        VARIATION   tmnxSyncIfTimingPTPState
            DESCRIPTION
                 "tmnxSyncIfTimingPTPState is only supported on Nokia 7750 SR-a4
                  with an active CPM/SFM that supports PTP. Otherwise, this
                  object is not-implemented."

        VARIATION   tmnxSyncIfTimingRef1NationalUse
            ACCESS  not-implemented
            DESCRIPTION
                 "tmnxSyncIfTimingRef1NationalUse is not implemented on Nokia
                  7750 SR-a4 in release 14.0."

        VARIATION   tmnxSyncIfTimingRef2NationalUse
            ACCESS  not-implemented
            DESCRIPTION
                 "tmnxSyncIfTimingRef2NationalUse is not implemented on Nokia
                  7750 SR-a4 in release 14.0."

        VARIATION   tmnxSyncIfTimingRefOrder4
            DESCRIPTION
                 "tmnxSyncIfTimingRefOrder4 is only supported on Nokia 7750
                  SR-a4 with an active CPM/SFM that supports PTP. Otherwise,
                  this object is not-implemented."

    ::= { tmnx7750SRa4AgentV14v0   6 }

--
-- 7750SR-a8 CHASSIS CAPABILITIES
--
tmnx7750SRa8ChassisV14v0          AGENT-CAPABILITIES
    PRODUCT-RELEASE "Nokia SROS"
    STATUS          current
    DESCRIPTION
         "Implementation of CHASSIS functions for Nokia 7750 SR-a8 systems
          release 14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  SR-a8 with an active CPM/SFM that supports PTP. Otherwise,
                  this object is not-implemented."

        VARIATION   tSyncIfTimingAdmPTPCfgQltyLevel
            DESCRIPTION
                 "tSyncIfTimingAdmPTPCfgQltyLevel is only supported on Nokia
                  7750 SR-a8 with an active CPM/SFM that supports PTP.
                  Otherwise, this object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 SR-a8 in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 SR-a8 in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750
                  SR-a8 with an active CPM/SFM that supports PTP. Otherwise,
                  this object is not-implemented."

        VARIATION   tmnxCardAllowedTypes
            ACCESS  not-implemented
            DESCRIPTION
                 "tmnxCardAllowedTypes is not implemented on Nokia 7750 SR-a8 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 SR-a8 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  SR-a8 in release 14.0.

                  tmnxChassisAdminLastSetTimer was obsoleted in release 12.0."

        VARIATION   tmnxChassisPowerSupplyFanDir
            DESCRIPTION
                 "The tmnxChassisPowerSupplyFanDir object is only supported on
                  Nokia 7750 SR-a8."

        VARIATION   tmnxChassisRowStatus
            ACCESS  read-only
            DESCRIPTION
                 "tmnxChassisRowStatus is implemented as read-only on Nokia 7750
                  SR-a8 in release 14.0.

                  Row entries cannot be created by SNMP SET requests. Multiple
                  chassis's are not supported on Nokia 7750 SR-a8."

        VARIATION   tmnxCpmCardAllowedTypes
            ACCESS  not-implemented
            DESCRIPTION
                 "tmnxCpmCardAllowedTypes is not implemented on Nokia 7750 SR-a8
                  in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 SR-a8 in release 14.0.

                  Multiple CPM card types are not supported on Nokia 7750
                  SR-a8."

        VARIATION   tmnxEqBackdoorBusFailure
            ACCESS  not-implemented
            DESCRIPTION
                 "tmnxEqBackdoorBusFailure is not implemented on Nokia 7750
                  SR-a8 in release 14.0.

                  This notification was made obsolete in the 2.1 release."

        VARIATION   tmnxEqCpuFailure
            ACCESS  not-implemented
            DESCRIPTION
                 "tmnxEqCpuFailure is not implemented on Nokia 7750 SR-a8 in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 SR-a8 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  SR-a8 with an active CPM/SFM that supports PTP. Otherwise,
                  this object is not-implemented."

        VARIATION   tmnxEqSyncIfTimingPTPAlarmClear
            DESCRIPTION
                 "tmnxEqSyncIfTimingPTPAlarmClear is only supported on Nokia
                  7750 SR-a8 with an active CPM/SFM that supports PTP.
                  Otherwise, this object is not-implemented."

        VARIATION   tmnxEqSyncIfTimingPTPQuality
            DESCRIPTION
                 "tmnxEqSyncIfTimingPTPQuality is only supported on Nokia 7750
                  SR-a8 with an active CPM/SFM that supports PTP. Otherwise,
                  this object is not-implemented."

        VARIATION   tmnxHwConfigChange
            ACCESS  not-implemented
            DESCRIPTION
                 "tmnxHwConfigChange is not implemented on Nokia 7750 SR-a8 in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 SR-a8 in
                  release 14.0."

        VARIATION   tmnxHwLastAlarmEvent
            DESCRIPTION
                 "tmnxHwLastAlarmEvent is not supported on Nokia 7750 SR-a8. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 SR-a8 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  SR-a8 in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 SR-a8 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxPowerSupplyWrongFanDir
            DESCRIPTION
                 "The tmnxPowerSupplyWrongFanDir notification is only supported
                  on Nokia 7750 SR-a8."

        VARIATION   tmnxPowerSupplyWrongFanDirClear
            DESCRIPTION
                 "The tmnxPowerSupplyWrongFanDirClear notification is only
                  supported on Nokia 7750 SR-a8."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7750 SR-a8 in release 14.0."

        VARIATION   tmnxSyncIfTimingBITS2Alarm
            ACCESS  not-implemented
            DESCRIPTION
                 "tmnxSyncIfTimingBITS2Alarm is not implemented on Nokia 7750
                  SR-a8 in release 14.0."

        VARIATION   tmnxSyncIfTimingBITS2InUse
            ACCESS  not-implemented
            DESCRIPTION
                 "tmnxSyncIfTimingBITS2InUse is not implemented on Nokia 7750
                  SR-a8 in release 14.0."

        VARIATION   tmnxSyncIfTimingBITS2Qualified
            ACCESS  not-implemented
            DESCRIPTION
                 "tmnxSyncIfTimingBITS2Qualified is not implemented on Nokia
                  7750 SR-a8 in release 14.0."

        VARIATION   tmnxSyncIfTimingBITS2RxQltyLevel
            ACCESS  not-implemented
            DESCRIPTION
                 "tmnxSyncIfTimingBITS2RxQltyLevel is not implemented on Nokia
                  7750 SR-a8 in release 14.0."

        VARIATION   tmnxSyncIfTimingBITS2State
            ACCESS  not-implemented
            DESCRIPTION
                 "tmnxSyncIfTimingBITS2State is not implemented on Nokia 7750
                  SR-a8 in release 14.0."

        VARIATION   tmnxSyncIfTimingPTPAdminStatus
            DESCRIPTION
                 "tmnxSyncIfTimingPTPAdminStatus is only supported on Nokia 7750
                  SR-a8 with an active CPM/SFM that supports PTP. Otherwise,
                  this object is not-implemented."

        VARIATION   tmnxSyncIfTimingPTPAlarm
            DESCRIPTION
                 "tmnxSyncIfTimingPTPAlarm is only supported on Nokia 7750 SR-a8
                  with an active CPM/SFM that supports PTP. Otherwise, this
                  object is not-implemented."

        VARIATION   tmnxSyncIfTimingPTPCfgQltyLevel
            DESCRIPTION
                 "tmnxSyncIfTimingPTPCfgQltyLevel is only supported on Nokia
                  7750 SR-a8 with an active CPM/SFM that supports PTP.
                  Otherwise, this object is not-implemented."

        VARIATION   tmnxSyncIfTimingPTPInUse
            DESCRIPTION
                 "tmnxSyncIfTimingPTPInUse is only supported on Nokia 7750 SR-a8
                  with an active CPM/SFM that supports PTP. Otherwise, this
                  object is not-implemented."

        VARIATION   tmnxSyncIfTimingPTPQualified
            DESCRIPTION
                 "tmnxSyncIfTimingPTPQualified is only supported on Nokia 7750
                  SR-a8 with an active CPM/SFM that supports PTP. Otherwise,
                  this object is not-implemented."

        VARIATION   tmnxSyncIfTimingPTPRxQltyLevel
            DESCRIPTION
                 "tmnxSyncIfTimingPTPRxQltyLevel is only supported on Nokia 7750
                  SR-a8 with an active CPM/SFM that supports PTP. Otherwise,
                  this object is not-implemented."

        VARIATION   tmnxSyncIfTimingPTPState
            DESCRIPTION
                 "tmnxSyncIfTimingPTPState is only supported on Nokia 7750 SR-a8
                  with an active CPM/SFM that supports PTP. Otherwise, this
                  object is not-implemented."

        VARIATION   tmnxSyncIfTimingRef1NationalUse
            ACCESS  not-implemented
            DESCRIPTION
                 "tmnxSyncIfTimingRef1NationalUse is not implemented on Nokia
                  7750 SR-a8 in release 14.0."

        VARIATION   tmnxSyncIfTimingRef2NationalUse
            ACCESS  not-implemented
            DESCRIPTION
                 "tmnxSyncIfTimingRef2NationalUse is not implemented on Nokia
                  7750 SR-a8 in release 14.0."

        VARIATION   tmnxSyncIfTimingRefOrder4
            DESCRIPTION
                 "tmnxSyncIfTimingRefOrder4 is only supported on Nokia 7750
                  SR-a8 with an active CPM/SFM that supports PTP. Otherwise,
                  this object is not-implemented."

    ::= { tmnx7750SRa8AgentV14v0   6 }

--
-- 7750SR-1e CHASSIS CAPABILITIES
--
tmnx7750SR1eChassisV14v0          AGENT-CAPABILITIES
    PRODUCT-RELEASE "Nokia SROS"
    STATUS          current
    DESCRIPTION
         "Implementation of CHASSIS functions for Nokia 7750 SR-1e systems
          release 14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  SR-1e with an active CPM/SFM that supports PTP. Otherwise,
                  this object is not-implemented."

        VARIATION   tSyncIfTimingAdmPTPCfgQltyLevel
            DESCRIPTION
                 "tSyncIfTimingAdmPTPCfgQltyLevel is only supported on Nokia
                  7750 SR-1e with an active CPM/SFM that supports PTP.
                  Otherwise, this object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 SR-1e in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 SR-1e in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750
                  SR-1e with an active CPM/SFM that supports PTP. Otherwise,
                  this object is not-implemented."

        VARIATION   tmnxCardAllowedTypes
            ACCESS  not-implemented
            DESCRIPTION
                 "tmnxCardAllowedTypes is not implemented on Nokia 7750 SR-1e in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 SR-1e in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  SR-1e in release 14.0.

                  tmnxChassisAdminLastSetTimer was obsoleted in release 12.0."

        VARIATION   tmnxChassisPowerSupplyFanDir
            DESCRIPTION
                 "The tmnxChassisPowerSupplyFanDir object is only supported on
                  Nokia 7750 SR-1e."

        VARIATION   tmnxChassisRowStatus
            ACCESS  read-only
            DESCRIPTION
                 "tmnxChassisRowStatus is implemented as read-only on Nokia 7750
                  SR-1e in release 14.0.

                  Row entries cannot be created by SNMP SET requests. Multiple
                  chassis's are not supported on Nokia 7750 SR-1e."

        VARIATION   tmnxCpmCardAllowedTypes
            ACCESS  not-implemented
            DESCRIPTION
                 "tmnxCpmCardAllowedTypes is not implemented on Nokia 7750 SR-1e
                  in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 SR-1e in release 14.0.

                  Multiple CPM card types are not supported on Nokia 7750
                  SR-1e."

        VARIATION   tmnxEqBackdoorBusFailure
            ACCESS  not-implemented
            DESCRIPTION
                 "tmnxEqBackdoorBusFailure is not implemented on Nokia 7750
                  SR-1e in release 14.0.

                  This notification was made obsolete in the 2.1 release."

        VARIATION   tmnxEqCpuFailure
            ACCESS  not-implemented
            DESCRIPTION
                 "tmnxEqCpuFailure is not implemented on Nokia 7750 SR-1e in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 SR-1e in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  SR-1e with an active CPM/SFM that supports PTP. Otherwise,
                  this object is not-implemented."

        VARIATION   tmnxEqSyncIfTimingPTPAlarmClear
            DESCRIPTION
                 "tmnxEqSyncIfTimingPTPAlarmClear is only supported on Nokia
                  7750 SR-1e with an active CPM/SFM that supports PTP.
                  Otherwise, this object is not-implemented."

        VARIATION   tmnxEqSyncIfTimingPTPQuality
            DESCRIPTION
                 "tmnxEqSyncIfTimingPTPQuality is only supported on Nokia 7750
                  SR-1e with an active CPM/SFM that supports PTP. Otherwise,
                  this object is not-implemented."

        VARIATION   tmnxHwConfigChange
            ACCESS  not-implemented
            DESCRIPTION
                 "tmnxHwConfigChange is not implemented on Nokia 7750 SR-1e in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 SR-1e in
                  release 14.0."

        VARIATION   tmnxHwLastAlarmEvent
            DESCRIPTION
                 "tmnxHwLastAlarmEvent is not supported on Nokia 7750 SR-1e. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 SR-1e in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  SR-1e in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 SR-1e in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxPowerSupplyWrongFanDir
            DESCRIPTION
                 "The tmnxPowerSupplyWrongFanDir notification is only supported
                  on Nokia 7750 SR-1e."

        VARIATION   tmnxPowerSupplyWrongFanDirClear
            DESCRIPTION
                 "The tmnxPowerSupplyWrongFanDirClear notification is only
                  supported on Nokia 7750 SR-1e."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            DESCRIPTION
                 "tmnxSyncIfTimingBITS2AdminStatus on Nokia 7750 SR-1e refers to
                  the BITS port on CCM-B. On the extension chassis of an XRS-40
                  platform, tmnxSyncIfTimingBITS2AdminStatus refers to the BITS
                  port on CCM-D."

        VARIATION   tmnxSyncIfTimingBITS2Alarm
            DESCRIPTION
                 "tmnxSyncIfTimingBITS2Alarm on Nokia 7750 SR-1e refers to the
                  BITS port on CCM-B. On the extension chassis of an XRS-40
                  platform, tmnxSyncIfTimingBITS2Alarm refers to the BITS port
                  on CCM-D."

        VARIATION   tmnxSyncIfTimingBITS2InUse
            DESCRIPTION
                 "tmnxSyncIfTimingBITS2InUse on Nokia 7750 SR-1e refers to the
                  BITS port on CCM-B. On the extension chassis of an XRS-40
                  platform, tmnxSyncIfTimingBITS2InUse refers to the BITS port
                  on CCM-D."

        VARIATION   tmnxSyncIfTimingBITS2Qualified
            DESCRIPTION
                 "tmnxSyncIfTimingBITS2Qualified on Nokia 7750 SR-1e refers to
                  the BITS port on CCM-B. On the extension chassis of an XRS-40
                  platform, tmnxSyncIfTimingBITS2Qualified refers to the BITS
                  port on CCM-D."

        VARIATION   tmnxSyncIfTimingBITS2RxQltyLevel
            DESCRIPTION
                 "tmnxSyncIfTimingBITS2RxQltyLevel on Nokia 7750 SR-1e refers to
                  the BITS port on CCM-B. On the extension chassis of an XRS-40
                  platform, tmnxSyncIfTimingBITS2RxQltyLevel refers to the BITS
                  port on CCM-D."

        VARIATION   tmnxSyncIfTimingBITS2State
            DESCRIPTION
                 "tmnxSyncIfTimingBITS2State on Nokia 7750 SR-1e refers to the
                  BITS port on CCM-B. On the extension chassis of an XRS-40
                  platform, tmnxSyncIfTimingBITS2State refers to the BITS port
                  on CCM-D."

        VARIATION   tmnxSyncIfTimingPTPAdminStatus
            DESCRIPTION
                 "tmnxSyncIfTimingPTPAdminStatus is only supported on Nokia 7750
                  SR-1e with an active CPM/SFM that supports PTP. Otherwise,
                  this object is not-implemented."

        VARIATION   tmnxSyncIfTimingPTPAlarm
            DESCRIPTION
                 "tmnxSyncIfTimingPTPAlarm is only supported on Nokia 7750 SR-1e
                  with an active CPM/SFM that supports PTP. Otherwise, this
                  object is not-implemented."

        VARIATION   tmnxSyncIfTimingPTPCfgQltyLevel
            DESCRIPTION
                 "tmnxSyncIfTimingPTPCfgQltyLevel is only supported on Nokia
                  7750 SR-1e with an active CPM/SFM that supports PTP.
                  Otherwise, this object is not-implemented."

        VARIATION   tmnxSyncIfTimingPTPInUse
            DESCRIPTION
                 "tmnxSyncIfTimingPTPInUse is only supported on Nokia 7750 SR-1e
                  with an active CPM/SFM that supports PTP. Otherwise, this
                  object is not-implemented."

        VARIATION   tmnxSyncIfTimingPTPQualified
            DESCRIPTION
                 "tmnxSyncIfTimingPTPQualified is only supported on Nokia 7750
                  SR-1e with an active CPM/SFM that supports PTP. Otherwise,
                  this object is not-implemented."

        VARIATION   tmnxSyncIfTimingPTPRxQltyLevel
            DESCRIPTION
                 "tmnxSyncIfTimingPTPRxQltyLevel is only supported on Nokia 7750
                  SR-1e with an active CPM/SFM that supports PTP. Otherwise,
                  this object is not-implemented."

        VARIATION   tmnxSyncIfTimingPTPState
            DESCRIPTION
                 "tmnxSyncIfTimingPTPState is only supported on Nokia 7750 SR-1e
                  with an active CPM/SFM that supports PTP. Otherwise, this
                  object is not-implemented."

        VARIATION   tmnxSyncIfTimingRef1NationalUse
            ACCESS  not-implemented
            DESCRIPTION
                 "tmnxSyncIfTimingRef1NationalUse is not implemented on Nokia
                  7750 SR-1e in release 14.0."

        VARIATION   tmnxSyncIfTimingRef2NationalUse
            ACCESS  not-implemented
            DESCRIPTION
                 "tmnxSyncIfTimingRef2NationalUse is not implemented on Nokia
                  7750 SR-1e in release 14.0."

        VARIATION   tmnxSyncIfTimingRefOrder4
            DESCRIPTION
                 "tmnxSyncIfTimingRefOrder4 is only supported on Nokia 7750
                  SR-1e with an active CPM/SFM that supports PTP. Otherwise,
                  this object is not-implemented."

    ::= { tmnx7750SR1eAgentV14v0   6 }

--
-- 7750SR-2e CHASSIS CAPABILITIES
--
tmnx7750SR2eChassisV14v0          AGENT-CAPABILITIES
    PRODUCT-RELEASE "Nokia SROS"
    STATUS          current
    DESCRIPTION
         "Implementation of CHASSIS functions for Nokia 7750 SR-2e systems
          release 14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  SR-2e with an active CPM/SFM that supports PTP. Otherwise,
                  this object is not-implemented."

        VARIATION   tSyncIfTimingAdmPTPCfgQltyLevel
            DESCRIPTION
                 "tSyncIfTimingAdmPTPCfgQltyLevel is only supported on Nokia
                  7750 SR-2e with an active CPM/SFM that supports PTP.
                  Otherwise, this object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 SR-2e in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 SR-2e in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750
                  SR-2e with an active CPM/SFM that supports PTP. Otherwise,
                  this object is not-implemented."

        VARIATION   tmnxCardAllowedTypes
            ACCESS  not-implemented
            DESCRIPTION
                 "tmnxCardAllowedTypes is not implemented on Nokia 7750 SR-2e in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 SR-2e in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  SR-2e in release 14.0.

                  tmnxChassisAdminLastSetTimer was obsoleted in release 12.0."

        VARIATION   tmnxChassisPowerSupplyFanDir
            DESCRIPTION
                 "The tmnxChassisPowerSupplyFanDir object is only supported on
                  Nokia 7750 SR-2e."

        VARIATION   tmnxChassisRowStatus
            ACCESS  read-only
            DESCRIPTION
                 "tmnxChassisRowStatus is implemented as read-only on Nokia 7750
                  SR-2e in release 14.0.

                  Row entries cannot be created by SNMP SET requests. Multiple
                  chassis's are not supported on Nokia 7750 SR-2e."

        VARIATION   tmnxCpmCardAllowedTypes
            ACCESS  not-implemented
            DESCRIPTION
                 "tmnxCpmCardAllowedTypes is not implemented on Nokia 7750 SR-2e
                  in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 SR-2e in release 14.0.

                  Multiple CPM card types are not supported on Nokia 7750
                  SR-2e."

        VARIATION   tmnxEqBackdoorBusFailure
            ACCESS  not-implemented
            DESCRIPTION
                 "tmnxEqBackdoorBusFailure is not implemented on Nokia 7750
                  SR-2e in release 14.0.

                  This notification was made obsolete in the 2.1 release."

        VARIATION   tmnxEqCpuFailure
            ACCESS  not-implemented
            DESCRIPTION
                 "tmnxEqCpuFailure is not implemented on Nokia 7750 SR-2e in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 SR-2e in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  SR-2e with an active CPM/SFM that supports PTP. Otherwise,
                  this object is not-implemented."

        VARIATION   tmnxEqSyncIfTimingPTPAlarmClear
            DESCRIPTION
                 "tmnxEqSyncIfTimingPTPAlarmClear is only supported on Nokia
                  7750 SR-2e with an active CPM/SFM that supports PTP.
                  Otherwise, this object is not-implemented."

        VARIATION   tmnxEqSyncIfTimingPTPQuality
            DESCRIPTION
                 "tmnxEqSyncIfTimingPTPQuality is only supported on Nokia 7750
                  SR-2e with an active CPM/SFM that supports PTP. Otherwise,
                  this object is not-implemented."

        VARIATION   tmnxHwConfigChange
            ACCESS  not-implemented
            DESCRIPTION
                 "tmnxHwConfigChange is not implemented on Nokia 7750 SR-2e in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 SR-2e in
                  release 14.0."

        VARIATION   tmnxHwLastAlarmEvent
            DESCRIPTION
                 "tmnxHwLastAlarmEvent is not supported on Nokia 7750 SR-2e. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 SR-2e in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  SR-2e in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 SR-2e in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxPowerSupplyWrongFanDir
            DESCRIPTION
                 "The tmnxPowerSupplyWrongFanDir notification is only supported
                  on Nokia 7750 SR-2e."

        VARIATION   tmnxPowerSupplyWrongFanDirClear
            DESCRIPTION
                 "The tmnxPowerSupplyWrongFanDirClear notification is only
                  supported on Nokia 7750 SR-2e."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            DESCRIPTION
                 "tmnxSyncIfTimingBITS2AdminStatus on Nokia 7750 SR-2e refers to
                  the BITS port on CCM-B. On the extension chassis of an XRS-40
                  platform, tmnxSyncIfTimingBITS2AdminStatus refers to the BITS
                  port on CCM-D."

        VARIATION   tmnxSyncIfTimingBITS2Alarm
            DESCRIPTION
                 "tmnxSyncIfTimingBITS2Alarm on Nokia 7750 SR-2e refers to the
                  BITS port on CCM-B. On the extension chassis of an XRS-40
                  platform, tmnxSyncIfTimingBITS2Alarm refers to the BITS port
                  on CCM-D."

        VARIATION   tmnxSyncIfTimingBITS2InUse
            DESCRIPTION
                 "tmnxSyncIfTimingBITS2InUse on Nokia 7750 SR-2e refers to the
                  BITS port on CCM-B. On the extension chassis of an XRS-40
                  platform, tmnxSyncIfTimingBITS2InUse refers to the BITS port
                  on CCM-D."

        VARIATION   tmnxSyncIfTimingBITS2Qualified
            DESCRIPTION
                 "tmnxSyncIfTimingBITS2Qualified on Nokia 7750 SR-2e refers to
                  the BITS port on CCM-B. On the extension chassis of an XRS-40
                  platform, tmnxSyncIfTimingBITS2Qualified refers to the BITS
                  port on CCM-D."

        VARIATION   tmnxSyncIfTimingBITS2RxQltyLevel
            DESCRIPTION
                 "tmnxSyncIfTimingBITS2RxQltyLevel on Nokia 7750 SR-2e refers to
                  the BITS port on CCM-B. On the extension chassis of an XRS-40
                  platform, tmnxSyncIfTimingBITS2RxQltyLevel refers to the BITS
                  port on CCM-D."

        VARIATION   tmnxSyncIfTimingBITS2State
            DESCRIPTION
                 "tmnxSyncIfTimingBITS2State on Nokia 7750 SR-2e refers to the
                  BITS port on CCM-B. On the extension chassis of an XRS-40
                  platform, tmnxSyncIfTimingBITS2State refers to the BITS port
                  on CCM-D."

        VARIATION   tmnxSyncIfTimingPTPAdminStatus
            DESCRIPTION
                 "tmnxSyncIfTimingPTPAdminStatus is only supported on Nokia 7750
                  SR-2e with an active CPM/SFM that supports PTP. Otherwise,
                  this object is not-implemented."

        VARIATION   tmnxSyncIfTimingPTPAlarm
            DESCRIPTION
                 "tmnxSyncIfTimingPTPAlarm is only supported on Nokia 7750 SR-2e
                  with an active CPM/SFM that supports PTP. Otherwise, this
                  object is not-implemented."

        VARIATION   tmnxSyncIfTimingPTPCfgQltyLevel
            DESCRIPTION
                 "tmnxSyncIfTimingPTPCfgQltyLevel is only supported on Nokia
                  7750 SR-2e with an active CPM/SFM that supports PTP.
                  Otherwise, this object is not-implemented."

        VARIATION   tmnxSyncIfTimingPTPInUse
            DESCRIPTION
                 "tmnxSyncIfTimingPTPInUse is only supported on Nokia 7750 SR-2e
                  with an active CPM/SFM that supports PTP. Otherwise, this
                  object is not-implemented."

        VARIATION   tmnxSyncIfTimingPTPQualified
            DESCRIPTION
                 "tmnxSyncIfTimingPTPQualified is only supported on Nokia 7750
                  SR-2e with an active CPM/SFM that supports PTP. Otherwise,
                  this object is not-implemented."

        VARIATION   tmnxSyncIfTimingPTPRxQltyLevel
            DESCRIPTION
                 "tmnxSyncIfTimingPTPRxQltyLevel is only supported on Nokia 7750
                  SR-2e with an active CPM/SFM that supports PTP. Otherwise,
                  this object is not-implemented."

        VARIATION   tmnxSyncIfTimingPTPState
            DESCRIPTION
                 "tmnxSyncIfTimingPTPState is only supported on Nokia 7750 SR-2e
                  with an active CPM/SFM that supports PTP. Otherwise, this
                  object is not-implemented."

        VARIATION   tmnxSyncIfTimingRef1NationalUse
            ACCESS  not-implemented
            DESCRIPTION
                 "tmnxSyncIfTimingRef1NationalUse is not implemented on Nokia
                  7750 SR-2e in release 14.0."

        VARIATION   tmnxSyncIfTimingRef2NationalUse
            ACCESS  not-implemented
            DESCRIPTION
                 "tmnxSyncIfTimingRef2NationalUse is not implemented on Nokia
                  7750 SR-2e in release 14.0."

        VARIATION   tmnxSyncIfTimingRefOrder4
            DESCRIPTION
                 "tmnxSyncIfTimingRefOrder4 is only supported on Nokia 7750
                  SR-2e with an active CPM/SFM that supports PTP. Otherwise,
                  this object is not-implemented."

    ::= { tmnx7750SR2eAgentV14v0   6 }

--
-- 7750SR-3e CHASSIS CAPABILITIES
--
tmnx7750SR3eChassisV14v0          AGENT-CAPABILITIES
    PRODUCT-RELEASE "Nokia SROS"
    STATUS          current
    DESCRIPTION
         "Implementation of CHASSIS functions for Nokia 7750 SR-3e systems
          release 14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
           tmnxCardResetOnRecoverErGrp,
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
-- EXCLUDE tmnxFPQGrpV10v0R4Group
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
           tmnxSyncIfTimingV9v0Group,
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7750
                  SR-3e with an active CPM/SFM that supports PTP. Otherwise,
                  this object is not-implemented."

        VARIATION   tSyncIfTimingAdmPTPCfgQltyLevel
            DESCRIPTION
                 "tSyncIfTimingAdmPTPCfgQltyLevel is only supported on Nokia
                  7750 SR-3e with an active CPM/SFM that supports PTP.
                  Otherwise, this object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7750 SR-3e in release 14.0."

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7750 SR-3e in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7750
                  SR-3e with an active CPM/SFM that supports PTP. Otherwise,
                  this object is not-implemented."

        VARIATION   tmnxCardAllowedTypes
            ACCESS  not-implemented
            DESCRIPTION
                 "tmnxCardAllowedTypes is not implemented on Nokia 7750 SR-3e in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7750 SR-3e in release 14.0.

                  tmnxChassisAdminLastSetTimeout was obsoleted in release
                  12.0."

        VARIATION   tmnxChassisAdminLastSetTimer
            ACCESS  not-implemented
            DESCRIPTION
                 "tmnxChassisAdminLastSetTimer is not implemented on Nokia 7750
                  SR-3e in release 14.0.

                  tmnxChassisAdminLastSetTimer was obsoleted in release 12.0."

        VARIATION   tmnxChassisRowStatus
            ACCESS  read-only
            DESCRIPTION
                 "tmnxChassisRowStatus is implemented as read-only on Nokia 7750
                  SR-3e in release 14.0.

                  Row entries cannot be created by SNMP SET requests. Multiple
                  chassis's are not supported on Nokia 7750 SR-3e."

        VARIATION   tmnxCpmCardAllowedTypes
            ACCESS  not-implemented
            DESCRIPTION
                 "tmnxCpmCardAllowedTypes is not implemented on Nokia 7750 SR-3e
                  in release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7750 SR-3e in release 14.0.

                  Multiple CPM card types are not supported on Nokia 7750
                  SR-3e."

        VARIATION   tmnxEqBackdoorBusFailure
            ACCESS  not-implemented
            DESCRIPTION
                 "tmnxEqBackdoorBusFailure is not implemented on Nokia 7750
                  SR-3e in release 14.0.

                  This notification was made obsolete in the 2.1 release."

        VARIATION   tmnxEqCpuFailure
            ACCESS  not-implemented
            DESCRIPTION
                 "tmnxEqCpuFailure is not implemented on Nokia 7750 SR-3e in
                  release 14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7750 SR-3e in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7750
                  SR-3e with an active CPM/SFM that supports PTP. Otherwise,
                  this object is not-implemented."

        VARIATION   tmnxEqSyncIfTimingPTPAlarmClear
            DESCRIPTION
                 "tmnxEqSyncIfTimingPTPAlarmClear is only supported on Nokia
                  7750 SR-3e with an active CPM/SFM that supports PTP.
                  Otherwise, this object is not-implemented."

        VARIATION   tmnxEqSyncIfTimingPTPQuality
            DESCRIPTION
                 "tmnxEqSyncIfTimingPTPQuality is only supported on Nokia 7750
                  SR-3e with an active CPM/SFM that supports PTP. Otherwise,
                  this object is not-implemented."

        VARIATION   tmnxHwConfigChange
            ACCESS  not-implemented
            DESCRIPTION
                 "tmnxHwConfigChange is not implemented on Nokia 7750 SR-3e in
                  release 14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7750 SR-3e in
                  release 14.0."

        VARIATION   tmnxHwLastAlarmEvent
            DESCRIPTION
                 "tmnxHwLastAlarmEvent is not supported on Nokia 7750 SR-3e. The
                  value of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxIPsecIsaGrpAdminState
            SYNTAX  INTEGER {
                    -- noop                 (1)
                       inService            (2),
                       outOfService         (3)
                    }
            DESCRIPTION
                 "tmnxIPsecIsaGrpAdminState supports only the values 'inService
                  (2)' and 'outOfService (3)'."

        VARIATION   tmnxIPsecIsaGrpIsaChassis
            SYNTAX  TmnxChassisIndex (1)
            DESCRIPTION
                 "The tmnxIPsecIsaGrpIsaChassis supports only the value 1. An
                  attempt to set it to any other value results in a 'wrongValue'
                  error."

        VARIATION   tmnxIPsecIsaGrpRowStatus
            SYNTAX  RowStatus {
                       active               (1),
                    -- notInService         (2)
                    -- notReady             (3)
                       createAndGo          (4),
                    -- createAndWait        (5)
                       destroy              (6)
                    }
            DESCRIPTION
                 "tmnxIPsecIsaGrpRowStatus supports only 'active (1)',
                  'createAndGo (4)', and 'destroy (6)'."

        VARIATION   tmnxMDAAllowedTypes
            ACCESS  not-implemented
            DESCRIPTION
                 "tmnxMDAAllowedTypes is not implemented on Nokia 7750 SR-3e in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7750
                  SR-3e in release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7750 SR-3e in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            DESCRIPTION
                 "tmnxSyncIfTimingBITS2AdminStatus on Nokia 7750 SR-3e refers to
                  the BITS port on CCM-B. On the extension chassis of an XRS-40
                  platform, tmnxSyncIfTimingBITS2AdminStatus refers to the BITS
                  port on CCM-D."

        VARIATION   tmnxSyncIfTimingBITS2Alarm
            DESCRIPTION
                 "tmnxSyncIfTimingBITS2Alarm on Nokia 7750 SR-3e refers to the
                  BITS port on CCM-B. On the extension chassis of an XRS-40
                  platform, tmnxSyncIfTimingBITS2Alarm refers to the BITS port
                  on CCM-D."

        VARIATION   tmnxSyncIfTimingBITS2InUse
            DESCRIPTION
                 "tmnxSyncIfTimingBITS2InUse on Nokia 7750 SR-3e refers to the
                  BITS port on CCM-B. On the extension chassis of an XRS-40
                  platform, tmnxSyncIfTimingBITS2InUse refers to the BITS port
                  on CCM-D."

        VARIATION   tmnxSyncIfTimingBITS2Qualified
            DESCRIPTION
                 "tmnxSyncIfTimingBITS2Qualified on Nokia 7750 SR-3e refers to
                  the BITS port on CCM-B. On the extension chassis of an XRS-40
                  platform, tmnxSyncIfTimingBITS2Qualified refers to the BITS
                  port on CCM-D."

        VARIATION   tmnxSyncIfTimingBITS2RxQltyLevel
            DESCRIPTION
                 "tmnxSyncIfTimingBITS2RxQltyLevel on Nokia 7750 SR-3e refers to
                  the BITS port on CCM-B. On the extension chassis of an XRS-40
                  platform, tmnxSyncIfTimingBITS2RxQltyLevel refers to the BITS
                  port on CCM-D."

        VARIATION   tmnxSyncIfTimingBITS2State
            DESCRIPTION
                 "tmnxSyncIfTimingBITS2State on Nokia 7750 SR-3e refers to the
                  BITS port on CCM-B. On the extension chassis of an XRS-40
                  platform, tmnxSyncIfTimingBITS2State refers to the BITS port
                  on CCM-D."

        VARIATION   tmnxSyncIfTimingPTPAdminStatus
            DESCRIPTION
                 "tmnxSyncIfTimingPTPAdminStatus is only supported on Nokia 7750
                  SR-3e with an active CPM/SFM that supports PTP. Otherwise,
                  this object is not-implemented."

        VARIATION   tmnxSyncIfTimingPTPAlarm
            DESCRIPTION
                 "tmnxSyncIfTimingPTPAlarm is only supported on Nokia 7750 SR-3e
                  with an active CPM/SFM that supports PTP. Otherwise, this
                  object is not-implemented."

        VARIATION   tmnxSyncIfTimingPTPCfgQltyLevel
            DESCRIPTION
                 "tmnxSyncIfTimingPTPCfgQltyLevel is only supported on Nokia
                  7750 SR-3e with an active CPM/SFM that supports PTP.
                  Otherwise, this object is not-implemented."

        VARIATION   tmnxSyncIfTimingPTPInUse
            DESCRIPTION
                 "tmnxSyncIfTimingPTPInUse is only supported on Nokia 7750 SR-3e
                  with an active CPM/SFM that supports PTP. Otherwise, this
                  object is not-implemented."

        VARIATION   tmnxSyncIfTimingPTPQualified
            DESCRIPTION
                 "tmnxSyncIfTimingPTPQualified is only supported on Nokia 7750
                  SR-3e with an active CPM/SFM that supports PTP. Otherwise,
                  this object is not-implemented."

        VARIATION   tmnxSyncIfTimingPTPRxQltyLevel
            DESCRIPTION
                 "tmnxSyncIfTimingPTPRxQltyLevel is only supported on Nokia 7750
                  SR-3e with an active CPM/SFM that supports PTP. Otherwise,
                  this object is not-implemented."

        VARIATION   tmnxSyncIfTimingPTPState
            DESCRIPTION
                 "tmnxSyncIfTimingPTPState is only supported on Nokia 7750 SR-3e
                  with an active CPM/SFM that supports PTP. Otherwise, this
                  object is not-implemented."

        VARIATION   tmnxSyncIfTimingRef1NationalUse
            ACCESS  not-implemented
            DESCRIPTION
                 "tmnxSyncIfTimingRef1NationalUse is not implemented on Nokia
                  7750 SR-3e in release 14.0."

        VARIATION   tmnxSyncIfTimingRef2NationalUse
            ACCESS  not-implemented
            DESCRIPTION
                 "tmnxSyncIfTimingRef2NationalUse is not implemented on Nokia
                  7750 SR-3e in release 14.0."

        VARIATION   tmnxSyncIfTimingRefOrder4
            DESCRIPTION
                 "tmnxSyncIfTimingRefOrder4 is only supported on Nokia 7750
                  SR-3e with an active CPM/SFM that supports PTP. Otherwise,
                  this object is not-implemented."

    ::= { tmnx7750SR3eAgentV14v0   6 }

--
-- 7450 CHASSIS CAPABILITIES
--
tmnx7450ChassisV14v0              AGENT-CAPABILITIES
    PRODUCT-RELEASE "Nokia SROS"
    STATUS          current
    DESCRIPTION
         "Implementation of CHASSIS functions for Nokia 7450 systems release
          14.0."

    SUPPORTS        TIMETRA-CHASSIS-MIB
        INCLUDES {
           tFPFwdEngStatsGroup,
           tmnx7710HwV3v0Group,
           tmnx7710SETSRefSrcHwV6v0Group,
-- EXCLUDE tmnx77x0CESMDAV6v0Group
           tmnxAtmGroup,
           tmnxCardCamErrorV6v1Group,
           tmnxCardCmplChipIfErrV9v0Group,
           tmnxCardCmplQChipMemErrV9v0Group,
           tmnxCardPchipV5v0Group,
           tmnxCardPchipV8v0Group,
-- EXCLUDE tmnxCardResetOnRecoverErGrp
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
           tmnxChassisMixedModeIomV8v0Group,
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
           tmnxFPQGrpV10v0R4Group,
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
           tmnxMdaHsmdaPoolV10v0Group,
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
-- EXCLUDE tmnxSyncIfTimingV9v0Group
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7450
                  with an active CPM/SFM that supports PTP. Otherwise, this
                  object is not-implemented."

        VARIATION   tSyncIfTimingAdmPTPCfgQltyLevel
            DESCRIPTION
                 "tSyncIfTimingAdmPTPCfgQltyLevel is only supported on Nokia
                  7450 with an active CPM/SFM that supports PTP. Otherwise, this
                  object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7450 in release 14.0."

        VARIATION   tSyncIfTimingAdmRef2BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef2BITSIfType does not support the value
                  'none (0).'"

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7450 in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder3
            SYNTAX  TmnxSETSRefSource {
                    -- otherCPM             (0)
                       reference1           (1),
                       reference2           (2),
                       bits                 (3)
                    -- reserved4            (4)
                    -- reserved5            (5)
                    -- noReference          (6)
                    }
            DESCRIPTION
                 "tSyncIfTimingAdmRefOrder3 supports only the values 'reference1
                  (1)', 'reference (2)', and 'bits (3)'."

        VARIATION   tSyncIfTimingAdmRefOrder4
            DESCRIPTION
                 "tSyncIfTimingAdmRefOrder4 is only supported on Nokia 7450 with
                  an active CPM/SFM that supports PTP. Otherwise, this object is
                  not-implemented."

        VARIATION   tmnxCardAllowedTypes
            ACCESS  not-implemented
            DESCRIPTION
                 "tmnxCardAllowedTypes is not implemented on Nokia 7450 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7450 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7450
                  in release 14.0.

                  tmnxChassisAdminLastSetTimer was obsoleted in release 12.0."

        VARIATION   tmnxChassisAdminMode
            SYNTAX  TmnxChassisMode {
                       modeA                (1),
                       modeB                (2),
                    -- modeC                (3)
                       modeD                (4)
                    }
            DESCRIPTION
                 "The value 'modeC (3)' is invalid on a Nokia 7450, because
                  scaling and features corresponding to the IOM2-20g card are
                  not supported on this system."

        VARIATION   tmnxChassisRowStatus
            ACCESS  read-only
            DESCRIPTION
                 "tmnxChassisRowStatus is implemented as read-only on Nokia 7450
                  in release 14.0.

                  Row entries cannot be created by SNMP SET requests. Multiple
                  chassis's are not supported on Nokia 7450."

        VARIATION   tmnxCpmCardAllowedTypes
            ACCESS  not-implemented
            DESCRIPTION
                 "tmnxCpmCardAllowedTypes is not implemented on Nokia 7450 in
                  release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7450 in release 14.0.

                  Multiple CPM card types are not supported on Nokia 7450."

        VARIATION   tmnxEqBackdoorBusFailure
            ACCESS  not-implemented
            DESCRIPTION
                 "tmnxEqBackdoorBusFailure is not implemented on Nokia 7450 in
                  release 14.0.

                  This notification was made obsolete in the 2.1 release."

        VARIATION   tmnxEqCpuFailure
            ACCESS  not-implemented
            DESCRIPTION
                 "tmnxEqCpuFailure is not implemented on Nokia 7450 in release
                  14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7450 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7450
                  with an active CPM/SFM that supports PTP. Otherwise, this
                  object is not-implemented."

        VARIATION   tmnxEqSyncIfTimingPTPAlarmClear
            DESCRIPTION
                 "tmnxEqSyncIfTimingPTPAlarmClear is only supported on Nokia
                  7450 with an active CPM/SFM that supports PTP. Otherwise, this
                  object is not-implemented."

        VARIATION   tmnxEqSyncIfTimingPTPQuality
            DESCRIPTION
                 "tmnxEqSyncIfTimingPTPQuality is only supported on Nokia 7450
                  with an active CPM/SFM that supports PTP. Otherwise, this
                  object is not-implemented."

        VARIATION   tmnxHwConfigChange
            ACCESS  not-implemented
            DESCRIPTION
                 "tmnxHwConfigChange is not implemented on Nokia 7450 in release
                  14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7450 in
                  release 14.0."

        VARIATION   tmnxHwLastAlarmEvent
            DESCRIPTION
                 "tmnxHwLastAlarmEvent is not supported on Nokia 7450. The value
                  of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxMDAAllowedTypes
            ACCESS  not-implemented
            DESCRIPTION
                 "tmnxMDAAllowedTypes is not implemented on Nokia 7450 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7450 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7450 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7450 in release 14.0."

        VARIATION   tmnxSyncIfTimingBITS2Alarm
            ACCESS  not-implemented
            DESCRIPTION
                 "tmnxSyncIfTimingBITS2Alarm is not implemented on Nokia 7450 in
                  release 14.0."

        VARIATION   tmnxSyncIfTimingBITS2InUse
            ACCESS  not-implemented
            DESCRIPTION
                 "tmnxSyncIfTimingBITS2InUse is not implemented on Nokia 7450 in
                  release 14.0."

        VARIATION   tmnxSyncIfTimingBITS2Qualified
            ACCESS  not-implemented
            DESCRIPTION
                 "tmnxSyncIfTimingBITS2Qualified is not implemented on Nokia
                  7450 in release 14.0."

        VARIATION   tmnxSyncIfTimingBITS2RxQltyLevel
            ACCESS  not-implemented
            DESCRIPTION
                 "tmnxSyncIfTimingBITS2RxQltyLevel is not implemented on Nokia
                  7450 in release 14.0."

        VARIATION   tmnxSyncIfTimingBITS2State
            ACCESS  not-implemented
            DESCRIPTION
                 "tmnxSyncIfTimingBITS2State is not implemented on Nokia 7450 in
                  release 14.0."

        VARIATION   tmnxSyncIfTimingPTPAdminStatus
            DESCRIPTION
                 "tmnxSyncIfTimingPTPAdminStatus is only supported on Nokia 7450
                  with an active CPM/SFM that supports PTP. Otherwise, this
                  object is not-implemented."

        VARIATION   tmnxSyncIfTimingPTPAlarm
            DESCRIPTION
                 "tmnxSyncIfTimingPTPAlarm is only supported on Nokia 7450 with
                  an active CPM/SFM that supports PTP. Otherwise, this object is
                  not-implemented."

        VARIATION   tmnxSyncIfTimingPTPCfgQltyLevel
            DESCRIPTION
                 "tmnxSyncIfTimingPTPCfgQltyLevel is only supported on Nokia
                  7450 with an active CPM/SFM that supports PTP. Otherwise, this
                  object is not-implemented."

        VARIATION   tmnxSyncIfTimingPTPInUse
            DESCRIPTION
                 "tmnxSyncIfTimingPTPInUse is only supported on Nokia 7450 with
                  an active CPM/SFM that supports PTP. Otherwise, this object is
                  not-implemented."

        VARIATION   tmnxSyncIfTimingPTPQualified
            DESCRIPTION
                 "tmnxSyncIfTimingPTPQualified is only supported on Nokia 7450
                  with an active CPM/SFM that supports PTP. Otherwise, this
                  object is not-implemented."

        VARIATION   tmnxSyncIfTimingPTPRxQltyLevel
            DESCRIPTION
                 "tmnxSyncIfTimingPTPRxQltyLevel is only supported on Nokia 7450
                  with an active CPM/SFM that supports PTP. Otherwise, this
                  object is not-implemented."

        VARIATION   tmnxSyncIfTimingPTPState
            DESCRIPTION
                 "tmnxSyncIfTimingPTPState is only supported on Nokia 7450 with
                  an active CPM/SFM that supports PTP. Otherwise, this object is
                  not-implemented."

        VARIATION   tmnxSyncIfTimingRef1NationalUse
            ACCESS  not-implemented
            DESCRIPTION
                 "tmnxSyncIfTimingRef1NationalUse is not implemented on Nokia
                  7450 in release 14.0."

        VARIATION   tmnxSyncIfTimingRef2NationalUse
            ACCESS  not-implemented
            DESCRIPTION
                 "tmnxSyncIfTimingRef2NationalUse is not implemented on Nokia
                  7450 in release 14.0."

        VARIATION   tmnxSyncIfTimingRefOrder4
            DESCRIPTION
                 "tmnxSyncIfTimingRefOrder4 is only supported on Nokia 7450 with
                  an active CPM/SFM that supports PTP. Otherwise, this object is
                  not-implemented."

    ::= { tmnx7450AgentV14v0   6 }

--
-- 7710 CHASSIS CAPABILITIES
--
tmnx7710ChassisV14v0              AGENT-CAPABILITIES
    PRODUCT-RELEASE "Nokia SROS"
    STATUS          current
    DESCRIPTION
         "Implementation of CHASSIS functions for Nokia 7710 systems release
          14.0."

    SUPPORTS        TIMETRA-CHASSIS-MIB
        INCLUDES {
           tFPFwdEngStatsGroup,
           tmnx7710HwV3v0Group,
           tmnx7710SETSRefSrcHwV6v0Group,
           tmnx77x0CESMDAV6v0Group,
           tmnxAtmGroup,
           tmnxCardCamErrorV6v1Group,
           tmnxCardCmplChipIfErrV9v0Group,
           tmnxCardCmplQChipMemErrV9v0Group,
           tmnxCardPchipV5v0Group,
           tmnxCardPchipV8v0Group,
-- EXCLUDE tmnxCardResetOnRecoverErGrp
           tmnxCardV10v0Group,
           tmnxCardV3v0Group,
           tmnxCardV6v0NamedPoolPlcyGroup,
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
           tmnxChassisMixedModeIomV8v0Group,
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
-- EXCLUDE tmnxChassisPowerMgmtGroup
-- EXCLUDE tmnxChassisPowerMgmtGroupV13v0
-- EXCLUDE tmnxChassisPowerMgmtNotifyGroup
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
-- EXCLUDE tmnxChassisV10v0Group
           tmnxChassisV11v0Group,
           tmnxChassisV12v0Group,
           tmnxChassisV13v0Group,
           tmnxChassisV6v1Group,
           tmnxChassisV7v0Group,
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
           tmnxFPMcPathMgmtV6v1Group,
           tmnxFPPlcyAcctV12v0Group,
           tmnxFPPoolSizingV11v0Group,
           tmnxFPQGrpGroup,
           tmnxFPQGrpV10v0R4Group,
           tmnxFPV13v0Group,
           tmnxFPWredV7v0Group,
           tmnxIPsecIsaGrpV6v0Group,
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
           tmnxMDACcagV6v1Group,
           tmnxMDAMcPathMgmtV6v0Group,
-- EXCLUDE tmnxMDAResetOnRecoverErGrp
           tmnxMDAV6v1Group,
           tmnxMDAV9v0Group,
-- EXCLUDE tmnxMdaHsmdaPoolV10v0Group
           tmnxMdaV10v0Group,
           tmnxMdaXplV5v0Group,
-- EXCLUDE tmnxPhysChassisGroup
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
-- EXCLUDE tmnxSyncIfTimingV9v0Group
           tmnxSyncV6v0Group
        }

        VARIATION   tSyncIfTimingAdmBITSCfgQltyLevel
            ACCESS  not-implemented
            DESCRIPTION
                 "tSyncIfTimingAdmBITSCfgQltyLevel is not implemented on Nokia
                  7710 in release 14.0."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmBITSNationalUse
            ACCESS  not-implemented
            DESCRIPTION
                 "tSyncIfTimingAdmBITSNationalUse is not implemented on Nokia
                  7710 in release 14.0."

        VARIATION   tSyncIfTimingAdmBITSOutAdmStatus
            ACCESS  not-implemented
            DESCRIPTION
                 "tSyncIfTimingAdmBITSOutAdmStatus is not implemented on Nokia
                  7710 in release 14.0."

        VARIATION   tSyncIfTimingAdmBITSOutLineLen
            ACCESS  not-implemented
            DESCRIPTION
                 "tSyncIfTimingAdmBITSOutLineLen is not implemented on Nokia
                  7710 in release 14.0."

        VARIATION   tSyncIfTimingAdmBITSOutSource
            ACCESS  not-implemented
            DESCRIPTION
                 "tSyncIfTimingAdmBITSOutSource is not implemented on Nokia 7710
                  in release 14.0."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef2BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef2BITSIfType does not support the value
                  'none (0).'"

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRefOrder1
            SYNTAX  INTEGER {
                    -- otherCPM             (0)
                       reference1           (1),
                       reference2           (2)
                    -- bits                 (3)
                    -- bits2                (4)
                    -- ptp                  (5)
                    -- noReference          (6)
                    }
            DEFVAL  { reference1  }
            DESCRIPTION
                 "The only values supported for tSyncIfTimingAdmRefOrder1 on
                  Nokia 7710 are 'reference1 (1)' and 'reference2 (2)'.

                  An attempt to set tSyncIfTimingAdmRefOrder1 to the value
                  'bits (3)' will result in a 'wrongValue' error. The default
                  Value is 'reference1' instead of 'bits'."

        VARIATION   tSyncIfTimingAdmRefOrder2
            SYNTAX  INTEGER {
                    -- otherCPM             (0)
                       reference1           (1),
                       reference2           (2)
                    -- bits                 (3)
                    -- bits2                (4)
                    -- ptp                  (5)
                    -- noReference          (6)
                    }
            DEFVAL  { reference2  }
            DESCRIPTION
                 "The only values supported for tSyncIfTimingAdmRefOrder2 on
                  Nokia 7710 are 'reference1 (1)' and 'reference2 (2)'.

                  An attempt to set tSyncIfTimingAdmRefOrder2 to the value
                  'bits (3)' will result in a 'wrongValue' error. The default
                  value is 'reference2' instead of 'bits'."

        VARIATION   tSyncIfTimingAdmRefOrder3
            ACCESS  not-implemented
            DESCRIPTION
                 "tSyncIfTimingAdmRefOrder3 is not implemented on Nokia 7710 in
                  release 14.0."

        VARIATION   tSyncIfTimingAdmRefOrder4
            ACCESS  not-implemented
            DESCRIPTION
                 "tSyncIfTimingAdmRefOrder4 is not implemented on Nokia 7710 in
                  release 14.0."

        VARIATION   tmnxCardAllowedTypes
            ACCESS  not-implemented
            DESCRIPTION
                 "tmnxCardAllowedTypes is not implemented on Nokia 7710 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7710 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7710
                  in release 14.0.

                  tmnxChassisAdminLastSetTimer was obsoleted in release 12.0."

        VARIATION   tmnxChassisAdminMode
            SYNTAX  TmnxChassisMode {
                    -- modeA                (1)
                    -- modeB                (2)
                       modeC                (3)
                    -- modeD                (4)
                    }
            DESCRIPTION
                 "The only value supported for tmnxChassisAdminMode on Nokia
                  7710 is 'modeC(3)'."

        VARIATION   tmnxChassisRowStatus
            ACCESS  read-only
            DESCRIPTION
                 "tmnxChassisRowStatus is implemented as read-only on Nokia 7710
                  in release 14.0.

                  Row entries cannot be created by SNMP SET requests. Multiple
                  chassis's are not supported on Nokia 7710."

        VARIATION   tmnxCpmCardAllowedTypes
            ACCESS  not-implemented
            DESCRIPTION
                 "tmnxCpmCardAllowedTypes is not implemented on Nokia 7710 in
                  release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7710 in release 14.0.

                  Multiple CPM card types are not supported on Nokia 7710."

        VARIATION   tmnxEqBackdoorBusFailure
            ACCESS  not-implemented
            DESCRIPTION
                 "tmnxEqBackdoorBusFailure is not implemented on Nokia 7710 in
                  release 14.0.

                  This notification was made obsolete in the 2.1 release."

        VARIATION   tmnxEqCpuFailure
            ACCESS  not-implemented
            DESCRIPTION
                 "tmnxEqCpuFailure is not implemented on Nokia 7710 in release
                  14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7710 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxHwConfigChange
            ACCESS  not-implemented
            DESCRIPTION
                 "tmnxHwConfigChange is not implemented on Nokia 7710 in release
                  14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7710 in
                  release 14.0."

        VARIATION   tmnxHwLastAlarmEvent
            DESCRIPTION
                 "tmnxHwLastAlarmEvent is not supported on Nokia 7710. The value
                  of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxMDAAllowedTypes
            ACCESS  not-implemented
            DESCRIPTION
                 "tmnxMDAAllowedTypes is not implemented on Nokia 7710 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEgrNamedPoolPolicy
            ACCESS  not-implemented
            DESCRIPTION
                 "tmnxMDAEgrNamedPoolPolicy is not implemented on Nokia 7710 in
                  release 14.0."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxMDAIngNamedPoolPolicy
            ACCESS  not-implemented
            DESCRIPTION
                 "tmnxMDAIngNamedPoolPolicy is not implemented on Nokia 7710 in
                  release 14.0."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7710 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7710 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            ACCESS  not-implemented
            DESCRIPTION
                 "tmnxSyncIfTimingBITS2AdminStatus is not implemented on Nokia
                  7710 in release 14.0."

        VARIATION   tmnxSyncIfTimingBITS2Alarm
            ACCESS  not-implemented
            DESCRIPTION
                 "tmnxSyncIfTimingBITS2Alarm is not implemented on Nokia 7710 in
                  release 14.0."

        VARIATION   tmnxSyncIfTimingBITS2InUse
            ACCESS  not-implemented
            DESCRIPTION
                 "tmnxSyncIfTimingBITS2InUse is not implemented on Nokia 7710 in
                  release 14.0."

        VARIATION   tmnxSyncIfTimingBITS2Qualified
            ACCESS  not-implemented
            DESCRIPTION
                 "tmnxSyncIfTimingBITS2Qualified is not implemented on Nokia
                  7710 in release 14.0."

        VARIATION   tmnxSyncIfTimingBITS2RxQltyLevel
            ACCESS  not-implemented
            DESCRIPTION
                 "tmnxSyncIfTimingBITS2RxQltyLevel is not implemented on Nokia
                  7710 in release 14.0."

        VARIATION   tmnxSyncIfTimingBITS2State
            ACCESS  not-implemented
            DESCRIPTION
                 "tmnxSyncIfTimingBITS2State is not implemented on Nokia 7710 in
                  release 14.0."

        VARIATION   tmnxSyncIfTimingBITSCfgQltyLevel
            ACCESS  not-implemented
            DESCRIPTION
                 "tmnxSyncIfTimingBITSCfgQltyLevel is not implemented on Nokia
                  7710 in release 14.0."

        VARIATION   tmnxSyncIfTimingBITSNationalUse
            ACCESS  not-implemented
            DESCRIPTION
                 "tmnxSyncIfTimingBITSNationalUse is not implemented on Nokia
                  7710 in release 14.0."

        VARIATION   tmnxSyncIfTimingBITSOutAdmStatus
            ACCESS  not-implemented
            DESCRIPTION
                 "tmnxSyncIfTimingBITSOutAdmStatus is not implemented on Nokia
                  7710 in release 14.0."

        VARIATION   tmnxSyncIfTimingBITSOutLineLen
            ACCESS  not-implemented
            DESCRIPTION
                 "tmnxSyncIfTimingBITSOutLineLen is not implemented on Nokia
                  7710 in release 14.0."

        VARIATION   tmnxSyncIfTimingBITSOutRefSel
            ACCESS  not-implemented
            DESCRIPTION
                 "tmnxSyncIfTimingBITSOutRefSel is not implemented on Nokia 7710
                  in release 14.0."

        VARIATION   tmnxSyncIfTimingBITSOutSource
            ACCESS  not-implemented
            DESCRIPTION
                 "tmnxSyncIfTimingBITSOutSource is not implemented on Nokia 7710
                  in release 14.0."

        VARIATION   tmnxSyncIfTimingBITSRxQltyLevel
            ACCESS  not-implemented
            DESCRIPTION
                 "tmnxSyncIfTimingBITSRxQltyLevel is not implemented on Nokia
                  7710 in release 14.0."

        VARIATION   tmnxSyncIfTimingBITSTxQltyLevel
            ACCESS  not-implemented
            DESCRIPTION
                 "tmnxSyncIfTimingBITSTxQltyLevel is not implemented on Nokia
                  7710 in release 14.0."

        VARIATION   tmnxSyncIfTimingRefOrder3
            ACCESS  not-implemented
            DESCRIPTION
                 "tmnxSyncIfTimingRefOrder3 is not implemented on Nokia 7710 in
                  release 14.0."

        VARIATION   tmnxSyncIfTimingRefOrder4
            ACCESS  not-implemented
            DESCRIPTION
                 "tmnxSyncIfTimingRefOrder4 is not implemented on Nokia 7710 in
                  release 14.0."

    ::= { tmnx7710AgentV14v0   6 }

--
-- 7950 CHASSIS CAPABILITIES
--
tmnx7950ChassisV14v0              AGENT-CAPABILITIES
    PRODUCT-RELEASE "Nokia SROS"
    STATUS          current
    DESCRIPTION
         "Implementation of CHASSIS functions for Nokia 7950 systems release
          14.0."

    SUPPORTS        TIMETRA-CHASSIS-MIB
        INCLUDES {
           tFPFwdEngStatsGroup,
-- EXCLUDE tmnx7710HwV3v0Group
-- EXCLUDE tmnx7710SETSRefSrcHwV6v0Group
-- EXCLUDE tmnx77x0CESMDAV6v0Group
           tmnxAtmGroup,
           tmnxCardCamErrorV6v1Group,
           tmnxCardCmplChipIfErrV9v0Group,
           tmnxCardCmplQChipMemErrV9v0Group,
           tmnxCardPchipV5v0Group,
           tmnxCardPchipV8v0Group,
-- EXCLUDE tmnxCardResetOnRecoverErGrp
           tmnxCardV10v0Group,
           tmnxCardV3v0Group,
-- EXCLUDE tmnxCardV6v0NamedPoolPlcyGroup
           tmnxCardV7v0Group,
           tmnxCardVirtualGroupV14v0,
           tmnxCardVirtualSchAdjV13v0Group,
           tmnxChassPANotifyObjsV12v0Grp,
-- EXCLUDE tmnxChassisFabricV11v0Group
           tmnxChassisFanV11v0Group,
           tmnxChassisFpResourceV13v0Group,
           tmnxChassisHwEventGroup,
           tmnxChassisHwEventGroupV10v0,
           tmnxChassisHwEventNotifyGroup,
           tmnxChassisHwEventNotifyGrpV10v0,
           tmnxChassisHwV11v0Group,
           tmnxChassisHwV6v1Group,
           tmnxChassisHwV9v0Group,
           tmnxChassisMgmtEthRedNtfV13v0Grp,
           tmnxChassisMgmtEthRedV13v0Grp,
-- EXCLUDE tmnxChassisMixedModeIomV8v0Group
           tmnxChassisNotifV12v0Group,
           tmnxChassisNotifV13v0Group,
           tmnxChassisNotificationV7v0Group,
           tmnxChassisNotificationV9v0Group,
           tmnxChassisNotifyObjsV12v0Group,
           tmnxChassisNotifyObjsV13v0Grp,
           tmnxChassisNotifyV10v0Group,
           tmnxChassisPlcyAcctNtfyV12v0Grp,
           tmnxChassisPowerMgmtGroup,
           tmnxChassisPowerMgmtGroupV13v0,
           tmnxChassisPowerMgmtNotifyGroup,
           tmnxChassisPowerNotifV12v0Group,
           tmnxChassisPowerSupplyV9v0Grp,
           tmnxChassisPowerV11v0Group,
           tmnxChassisPowerV12v0Group,
           tmnxChassisQGrpOvrGroup,
           tmnxChassisResourceV13v0Group,
           tmnxChassisResourceV14v0Group,
           tmnxChassisSmartPeqNtfyV11v0Grp,
           tmnxChassisSmartPeqV11v0Group,
           tmnxChassisSwitchFabNtfyV11v0Grp,
           tmnxChassisUserModV7v0Group,
           tmnxChassisV10v0Group,
           tmnxChassisV11v0Group,
           tmnxChassisV12v0Group,
           tmnxChassisV13v0Group,
           tmnxChassisV6v1Group,
-- EXCLUDE tmnxChassisV7v0Group
           tmnxChassisV8v0Group,
           tmnxCpmCardCmplxMemErrV9v0Group,
           tmnxCpmCardRebootHoldV11v0Group,
           tmnxCpmCardV13v0Group,
           tmnxCpmFlashV14v0Group,
           tmnxCpmMemSizeNotifGroupV12v0,
           tmnxCpmPChipFcsObjGroupV12v0,
           tmnxFPBufAllocV12v0Group,
           tmnxFPDCpuProtV11v0R0Group,
           tmnxFPDcpNotifyObjsV11v0Group,
           tmnxFPDcpNotifyV11v0Group,
-- EXCLUDE tmnxFPMcPathMgmtV6v1Group
           tmnxFPPlcyAcctV12v0Group,
           tmnxFPPoolSizingV11v0Group,
           tmnxFPQGrpGroup,
           tmnxFPQGrpV10v0R4Group,
           tmnxFPV13v0Group,
-- EXCLUDE tmnxFPWredV7v0Group
-- EXCLUDE tmnxIPsecIsaGrpV6v0Group
           tmnxIPsecNotifV7v0Group,
           tmnxIPsecV7v0Group,
           tmnxIomResrcNotifyObjsV12v0Grp,
           tmnxIomResrcNotifyV12v0Group,
           tmnxIpsecV10v0Group,
           tmnxIsaGrpIsaScaleModeGroupV14v0,
           tmnxIsaMemWMarkNotifGroupV14v0,
-- EXCLUDE tmnxMDACcagV6v1Group
-- EXCLUDE tmnxMDAMcPathMgmtV6v0Group
           tmnxMDAResetOnRecoverErGrp,
           tmnxMDAV6v1Group,
           tmnxMDAV9v0Group,
-- EXCLUDE tmnxMdaHsmdaPoolV10v0Group
-- EXCLUDE tmnxMdaV10v0Group
           tmnxMdaXplV5v0Group,
           tmnxPhysChassisGroup,
           tmnxPhysChassisGroupV14v0,
           tmnxPhysChassisNotifGroupV14v0,
           tmnxPhysChassisV13v0Group,
           tmnxSyncIfTimingNotifV8v0Group,
           tmnxSyncIfTimingNotifyV9v0Group,
           tmnxSyncIfTimingV14v0Group,
           tmnxSyncIfTimingV8v0Group,
-- EXCLUDE tmnxSyncIfTimingV9v0Group
           tmnxSyncV6v0Group
        }

        VARIATION   tSyncIfTimingAdmBITSCfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmBITSCfgQltyLevel does not support the
                  values 'smc (7)', 'st4 (8)', 'dus (9)', 'dnu (14)', 'inc
                  (15)', 'pno (16)', or 'failed (19)'."

        VARIATION   tSyncIfTimingAdmBITSIfType
            SYNTAX  TmnxBITSIfType {
                    -- none                 (0)
                       t1-esf               (1),
                       t1-sf                (2),
                       e1-pcm30crc          (3),
                       e1-pcm31crc          (4),
                       g703-2048khz         (5)
                    }
            DESCRIPTION
                 "tSyncIfTimingAdmBITSIfType does not support the value 'none
                  (0).'"

        VARIATION   tSyncIfTimingAdmPTPAdminStatus
            DESCRIPTION
                 "tSyncIfTimingAdmPTPAdminStatus is only supported on Nokia 7950
                  with an active CPM/SFM that supports PTP. Otherwise, this
                  object is not-implemented."

        VARIATION   tSyncIfTimingAdmPTPCfgQltyLevel
            DESCRIPTION
                 "tSyncIfTimingAdmPTPCfgQltyLevel is only supported on Nokia
                  7950 with an active CPM/SFM that supports PTP. Otherwise, this
                  object is not-implemented."

        VARIATION   tSyncIfTimingAdmRef1BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef1BITSIfType does not support the value
                  'none (0).'"

        VARIATION   tSyncIfTimingAdmRef1CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef1CfgQltyLevel does not support the
                  values 'smc (7)', 'st4 (8)', 'dus (9)', 'dnu (14)', 'inc
                  (15)', 'pno (16)', or 'failed (19)'."

        VARIATION   tSyncIfTimingAdmRef1NationalUse
            ACCESS  not-implemented
            DESCRIPTION
                 "tSyncIfTimingAdmRef1NationalUse is not implemented on Nokia
                  7950 in release 14.0."

        VARIATION   tSyncIfTimingAdmRef2BITSIfType
            SYNTAX  TmnxBITSIfType {
                    -- none                 (0)
                       t1-esf               (1),
                       t1-sf                (2),
                       e1-pcm30crc          (3),
                       e1-pcm31crc          (4)
                    }
            DESCRIPTION
                 "tSyncIfTimingAdmRef2BITSIfType does not support the value
                  'none (0).'"

        VARIATION   tSyncIfTimingAdmRef2CfgQltyLevel
            SYNTAX  TmnxSSMQualityLevel {
                       unknown              (0),
                       prs                  (1),
                       stu                  (2),
                       st2                  (3),
                       tnc                  (4),
                       st3e                 (5),
                       st3                  (6),
                    -- smc                  (7)
                    -- st4                  (8)
                    -- dus                  (9)
                       prc                  (10),
                       ssua                 (11),
                       ssub                 (12),
                       sec                  (13),
                    -- dnu                  (14)
                    -- inv                  (15)
                    -- pno                  (16)
                       eec1                 (17),
                       eec2                 (18)
                    -- failed               (19)
                    }
            DESCRIPTION
                 "The tSyncIfTimingAdmRef2CfgQltyLevel does not support the
                  values 'smc (7)', 'st4 (8)', 'dus (9)', 'dnu (14)', 'inc
                  (15)', 'pno (16)', or 'failed (19)'."

        VARIATION   tSyncIfTimingAdmRef2NationalUse
            ACCESS  not-implemented
            DESCRIPTION
                 "tSyncIfTimingAdmRef2NationalUse is not implemented on Nokia
                  7950 in release 14.0."

        VARIATION   tSyncIfTimingAdmRefOrder1
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder1 supports only the values 'reference1
                  (1)', 'reference (2)', and 'bits (3)'."

        VARIATION   tSyncIfTimingAdmRefOrder2
            SYNTAX  TmnxSETSRefSource {
                    -- otherCPM             (0)
                       reference1           (1),
                       reference2           (2),
                       bits                 (3)
                    -- bits2                (4)
                    -- ptp                  (5)
                    -- noReference          (6)
                    }
            DESCRIPTION
                 "tSyncIfTimingAdmRefOrder2 supports only the values 'reference1
                  (1)', 'reference (2)', and 'bits (3)'."

        VARIATION   tSyncIfTimingAdmRefOrder4
            DESCRIPTION
                 "tSyncIfTimingAdmRefOrder4 is only supported on Nokia 7950 with
                  an active CPM/SFM that supports PTP. Otherwise, this object is
                  not-implemented."

        VARIATION   tmnxCardAllowedTypes
            ACCESS  not-implemented
            DESCRIPTION
                 "tmnxCardAllowedTypes is not implemented on Nokia 7950 in
                  release 14.0.

                  This object was made obsolete in the 3.0 release.

                  A bit-mask that specifies what IOM card types the
                  administrator has designated be allowed to be inserted into
                  this slot. If the slot has not-been pre-provisioned and a card
                  that does not match one of the allowed types is inserted into
                  this slot, a mis-match alarm is raised. If a specific value
                  has not yet been SET by the manager, tmnxCardAllowedTypes
                  returns the same value to a GET request as
                  tmnxCardSupportedTypes."

        VARIATION   tmnxCardInternalSchedWghtMode
            SYNTAX  INTEGER {
                    -- noOverride           (1)
                       default              (2),
                       forceEqual           (3),
                       offeredLoad          (4),
                       cappedOfferedLoad    (5)
                    }
            DESCRIPTION
                 "tmnxCardInternalSchedWghtMode does not support the value
                  'noOverride (1)' as defined by TmnxInternalSchedWeightMode
                  textual-convention."

        VARIATION   tmnxChassisAdminLastSetTimeout
            ACCESS  not-implemented
            DESCRIPTION
                 "tmnxChassisAdminLastSetTimeout is not implemented on Nokia
                  7950 in release 14.0.

                  tmnxChassisAdminLastSetTimeout was obsoleted in release
                  12.0."

        VARIATION   tmnxChassisAdminLastSetTimer
            ACCESS  not-implemented
            DESCRIPTION
                 "tmnxChassisAdminLastSetTimer is not implemented on Nokia 7950
                  in release 14.0.

                  tmnxChassisAdminLastSetTimer was obsoleted in release 12.0."

        VARIATION   tmnxChassisAdminMode
            SYNTAX  TmnxChassisMode {
                    -- modeA                (1)
                    -- modeB                (2)
                    -- modeC                (3)
                       modeD                (4)
                    }
            DESCRIPTION
                 "The only value supported for tmnxChassisAdminMode on Nokia
                  7950 is 'modeD(4)'."

        VARIATION   tmnxChassisPowerSupplyAssignedType
            ACCESS  not-implemented
            DESCRIPTION
                 "tmnxChassisPowerSupplyAssignedType is not implemented on Nokia
                  7950 in release 14.0."

        VARIATION   tmnxChassisRowStatus
            ACCESS  read-only
            DESCRIPTION
                 "tmnxChassisRowStatus is implemented as read-only on Nokia 7950
                  in release 14.0.

                  Row entries cannot be created by SNMP SET requests. Multiple
                  chassis's are not supported on Nokia 7950."

        VARIATION   tmnxCpmCardAllowedTypes
            ACCESS  not-implemented
            DESCRIPTION
                 "tmnxCpmCardAllowedTypes is not implemented on Nokia 7950 in
                  release 14.0.

                  This object was made obsolete in the 3.0 release.

                  A bit-mask that specified what CPM card types the
                  administrator has designated be allowed to be inserted into
                  this slot. If the slot has not-been pre-provisioned and a card
                  that does not match one of the allowed types is inserted into
                  this slot, a mis-match alarm would be raised.

                  If a specific value had not yet been SET by the manager,
                  tmnxCpmCardAllowedTypes would return the same value to a GET
                  request as tmnxCpmCardSupportedTypes."

        VARIATION   tmnxCpmCardAssignedType
            ACCESS  read-only
            DESCRIPTION
                 "tmnxCpmCardAssignedType is implemented as read-only on Nokia
                  7950 in release 14.0.

                  Multiple CPM card types are not supported on Nokia 7950."

        VARIATION   tmnxEqBackdoorBusFailure
            ACCESS  not-implemented
            DESCRIPTION
                 "tmnxEqBackdoorBusFailure is not implemented on Nokia 7950 in
                  release 14.0.

                  This notification was made obsolete in the 2.1 release."

        VARIATION   tmnxEqCpuFailure
            ACCESS  not-implemented
            DESCRIPTION
                 "tmnxEqCpuFailure is not implemented on Nokia 7950 in release
                  14.0.

                  This notification was made obsolete in the 2.1 release.

                  A cpu failure on a CPM card is detected by the hardware
                  bootup and is indicated by the boot diagnostic display. If
                  there is no working redundant CPM card, the system does not
                  come up.

                  A failure of an IOM card or standby redundant CPM card causes
                  the tmnxEqCardFailure notification to be sent."

        VARIATION   tmnxEqMemoryFailure
            ACCESS  not-implemented
            DESCRIPTION
                 "tmnxEqMemoryFailure is not implemented on Nokia 7950 in
                  release 14.0.

                  This notification was made obsolete in the 2.1 release.

                  A failure of the memory device is detected by the hardware
                  bootup and is indicated by the boot diagnostic display. If
                  there is no working redundant CPM card, the system does not
                  come up.

                  A failure of the memory device during run-time causes the
                  system to fail and the 'admin tech-support' information to be
                  saved.

                  A failure of an IOM card or standby redundant CPM card causes
                  the tmnxEqCardFailure notification to be sent."

        VARIATION   tmnxEqSyncIfTimingPTPAlarm
            DESCRIPTION
                 "tmnxEqSyncIfTimingPTPAlarm is only supported on Nokia 7950
                  with an active CPM/SFM that supports PTP. Otherwise, this
                  object is not-implemented."

        VARIATION   tmnxEqSyncIfTimingPTPAlarmClear
            DESCRIPTION
                 "tmnxEqSyncIfTimingPTPAlarmClear is only supported on Nokia
                  7950 with an active CPM/SFM that supports PTP. Otherwise, this
                  object is not-implemented."

        VARIATION   tmnxEqSyncIfTimingPTPQuality
            DESCRIPTION
                 "tmnxEqSyncIfTimingPTPQuality is only supported on Nokia 7950
                  with an active CPM/SFM that supports PTP. Otherwise, this
                  object is not-implemented."

        VARIATION   tmnxHwConfigChange
            ACCESS  not-implemented
            DESCRIPTION
                 "tmnxHwConfigChange is not implemented on Nokia 7950 in release
                  14.0.

                  This notification was made obsolete in the 2.1 release.

                  The tmnxHwConfigChange notification has been replaced with
                  the generic change notifications from the TIMETRA-SYSTEM-MIB:
                  tmnxConfigModify, tmnxConfigCreate, tmnxConfigDelete,
                  tmnxStateChange."

        VARIATION   tmnxHwContainedIndex
            ACCESS  not-implemented
            DESCRIPTION
                 "tmnxHwContainedIndex is not implemented on Nokia 7950 in
                  release 14.0."

        VARIATION   tmnxHwLastAlarmEvent
            DESCRIPTION
                 "tmnxHwLastAlarmEvent is not supported on Nokia 7950. The value
                  of tmnxHwLastAlarmEvent is always '0.0'."

        VARIATION   tmnxHwOperState
            SYNTAX  INTEGER {
                       unknown              (1),
                       inService            (2),
                       outOfService         (3),
                       diagnosing           (4),
                       failed               (5),
                       booting              (6),
                       empty                (7),
                       provisioned          (8),
                       unprovisioned        (9),
                       upgrade              (10),
                       downgrade            (11)
                    -- inServiceUpgrage     (12)
                    -- inServiceDowngrade   (13)
                    -- resetPending         (14)
                    }
            DESCRIPTION
                 "The enumerations 'inServiceUpgrade (12)', 'inServiceDowngrade
                  (13)', and 'resetPending (14)' are no longer supported."

        VARIATION   tmnxMDAAllowedTypes
            ACCESS  not-implemented
            DESCRIPTION
                 "tmnxMDAAllowedTypes is not implemented on Nokia 7950 in
                  release 14.0.

                  This object was made obsolete in the 3.0 release.

                  A bit-mask specified what MDA card types the administrator
                  has designated be allowed to be inserted into this slot. If
                  the slot has not-been pre-provisioned and a MDA card that does
                  not match one of the allowed types is inserted into this slot,
                  a mis-match alarm would be raised. If a specific value has not
                  yet been SET by the manager, a GET to tmnxMDAAllowedTypes
                  returned the same value as tmnxMDASupportedTypes."

        VARIATION   tmnxMDAEgrNamedPoolPolicy
            ACCESS  not-implemented
            DESCRIPTION
                 "tmnxMDAEgrNamedPoolPolicy is not implemented on Nokia 7950 in
                  release 14.0."

        VARIATION   tmnxMDAEquippedPorts
            DESCRIPTION
                 "The value of tmnxMDAEquippedPorts indicates the number of
                  ports equipped on this MDA card. Previous to the 3.0 release
                  this object was defined to be a bit-mask of equipped ports.
                  However, the code implementation has always returned a value
                  that is just the total number of equipped ports."

        VARIATION   tmnxMDAIngNamedPoolPolicy
            ACCESS  not-implemented
            DESCRIPTION
                 "tmnxMDAIngNamedPoolPolicy is not implemented on Nokia 7950 in
                  release 14.0."

        VARIATION   tmnxPeConfigurationError
            ACCESS  not-implemented
            DESCRIPTION
                 "tmnxPeConfigurationError notification is not implemented. This
                  notification was made obsolete in the 2.1 release.

                  Many other notifications more specifically indicate detection
                  of a configuration error. In most cases the SNMP SET request
                  that tries to make an invalid configuration results in an
                  error response.

                  In some cases the configuration parameters are valid and the
                  SNMP SET request succeeds but the system cannot successfully
                  apply the new parameters. The affected object may then put
                  into an operational 'down' state. A state change notification
                  such as tmnxStateChange or a more specific notification is
                  sent to alert about the problem.

                  For example, an attempt to create an event log with a
                  file-type destination when the specified cflash media is full
                  or not present results in TIMETRA-LOG-MIB notifications
                  tmnxLogSpaceContention, tmnxLogAdminLocFailed, or
                  tmnxLogBackupLocFailed."

        VARIATION   tmnxPeCpuCyclesExceeded
            ACCESS  not-implemented
            DESCRIPTION
                 "tmnxPeCpuCyclesExceeded notification is not implemented. This
                  notification was made obsolete in the 2.1 release.

                  It does not apply. The SROS software architecture does not
                  restrict CPU cycles used by a specific code module."

        VARIATION   tmnxPeOutOfMemory
            ACCESS  not-implemented
            DESCRIPTION
                 "tmnxPeOutOfMemory notification is not implemented. This
                  notification was made obsolete in the 2.1 release.

                  The tmnxPeOutOfMemory notification has been replaced with the
                  module specific notification from the TIMETRA-SYSTEM-MIB:
                  tmnxModuleMallocFailed."

        VARIATION   tmnxPeSoftwareAbnormalHalt
            ACCESS  not-implemented
            DESCRIPTION
                 "tmnxPeSoftwareAbnormalHalt is not implemented on Nokia 7950 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeSoftwareError
            ACCESS  not-implemented
            DESCRIPTION
                 "tmnxPeSoftwareError is not implemented on Nokia 7950 in
                  release 14.0.

                  This notification was made obsolete in the 2.1 release.

                  Many of the other notifications more specifically indicate
                  detection of some type of software error.

                  Also, there are TRACE_* MACROs throughout the code that
                  developers use to trap failures that might result in a
                  software crash. The highest severity event, TRACE_ERROR,
                  prints directly to the CONSOLE and in release software causes
                  the system to reboot. Ideally, the customer never sees
                  TRACE_ERROR messages. The 'admin tech-support' information
                  includes a log of TRACE messages to help developers diagnose a
                  failure of the software in the field."

        VARIATION   tmnxPeStorageProblem
            ACCESS  not-implemented
            DESCRIPTION
                 "tmnxPeStorageProblem notification is not implemented. This
                  notification was made obsolete in the 2.1 release.

                  The only 'storage' devices on the SROS are the cflash drives.
                  Cflash write errors cause a tmnxEqFlashDataLoss notification
                  to be sent. The tmnxEqFlashDiskFull notification is sent when
                  the driver detects that the cflash device is full."

        VARIATION   tmnxRedRestoreFail
            ACCESS  not-implemented
            DESCRIPTION
                 "tmnxRedRestoreFail notification is not implemented. This
                  notification was made obsolete in the 2.1 release.

                  It does not apply. This event was originally created for an
                  early redundancy mechanism that was never released. This event
                  should be removed."

        VARIATION   tmnxRedRestoreSuccess
            ACCESS  not-implemented
            DESCRIPTION
                 "tmnxRedRestoreSuccess notification is not implemented. This
                  notification was made obsolete in the 2.1 release.

                  It does not apply. This event was originally created for an
                  early redundancy mechanism that was never released. This event
                  should be removed.

                  When the secondary CPM card takes over following a reboot or
                  failure of the active CPM, sbiBootConfig and sbiBootSnmpd
                  events from the TIMETRA-SYSTEM-MIB are generated to indicate
                  that the secondary card has successfully taken control of the
                  system."

        VARIATION   tmnxRedSecondaryCPMStatusChange
            ACCESS  not-implemented
            DESCRIPTION
                 "tmnxRedSecondaryCPMStatusChange notification is not
                  implemented. This notification was made obsolete in the 2.1
                  release.

                  There is no way to administratively enable or disable CPM
                  cards so there is no need for a status change event for
                  administrative state changes.

                  Operational changes detected about the Secondary CPM card are
                  indicated by more specific notifications such as
                  tmnxEqCardFailure, tmnxEqCardRemoved, and tmnxEqCardInserted."

        VARIATION   tmnxSyncIfTimingBITS2AdminStatus
            DESCRIPTION
                 "tmnxSyncIfTimingBITS2AdminStatus on Nokia 7950 refers to the
                  BITS port on CCM-B. On the extension chassis of an XRS-40
                  platform, tmnxSyncIfTimingBITS2AdminStatus refers to the BITS
                  port on CCM-D."

        VARIATION   tmnxSyncIfTimingBITS2Alarm
            DESCRIPTION
                 "tmnxSyncIfTimingBITS2Alarm on Nokia 7950 refers to the BITS
                  port on CCM-B. On the extension chassis of an XRS-40 platform,
                  tmnxSyncIfTimingBITS2Alarm refers to the BITS port on CCM-D."

        VARIATION   tmnxSyncIfTimingBITS2InUse
            DESCRIPTION
                 "tmnxSyncIfTimingBITS2InUse on Nokia 7950 refers to the BITS
                  port on CCM-B. On the extension chassis of an XRS-40 platform,
                  tmnxSyncIfTimingBITS2InUse refers to the BITS port on CCM-D."

        VARIATION   tmnxSyncIfTimingBITS2Qualified
            DESCRIPTION
                 "tmnxSyncIfTimingBITS2Qualified on Nokia 7950 refers to the
                  BITS port on CCM-B. On the extension chassis of an XRS-40
                  platform, tmnxSyncIfTimingBITS2Qualified refers to the BITS
                  port on CCM-D."

        VARIATION   tmnxSyncIfTimingBITS2RxQltyLevel
            DESCRIPTION
                 "tmnxSyncIfTimingBITS2RxQltyLevel on Nokia 7950 refers to the
                  BITS port on CCM-B. On the extension chassis of an XRS-40
                  platform, tmnxSyncIfTimingBITS2RxQltyLevel refers to the BITS
                  port on CCM-D."

        VARIATION   tmnxSyncIfTimingBITS2State
            DESCRIPTION
                 "tmnxSyncIfTimingBITS2State on Nokia 7950 refers to the BITS
                  port on CCM-B. On the extension chassis of an XRS-40 platform,
                  tmnxSyncIfTimingBITS2State refers to the BITS port on CCM-D."

        VARIATION   tmnxSyncIfTimingPTPAdminStatus
            DESCRIPTION
                 "tmnxSyncIfTimingPTPAdminStatus is only supported on Nokia 7950
                  with an active CPM/SFM that supports PTP. Otherwise, this
                  object is not-implemented."

        VARIATION   tmnxSyncIfTimingPTPAlarm
            DESCRIPTION
                 "tmnxSyncIfTimingPTPAlarm is only supported on Nokia 7950 with
                  an active CPM/SFM that supports PTP. Otherwise, this object is
                  not-implemented."

        VARIATION   tmnxSyncIfTimingPTPCfgQltyLevel
            DESCRIPTION
                 "tmnxSyncIfTimingPTPCfgQltyLevel is only supported on Nokia
                  7950 with an active CPM/SFM that supports PTP. Otherwise, this
                  object is not-implemented."

        VARIATION   tmnxSyncIfTimingPTPInUse
            DESCRIPTION
                 "tmnxSyncIfTimingPTPInUse is only supported on Nokia 7950 with
                  an active CPM/SFM that supports PTP. Otherwise, this object is
                  not-implemented."

        VARIATION   tmnxSyncIfTimingPTPQualified
            DESCRIPTION
                 "tmnxSyncIfTimingPTPQualified is only supported on Nokia 7950
                  with an active CPM/SFM that supports PTP. Otherwise, this
                  object is not-implemented."

        VARIATION   tmnxSyncIfTimingPTPRxQltyLevel
            DESCRIPTION
                 "tmnxSyncIfTimingPTPRxQltyLevel is only supported on Nokia 7950
                  with an active CPM/SFM that supports PTP. Otherwise, this
                  object is not-implemented."

        VARIATION   tmnxSyncIfTimingPTPState
            DESCRIPTION
                 "tmnxSyncIfTimingPTPState is only supported on Nokia 7950 with
                  an active CPM/SFM that supports PTP. Otherwise, this object is
                  not-implemented."

        VARIATION   tmnxSyncIfTimingRef1NationalUse
            ACCESS  not-implemented
            DESCRIPTION
                 "tmnxSyncIfTimingRef1NationalUse is not implemented on Nokia
                  7950 in release 14.0."

        VARIATION   tmnxSyncIfTimingRef2NationalUse
            ACCESS  not-implemented
            DESCRIPTION
                 "tmnxSyncIfTimingRef2NationalUse is not implemented on Nokia
                  7950 in release 14.0."

        VARIATION   tmnxSyncIfTimingRefOrder4
            DESCRIPTION
                 "tmnxSyncIfTimingRefOrder4 is only supported on Nokia 7950 with
                  an active CPM/SFM that supports PTP. Otherwise, this object is
                  not-implemented."

    ::= { tmnx7950AgentV14v0   6 }

--
-- 7950 CHASSIS_INTERCONNECT CAPABILITIES
--
tmnx7950ChassisInterconnectV14v0  AGENT-CAPABILITIES
    PRODUCT-RELEASE "Nokia SROS"
    STATUS          current
    DESCRIPTION
         "Implementation of CHASSIS_INTERCONNECT functions for Nokia 7950
          systems release 14.0."

    SUPPORTS        TIMETRA-CHASSIS-INTERCONNECT-MIB
        INCLUDES {
           tmnxChassIcNotifV12v0Group,
           tmnxChassIcNotifyObjsV12v0Group,
           tmnxCpmIcPortNotifV12v0Group,
           tmnxCpmIcPortV12v0Group,
           tmnxSfmIcPortNotifV12v0Group,
           tmnxSfmIcPortV12v0Group
        }

    ::= { tmnx7950AgentV14v0   4 }

--
-- SROS CLEAR CAPABILITIES
--
tmnxSROSClearV14v0                AGENT-CAPABILITIES
    PRODUCT-RELEASE "Nokia SROS"
    STATUS          current
    DESCRIPTION
         "Implementation of clear and reset capabilities for Nokia SROS systems
          release 14.0"

    SUPPORTS        TIMETRA-CLEAR-MIB
        INCLUDES {
           tmnxClearGroup,
           tmnxClearNotificationGroup
        }

    ::= { tmnxSROSAgentV14v0   7 }

--
-- 7750 CONN_PROF CAPABILITIES
--
tmnx7750ConnProfV14v0             AGENT-CAPABILITIES
    PRODUCT-RELEASE "Nokia SROS"
    STATUS          current
    DESCRIPTION
         "Implementation of connection profile capabilities for Nokia 7750
          systems release 14.0."

    SUPPORTS        TIMETRA-CONN-PROF-MIB
        INCLUDES {
           tmnxConnProfAtmMemberGroup,
           tmnxConnProfGroup,
           tmnxConnProfTimeStampGroup,
           tmnxConnProfVlanGroup
        }

        VARIATION   tmnxConnProfAtmMemberRowStatus
            SYNTAX  RowStatus {
                       active               (1),
                    -- notInService         (2)
                    -- notReady             (3)
                       createAndGo          (4),
                    -- createAndWait        (5)
                       destroy              (6)
                    }
            DESCRIPTION
                 "tmnxConnProfAtmMemberRowStatus supports only 'active (1)',
                  'createAndGo (4)', and 'destroy (6)'."

        VARIATION   tmnxConnProfRowStatus
            SYNTAX  RowStatus {
                       active               (1),
                    -- notInService         (2)
                    -- notReady             (3)
                       createAndGo          (4),
                    -- createAndWait        (5)
                       destroy              (6)
                    }
            DESCRIPTION
                 "tmnxConnProfRowStatus supports only 'active (1)', 'createAndGo
                  (4)', and 'destroy (6)'."

        VARIATION   tmnxConnProfVlanEthRowStatus
            SYNTAX  RowStatus {
                       active               (1),
                    -- notInService         (2)
                    -- notReady             (3)
                       createAndGo          (4),
                    -- createAndWait        (5)
                       destroy              (6)
                    }
            DESCRIPTION
                 "tmnxConnProfVlanEthRowStatus supports only 'active (1)',
                  'createAndGo (4)', and 'destroy (6)'."

        VARIATION   tmnxConnProfVlanRowStatus
            SYNTAX  RowStatus {
                       active               (1),
                    -- notInService         (2)
                    -- notReady             (3)
                       createAndGo          (4),
                    -- createAndWait        (5)
                       destroy              (6)
                    }
            DESCRIPTION
                 "tmnxConnProfVlanRowStatus supports only 'active (1)',
                  'createAndGo (4)', and 'destroy (6)'."

    ::= { tmnx7750AgentV14v0  78 }

--
-- 7450 CONN_PROF CAPABILITIES
--
tmnx7450ConnProfV14v0             AGENT-CAPABILITIES
    PRODUCT-RELEASE "Nokia SROS"
    STATUS          current
    DESCRIPTION
         "Implementation of connection profile capabilities for Nokia 7450
          systems release 14.0."

    SUPPORTS        TIMETRA-CONN-PROF-MIB
        INCLUDES {
           tmnxConnProfAtmMemberGroup,
           tmnxConnProfGroup,
           tmnxConnProfTimeStampGroup,
           tmnxConnProfVlanGroup
        }

        VARIATION   tmnxConnProfAtmMemberRowStatus
            SYNTAX  RowStatus {
                       active               (1),
                    -- notInService         (2)
                    -- notReady             (3)
                       createAndGo          (4),
                    -- createAndWait        (5)
                       destroy              (6)
                    }
            DESCRIPTION
                 "tmnxConnProfAtmMemberRowStatus supports only 'active (1)',
                  'createAndGo (4)', and 'destroy (6)'."

        VARIATION   tmnxConnProfRowStatus
            SYNTAX  RowStatus {
                       active               (1),
                    -- notInService         (2)
                    -- notReady             (3)
                       createAndGo          (4),
                    -- createAndWait        (5)
                       destroy              (6)
                    }
            DESCRIPTION
                 "tmnxConnProfRowStatus supports only 'active (1)', 'createAndGo
                  (4)', and 'destroy (6)'."

        VARIATION   tmnxConnProfVlanEthRowStatus
            SYNTAX  RowStatus {
                       active               (1),
                    -- notInService         (2)
                    -- notReady             (3)
                       createAndGo          (4),
                    -- createAndWait        (5)
                       destroy              (6)
                    }
            DESCRIPTION
                 "tmnxConnProfVlanEthRowStatus supports only 'active (1)',
                  'createAndGo (4)', and 'destroy (6)'."

        VARIATION   tmnxConnProfVlanRowStatus
            SYNTAX  RowStatus {
                       active               (1),
                    -- notInService         (2)
                    -- notReady             (3)
                       createAndGo          (4),
                    -- createAndWait        (5)
                       destroy              (6)
                    }
            DESCRIPTION
                 "tmnxConnProfVlanRowStatus supports only 'active (1)',
                  'createAndGo (4)', and 'destroy (6)'."

    ::= { tmnx7450AgentV14v0  78 }

--
-- SROS CRON CAPABILITIES
--
tmnxSROSCronV14v0                 AGENT-CAPABILITIES
    PRODUCT-RELEASE "Nokia SROS"
    STATUS          current
    DESCRIPTION
         "Implementation of CRON capabilities for Nokia SROS systems release
          14.0."

    SUPPORTS        DISMAN-SCHEDULE-MIB
        INCLUDES {
           schedCalendarGroup,
           schedGroup2,
           schedNotificationsGroup
        }

        VARIATION   schedInterval
            SYNTAX  Unsigned32 (30..42949672)
            DESCRIPTION
                 "The values supported for schedInterval are between 30 and
                  42949672 seconds. 42949672 seconds creates a maximum interval
                  of 497 days, 2 hours, 27 minutes and 52 seconds."

        VARIATION   schedOwner
            SYNTAX  SnmpAdminString (SIZE (1..32))
            DESCRIPTION
                 "The minimum length of schedOwner is 1 when creating new
                  entries in tables via SNMP SET requests."

    SUPPORTS        DISMAN-SCRIPT-MIB
        INCLUDES {
           smLanguageGroup,
           smLaunchGroup2,
           smNotificationsGroup2,
           smRunGroup2,
           smScriptGroup2
        }

        VARIATION   smLaunchAdminStatus
            SYNTAX  INTEGER {
                       enabled              (1),
                       disabled             (2)
                    -- autostart(3)
                    }
            DESCRIPTION
                 "The 'autostart (3)' state is not supported.

                  The mib is not clear if smLaunchAdminStatus can be set to
                  'disabled' if there are associated entries in the smRunTable.
                  This agent does not allow smLaunchAdminStatus to be set to
                  'disabled (2)' if there are any associated entries in the
                  smRunTable. Any associated smRunEntry must be aborted and aged
                  out before smLaunchAdminStatus can be set to 'disabled (2)'."

        VARIATION   smLaunchArgument
            DESCRIPTION
                 "This agent uses smLaunchArgument to specify the URL of the
                  file that is created to hold the CLI session output from the
                  'exec' of the CLI script specified in smScriptSource. The
                  script specified in smScriptSource is executed as if the
                  'exec' '-echo' switch was specified in a CLI CONSOLE/Telnet
                  session and the command echo and any display from CLI 'show'
                  commands specified in the script is redirected to the results
                  file specified in smLaunchArgument.

                  The smLaunchArgument URL should consist of the path and a
                  filename prefix. It refer to either the local cflash drives or
                  a remote file accessed through a remote ftp URL. When the exec
                  results file is created for a specific run of the script, a
                  timestamp of the form '_yyyymmdd-hhmmss.out' is appended on
                  the end of the smLaunchArgument filename prefix. For example,
                  setting smLaunchArgument to
                  'ftp://<user>:<passwd>@<a.b.c.d>/cron/results/test-res' causes
                  a script results file to be created named
                  'cron/results/test-res_yyyymmdd-hhmmss.out'.

                  NOTE: The agent does not have any capability to age out,
                  rotate, delete, or otherwise manage these script results
                  files. It is up to the SROS system operator or manager to
                  manage retrieval and cleanup of these files."

        VARIATION   smLaunchControl
            SYNTAX  INTEGER {
                       abort                (1),
                    -- suspend              (2)
                    -- resume               (3)
                       nop                  (4)
                    }
            DESCRIPTION
                 "The 'suspend (2)' and 'resume (3)' controls are not supported.
                  An attempt to set either value results in an 'wrongValue'
                  error. A read on this object always returns 'nop (4)'."

        VARIATION   smLaunchEntry
            DESCRIPTION
                 "A maximum of 255 smLaunchEntry rows are allowed to be
                  created."

        VARIATION   smLaunchExpireTime
            DESCRIPTION
                 "Unlike smLaunchLifeTime, the mib does not specify a value for
                  smLaunchExpireTime that can be used to indicate an associated
                  smRunEntry with a smRunState equal to 'terminated' should be
                  kept forever and never aged out. This agent uses the maximum
                  value (2147483647) to specify that an smRunEntry does not age
                  out after their smRunState transitions to 'terminated'. A
                  terminated smRunEntry with a maximum smRunExpireTime value
                  will never be removed from the table."

        VARIATION   smLaunchMaxCompleted
            SYNTAX  Unsigned32 (1..255)
            DESCRIPTION
                 "A maximum of 255 finished scripts invoked from this entry in
                  the smLaunchTable are allowed to be retained in the
                  smRunTable. Whenever the value of this object is changed and
                  whenever a script terminates, entries in the smRunTable are
                  deleted if necessary until the number of completed scripts is
                  smaller than the value of this object. Scripts whose
                  smRunEndTime value indicates the oldest completion time are
                  deleted first."

        VARIATION   smLaunchMaxRunning
            SYNTAX  Unsigned32 (1)
            DESCRIPTION
                 "Concurrently running scripts are not supported by this agent.
                  Scripts are queued and executed one at a time. An attempt to
                  set smLaunchMaxRunning to any value other than 1 results in an
                  'wrong`Value' error."

        VARIATION   smLaunchOwner
            SYNTAX  SnmpAdminString (SIZE (1..32))
            DESCRIPTION
                 "The minimum length of smLaunchOwner is 1 when creating new
                  entries in tables via SNMP SET requests."

        VARIATION   smLaunchRowExpireTime
            ACCESS  read-only
            DESCRIPTION
                 "smLaunchRowExpireTime functionality is not supported. The
                  default value 2147483647 is always returned to indicate that
                  the smLaunchTable row entry will never be aged out."

        VARIATION   smLaunchRunIndexNext
            DESCRIPTION
                 "The mib requires that subsequent reads of smLaunchRunIndexNext
                  must return different values. This agent does not increment
                  the value with every read. A read always returns the next
                  available index value."

        VARIATION   smLaunchStart
            DESCRIPTION
                 "In the 4.0 release there is no user access rights checking to
                  verify that the user setting smLaunchStart has read-access to
                  the script. A user command access profile with RADIUS/TACACS+
                  authentication will be associated to the script in a later
                  release.

                  The mib requires that in order for a set to smLaunchStart to
                  succeed the number of concurrently executing scripts must be
                  less than the value of smLaunchMaxRunning. This agent does not
                  support execution of more than one script at a time. Instead,
                  a smRunEntry is created with smRunState equal to
                  'initializing' and sequentially queued for later execution.
                  The maximum number of smRunEntry rows is limited to 255
                  regardless of the value of smRunState.

                  The mib specifies that when the smRunEntry is created by
                  setting smLaunchStart, the smRunStartTime should be set to the
                  current time. Because of the one-at-a-time queuing for
                  execution there may be a long time between entering the
                  'initializing' state and transitioning to the 'executing'
                  state, this agent does not set smRunStartTime until smRunState
                  transitions to 'executing'."

        VARIATION   smLaunchStorageType
            SYNTAX  INTEGER {
                    -- other                (1)
                    -- volatile             (2)
                       nonVolatile          (3)
                    -- permanent            (4)
                    -- readOnly             (5)
                    }
            DEFVAL  { nonVolatile  }
            DESCRIPTION
                 "This agent supports only 'nonVolatile (3)' storage type. This
                  is interpreted to be the desired storage type for the
                  configuration of the launch entry.

                  When smLaunchStorageType has a value of 'nonVolatile (3)' its
                  configuration is written to the configuration file upon a
                  'save configuration' operation. If the system reboots between
                  the time this row entry is created and before a 'save
                  configuration' operation is made, this row entry will NOT be
                  restored following the reboot."

        VARIATION   smRunArgument
            SYNTAX  OCTET STRING (SIZE (0..255))
            DESCRIPTION
                 "The maximum size string returned by a read of smRunArgument is
                  255 octets."

        VARIATION   smRunControl
            SYNTAX  INTEGER {
                       abort                (1),
                    -- suspend              (2)
                    -- resume               (3)
                       nop                  (4)
                    }
            DESCRIPTION
                 "The 'suspend (2)' and 'resume (3)' controls are not supported.
                  An attempt to set either value results in an
                  'inconsistentValue' error."

        VARIATION   smRunEntry
            DESCRIPTION
                 "A maximum of 255 smRunEntry rows are allowed to be created
                  regardless of the value of smRunState."

        VARIATION   smRunExpireTime
            DESCRIPTION
                 "Unlike smRunLifeTime, the mib does not specify a value for
                  smRunExpireTime that can be used to indicate this smRunEntry
                  should be kept forever and never aged out. This agent uses the
                  maximum value (2147483647) to specify that this smRunEntry
                  does not age out after its smRunState transitions to
                  'terminated'.

                  If smRunExpireTime is set to its maximum value (2147483647),
                  either by a set operation or by its initialization from the
                  smLaunchExpireTime object, then it does not tick backwards. A
                  terminated script with a maximum smRunExpireTime value thus is
                  never aged out and removed from the table."

        VARIATION   smRunLifeTime
            DESCRIPTION
                 "It is not clear from the mib if smRunLifeTime starts to tick
                  backwards when smRunState equals 'initializing' or when
                  smRunState equals 'executing'. This agent implementation
                  starts to decrement smRunLifeTime when smRunState transitions
                  to 'executing'."

        VARIATION   smRunResult
            SYNTAX  OCTET STRING (SIZE (0..255))
            DESCRIPTION
                 "The maximum size string returned by a read of smRunResult is
                  255 octets."

        VARIATION   smRunStartTime
            DESCRIPTION
                 "It is not clear from the mib if smRunStartTime is set when
                  smRunState transitions to 'initializing' or not until
                  smRunState transitions to 'executing'. This agent
                  implementation sets smRunStartTime when smRunState transitions
                  to 'executing'."

        VARIATION   smRunState
            SYNTAX  INTEGER {
                       initializing         (1),
                       executing            (2),
                    -- suspending           (3)
                    -- suspended            (4)
                    -- resuming             (5)
                       aborting             (6),
                       terminated           (7)
                    }
            DESCRIPTION
                 "The 'suspending (3)', 'suspended (4)', and 'resuming (5)'
                  states are not supported."

        VARIATION   smScriptAbort
            DESCRIPTION
                 "The smScriptAbort notification has tmnxSmRunExtAuthType and
                  tmnxSmRunExtUserName appended to the variable list."

        VARIATION   smScriptAdminStatus
            SYNTAX  INTEGER {
                       enabled              (1),
                       disabled             (2)
                    -- editing              (3)
                    }
            DESCRIPTION
                 "The smScriptAdminStatus state 'editing (3)' is not supported
                  because smCodeTable is not supported."

        VARIATION   smScriptDescr
            SYNTAX  SnmpAdminString (SIZE (0..80))
            DESCRIPTION
                 "The maximum size string supported for smScriptDescr is 80
                  octets."

        VARIATION   smScriptEntry
            DESCRIPTION
                 "A maximum of 255 smScriptEntry rows are allowed to be
                  created."

        VARIATION   smScriptException
            DESCRIPTION
                 "The smScriptException notification has tmnxSmRunExtAuthType
                  and tmnxSmRunExtUserName appended to the variable list."

        VARIATION   smScriptLanguage
            SYNTAX  Integer32 (1)
            DESCRIPTION
                 "The only script language supported is the TiMOS CLI that has
                  an smLangIndex value equal 1. smScriptLanguage can only be set
                  to the value 1."

        VARIATION   smScriptOwner
            SYNTAX  SnmpAdminString (SIZE (1..32))
            DESCRIPTION
                 "The minimum length of smScriptOwner is 1 when creating new
                  entries in tables via SNMP SET requests."

        VARIATION   smScriptResult
            DESCRIPTION
                 "The smScriptResult notification has tmnxSmRunExtAuthType and
                  tmnxSmRunExtUserName appended to the variable list."

        VARIATION   smScriptSource
            DESCRIPTION
                 "The mib requires that when smScriptAdminStatus is set to
                  'enabled', the agent at that point should 'pull' the script
                  from local cflash or remote URL if one is specified. This
                  agent does not 'pull' scripts to its local storage. The URL
                  specified in smScriptSource is passed as an argument to the
                  CLI 'exec' command when the smRunState transitions to
                  'executing'.

                  The mib states that an empty URL implies that the script
                  source is already in local storage and are located by some
                  implementation specific mapping scheme between the local
                  storage file name and the smScriptName index. This agent does
                  not support this behavior. An empty smScriptSource URL causes
                  an attempt to set a value to smLaunchStart to return an
                  'inconsistentValue' error."

        VARIATION   smScriptStorageType
            DEFVAL  { nonVolatile  }
            DESCRIPTION
                 "This agent supports only 'nonVolatile' storage type. This is
                  interpreted to be the desired storage type for the
                  configuration of the script row entry.

                  When smLaunchStorageType has a value of 'nonVolatile' its
                  configuration is written to the configuration file upon a
                  'save configuration' operation. If the system reboots between
                  the time this row entry is created and before a 'save
                  configuration' operation is made, this row entry will NOT be
                  restored following the reboot."

    ::= { tmnxSROSAgentV14v0  48 }

--
-- SROS DHCP_SERVER CAPABILITIES
--
tmnxSROSDhcpServerV14v0           AGENT-CAPABILITIES
    PRODUCT-RELEASE "Nokia SROS"
    STATUS          current
    DESCRIPTION
         "Implementation of DHCP server capabilities for Nokia SROS systems
          release 14.0."

    SUPPORTS        TIMETRA-DHCP-SERVER-MIB
        INCLUDES {
           tmnxDhcpAddrListGroup,
           tmnxDhcpLeaseGroup,
           tmnxDhcpLeaseV12v0Group,
           tmnxDhcpServerDuidGroup,
           tmnxDhcpServerStickyLseGroup,
           tmnxDhcpServerV10v0Group,
           tmnxDhcpServerV12v0Group,
           tmnxDhcpServerV13v0Group,
           tmnxDhcpServerV8v0Group,
           tmnxDhcpServerV9v0Group,
           tmnxDhcpStatsV11v0Group,
           tmnxDhcpStatsV13v0Group,
           tmnxDhcpStatsV8v0Group,
           tmnxDhcpStatsV9v0Group,
           tmnxDhcpSvrFoNotifGroup,
           tmnxDhcpSvrNotifGroup,
           tmnxDhcpSvrNotifV10v0Group,
           tmnxDhcpSvrNotifV12v0Group,
           tmnxDhcpSvrNotifV13v0Group,
           tmnxDhcpToolsGroup,
           tmnxDhcpsFailoverGroup,
           tmnxDhcpsFailoverV10v0Group,
           tmnxDhcpsFailoverV11v0Group,
           tmnxDhcpsFailoverV12v0Group,
           tmnxDhcpsPrefixLenExtensionGroup
        }

        VARIATION   tmnxDhcpServerCfgAdminState
            SYNTAX  INTEGER {
                    -- noop                 (1)
                       inService            (2),
                       outOfService         (3)
                    }
            DESCRIPTION
                 "tmnxDhcpServerCfgAdminState supports only the values
                  'inService (2)' and 'outOfService (3)'."

        VARIATION   tmnxDhcpServerDuidEnIdDataType
            SYNTAX  INTEGER {
                    -- ipv4(1)
                       ascii(2),
                       hex(3)
                    -- ipv6(4)
                    -- domain(5)
                    }
            DESCRIPTION
                 "The only allowed values for this object are 'ascii(2)' and
                  'hex(3)'."

        VARIATION   tmnxDhcpsStickyLseActAddress
            SYNTAX  InetAddressType {
                       unknown              (0),
                       ipv4                 (1)
                    -- ipv6                 (2)
                    -- ipv4z                (3)
                    -- ipv6z                (4)
                    -- dns                  (16)
                    }
            DESCRIPTION
                 "tmnxDhcpsStickyLseActAddress supports only the InetAddressType
                  values 'unknown (0)' and 'ipv4 (1)'."

    ::= { tmnxSROSAgentV14v0  57 }

--
-- 7950 DHCP_SERVER CAPABILITIES
--
tmnx7950DhcpServerV14v0           AGENT-CAPABILITIES
    PRODUCT-RELEASE "Nokia SROS"
    STATUS          current
    DESCRIPTION
         "Implementation of DHCP server capabilities for Nokia 7950 systems
          release 14.0."

--    SUPPORTS        TIMETRA-DHCP-SERVER-MIB
--        INCLUDES {
--        }

    ::= { tmnx7950AgentV14v0  57 }

--
-- SROS DIAMETER CAPABILITIES
--
tmnxSROSDiameterV14v0             AGENT-CAPABILITIES
    PRODUCT-RELEASE "Nokia SROS"
    STATUS          current
    DESCRIPTION
         "Implementation of DIAMETER capabilities for Nokia SROS systems release
          14.0."

    SUPPORTS        TIMETRA-DIAMETER-MIB
        INCLUDES {
           tmnxDiamObsoleteGroup,
           tmnxDiameterBaseV14v0Group,
           tmnxDiameterGyEfhGroup,
           tmnxDiameterNasreqV14v0Group,
           tmnxDiameterNotifyV14v0Group,
           tmnxDiameterPeerStatsGroup,
           tmnxDiameterProxyV14v0Group,
           tmnxDiameterV12v0Group,
           tmnxDiameterV13v0Group,
           tmnxDiameterV14v0Group
        }

        VARIATION   tmnxDiamAppPlcyRowStatus
            SYNTAX  RowStatus {
                       active               (1),
                    -- notInService         (2)
                    -- notReady             (3)
                       createAndGo          (4),
                    -- createAndWait        (5)
                       destroy              (6)
                    }
            DESCRIPTION
                 "tmnxDiamAppPlcyRowStatus supports only 'active (1)',
                  'createAndGo (4)', and 'destroy (6)'."

        VARIATION   tmnxDiamPlcyRowStatus
            SYNTAX  RowStatus {
                       active               (1),
                    -- notInService         (2)
                    -- notReady             (3)
                       createAndGo          (4),
                    -- createAndWait        (5)
                       destroy              (6)
                    }
            DESCRIPTION
                 "tmnxDiamPlcyRowStatus supports only 'active (1)', 'createAndGo
                  (4)', and 'destroy (6)'."

    ::= { tmnxSROSAgentV14v0  77 }

--
-- SROS DOT1AG_CFM CAPABILITIES
--
tmnxSROSDot1agCfmV14v0            AGENT-CAPABILITIES
    PRODUCT-RELEASE "Nokia SROS"
    STATUS          current
    DESCRIPTION
         "Implementation of Dot1ag CFM capabilities for Nokia SROS systems
          release 14.0."

    SUPPORTS        IEEE8021-CFM-MIB
        INCLUDES {
-- EXCLUDE dot1agCfmConfigErrorListGroup,
           dot1agCfmDefaultMdGroup,
           dot1agCfmMaGroup,
           dot1agCfmMdGroup,
           dot1agCfmMepDbGroup,
           dot1agCfmMepGroup,
           dot1agCfmNotificationsGroup
-- EXCLUDE dot1agCfmStackGroup,
-- EXCLUDE dot1agCfmVlanIdGroup,
        }

        VARIATION   dot1agCfmDefaultMdComponentId
            SYNTAX  Dot1agCfmPbbComponentIdentifier (1..2147483647)
            DESCRIPTION
                 "dot1agCfmDefaultMdComponentId supports a range from 1 to
                  2147483647."

        VARIATION   dot1agCfmDefaultMdDefIdPermission
            ACCESS  read-only
            DESCRIPTION
                 "dot1agCfmDefaultMdDefIdPermission is implemented as read-only
                  in Nokia SROS series systems. This object only supports its
                  default value."

        VARIATION   dot1agCfmDefaultMdDefLevel
            ACCESS  read-only
            DESCRIPTION
                 "dot1agCfmDefaultMdDefLevel is implemented as read-only in
                  Nokia SROS series systems. This object only supports its
                  default value."

        VARIATION   dot1agCfmDefaultMdDefMhfCreation
            ACCESS  read-only
            DESCRIPTION
                 "dot1agCfmDefaultMdDefMhfCreation is implemented as read-only
                  in Nokia SROS series systems. This object only supports its
                  default value."

        VARIATION   dot1agCfmDefaultMdIdPermission
            SYNTAX  Dot1agCfmIdPermission {
                       sendIdNone           (1),
                       sendIdChassis        (2),
                    -- sendIdManage         (3)
                    -- sendIdChassisManage  (4)
                       sendIdDefer          (5)
                    }
            DESCRIPTION
                 "dot1agCfmDefaultMdIdPermission only supports the values
                  'sendIdNone (1)', 'sentIdChassis (2)', and 'sendIdDefer (5)'."

        VARIATION   dot1agCfmDefaultMdPrimaryVid
            SYNTAX  VlanIdOrNone
            DESCRIPTION
                 "dot1agCfmDefaultMdPrimaryVid supports a VlanId of 0."

        VARIATION   dot1agCfmMaCompIdPermission
            SYNTAX  Dot1agCfmIdPermission {
                       sendIdNone           (1),
                       sendIdChassis        (2)
                    -- sendIdManage         (3)
                    -- sendIdChassisManage  (4)
                    -- sendIdDefer          (5)
                    }
            DEFVAL  { sendIdNone  }
            DESCRIPTION
                 "dot1agCfmMaCompIdPermission defaults to 'sendIdNone (1)'.
                  Supports the value 'sendIdChassis (2)' in addition to the
                  default."

        VARIATION   dot1agCfmMaCompMhfCreation
            SYNTAX  Dot1agCfmMhfCreation {
                       defMHFnone           (1),
                    -- defMHFdefault        (2)
                       defMHFexplicit       (3),
                    -- defMHFdefer          (4)
                       defMHFstatic         (32)
                    }
            DEFVAL  { defMHFnone  }
            DESCRIPTION
                 "dot1agCfmMaCompMhfCreation defaults to 'defMHFnone' if not
                  specified.

                  The SROS supports a proprietary value:

                  defMHFstatic (32) - multiple MHFs can be created on the
                  primary VID on any bridge port through which this primary VID
                  can pass, provided that any existing MEP is created at a lower
                  MD level."

        VARIATION   dot1agCfmMaComponentId
            DESCRIPTION
                 "dot1agCfmMaComponentId supports a smaller range than specified
                  in the IEEE-8021-CFM-MIB. The SROS series supports the range
                  of 1..2147483647."

        VARIATION   dot1agCfmMaNetCcmInterval
            SYNTAX  INTEGER {
                    -- intervalInvalid      (0)
                    -- interval300Hz        (1)
                       interval10ms         (2),
                       interval100ms        (3),
                       interval1s           (4),
                       interval10s          (5),
                       interval1min         (6),
                       interval10min        (7)
                    }
            DEFVAL  { interval10s  }
            DESCRIPTION
                 "dot1agCfmMaNetCcmInterval defaults to 'interval10s' if not
                  specified, and does not support anything lower than
                  interval10ms."

        VARIATION   dot1agCfmMaNetFormat
            SYNTAX  INTEGER {
                       primaryVid           (1),
                       charString           (2),
                       unsignedInt16        (3),
                       rfc2865VpnId         (4),
                       iccBased             (32)
                    }
            DEFVAL  { unsignedInt16  }
            DESCRIPTION
                 "dot1agCfmMaNetFormat defaults to 'unsignedInt16' if not
                  specified. The value 'iccBased (32)' is supported for Y.1731
                  MEPs. The dot1agCfmMaNetName must be between 8 and 13
                  characters (inclusive) long when dot1agCfmMaNetFormat is set
                  to 'iccBased (32)'."

        VARIATION   dot1agCfmMdMhfCreation
            SYNTAX  Dot1agCfmMhfCreation {
                       defMHFnone           (1)
                    -- defMHFdefault        (2)
                    -- defMHFexplicit       (3)
                    }
            DESCRIPTION
                 "dot1agCfmMdMhfCreation only supports 'defMHFnone (1)'."

        VARIATION   dot1agCfmMdMhfIdPermission
            SYNTAX  Dot1agCfmIdPermission {
                       sendIdNone           (1)
                    -- sendIdChassis        (2)
                    -- sendIdManage         (3)
                    -- sendIdChassisManage  (4)
                    -- sendIdDefer          (5)
                    }
            DESCRIPTION
                 "dot1agCfmMdMhfIdPermission only supports 'sendIdNone (1)'."

        VARIATION   dot1agCfmMdName
            SYNTAX  OCTET STRING (SIZE (0..43))
            DESCRIPTION
                 "dot1agCfmMdName supports a zero-length name when
                  dot1agCfmMdFormat is set to 'none (1)'."

        VARIATION   dot1agCfmMepCcmLtmPriority
            DEFVAL  { 7  }
            DESCRIPTION
                 "dot1agCfmMepCcmLtmPriority defaults to 7, if not specified."

        VARIATION   dot1agCfmMepDbChassisId
            SYNTAX  OCTET STRING (SIZE (0..255))
            DESCRIPTION
                 "The value of this object can be the zero-length string."

        VARIATION   dot1agCfmMepDbManAddress
            SYNTAX  OCTET STRING (SIZE (0..255))
            DESCRIPTION
                 "The value of this object can be the zero-length string."

        VARIATION   dot1agCfmMepErrorCcmLastFailure
            SYNTAX  OCTET STRING (SIZE(0..1522))
            DESCRIPTION
                 "dot1agCfmMepErrorCcmLastFailure supports a size of 0 octets."

        VARIATION   dot1agCfmMepFngAlarmTime
            SYNTAX  TimeInterval (0|250|500|1000)
            DEFVAL  { 0  }
            DESCRIPTION
                 "The range for dot1agCfmMepFngAlarmTime is changed from
                  (250..1000) to (0|250|500|1000) with a default value of 0."

        VARIATION   dot1agCfmMepFngResetTime
            SYNTAX  TimeInterval (0|250|500|1000)
            DEFVAL  { 0  }
            DESCRIPTION
                 "The range for dot1agCfmMepFngResetTime is changed from
                  (250..1000) to (0|250|500|1000) with a default value of 0."

        VARIATION   dot1agCfmMepLowPrDef
            DESCRIPTION
                 "dot1agCfmMepLowPrDef will default to allDef (1) for MEPs on
                  eth-tunnel or eth-ring paths, macRemErrXcon (2) otherwise."

        VARIATION   dot1agCfmMepPrimaryVid
            SYNTAX  Unsigned32
            DESCRIPTION
                 "dot1agCfmMepPrimaryVid supports the entire Unsigned32 range of
                  values. This is to facilitate Q-in-Q encapsulation for SAPs."

        VARIATION   dot1agCfmMepRowStatus
            SYNTAX  RowStatus {
                       active               (1),
                    -- notInService         (2)
                    -- notReady             (3)
                       createAndGo          (4),
                    -- createAndWait        (5)
                       destroy              (6)
                    }
            DESCRIPTION
                 "dot1agCfmMepRowStatus supports only 'active (1)', 'createAndGo
                  (4)', and 'destroy (6)'.

                  The use of dot1agCfmMepRowStatus is being deprecated in favor
                  of TIMETRA-IEEE8021-CFM-MIB:: tmnxDot1agCfmMepMgmtRowStatus
                  for extended SROS endpoint functionality. ACCESS of this
                  object may be restricted to 'read-only' in a future release."

        VARIATION   dot1agCfmMepTransmitLbmDestIsMepId
            DEFVAL  { false  }
            DESCRIPTION
                 "dot1agCfmMepTransmitLbmDestIsMepId defaults to, and only
                  supports the value false."

        VARIATION   dot1agCfmMepTransmitLbmDestMepId
            DEFVAL  { 0  }
            DESCRIPTION
                 "dot1agCfmMepTransmitLbmDestMepId defaults to, and only
                  supports the value zero (0)."

        VARIATION   dot1agCfmMepTransmitLbmMessages
            SYNTAX  Integer32 (0..1024)
            DEFVAL  { 0  }
            DESCRIPTION
                 "dot1agCfmMepTransmitLbmMessages supports a range from 0 to
                  1024 messages and defaults to 0."

        VARIATION   dot1agCfmMepTransmitLbmStatus
            ACCESS  read-only
            DESCRIPTION
                 "dot1agCfmMepTransmitLbmStatus is implemented as read-only on
                  Nokia SROS in release 14.0."

        VARIATION   dot1agCfmMepTransmitLbmVlanDropEnable
            ACCESS  read-only
            DESCRIPTION
                 "dot1agCfmMepTransmitLbmVlanDropEnable is implemented as
                  read-only and only supports the value of false."

        VARIATION   dot1agCfmMepTransmitLtmEgressIdentifier
            ACCESS  read-only
            DESCRIPTION
                 "dot1agCfmMepTransmitLtmEgressIdentifier is implemented as
                  read-only on Nokia SROS in release 14.0."

        VARIATION   dot1agCfmMepTransmitLtmTargetIsMepId
            DEFVAL  { false  }
            DESCRIPTION
                 "dot1agCfmMepTransmitLtmTargetIsMepId defaults to, and only
                  supports the value false."

        VARIATION   dot1agCfmMepXconCcmLastFailure
            SYNTAX  OCTET STRING (SIZE(0..1522))
            DESCRIPTION
                 "dot1agCfmMepXconCcmLastFailure supports a size of 0 octets."

    SUPPORTS        TIMETRA-IEEE8021-CFM-MIB
        INCLUDES {
           tmnxDot1agCfmCLENotifyGroupV14v0,
           tmnxDot1agCfmCSFNotifyGroupV11v0,
           tmnxDot1agCfmDefaultMdGroupV14v0,
           tmnxDot1agCfmGPGroupV10v0,
           tmnxDot1agCfmGlobalGroupV9v0,
           tmnxDot1agCfmMEPMgmtGroupV11v0,
           tmnxDot1agCfmMaGroupV10v0,
           tmnxDot1agCfmMaGroupV11v0,
           tmnxDot1agCfmMaGroupV12v0,
           tmnxDot1agCfmMaGroupV9v0,
           tmnxDot1agCfmMdGroupV11v0,
           tmnxDot1agCfmMepCSFGroupV11v0,
           tmnxDot1agCfmMepGroupV10v0,
           tmnxDot1agCfmMepGroupV12v0,
           tmnxDot1agCfmMepGroupV13v0,
           tmnxDot1agCfmMepGroupV7v0,
           tmnxDot1agCfmMepGroupV8v0,
           tmnxDot1agCfmMepGroupV9v0,
           tmnxDot1agCfmMepMcastLbmGroup,
           tmnxDot1agCfmMepSlmGroupV9v0,
           tmnxDot1agCfmMepSlmNotifyGroup,
           tmnxDot1agCfmMepSlmTWGroupV10v0,
           tmnxDot1agCfmMipGroupV8v0,
           tmnxDot1agCfmMipNotifyGroup,
           tmnxDot1agCfmNotificationGroup,
           tmnxDot1agCfmSapStackGroup,
           tmnxDot1agCfmScalarsGroupV12v0,
           tmnxDot1agCfmSdpBindStackGroup,
           tmnxDot1agCfmStatsGroupV10v0,
           tmnxDot1agCfmStatsGroupV12v0,
           tmnxDot1agCfmXmppEnhGroup,
           tmnxDot1agNotifyObjsGroupV14v0,
           tmnxY1731CfmNotificationGroup
        }

        VARIATION   tmnxDot1agCfmMepAisLowPrioDef
            SYNTAX  INTEGER {
                       allDef               (1),
                       macRemErrXcon        (2)
                    -- remErrXcon           (3)
                    -- errXcon              (4)
                    -- xcon                 (5)
                    -- noXcon               (6)
                    }
            DESCRIPTION
                 "tmnxDot1agCfmMepAisLowPrioDef defaults to 'allDef' if not
                  specified, and does not support remErrXcon, errXcon, xcon and
                  noXcon."

        VARIATION   tmnxDot1agCfmMepEthTestPattern
            SYNTAX  INTEGER {
                       allZerosNoCrc        (0),
                       allZerosCrc          (1),
                    -- prbsNoCrc            (2)
                    -- prbsCrc              (3)
                       allOnesNoCrc         (4),
                       allOnesCrc           (5)
                    }
            DESCRIPTION
                 "tmnxDot1agCfmMepEthTestPattern supports all zero and all one
                  patterns only."

        VARIATION   tmnxDot1agCfmMepSlmOWTestTable
            ACCESS  not-implemented
            DESCRIPTION
                 "tmnxDot1agCfmMepSlmOWTestTable is not supported on the SROS
                  series systems."

        VARIATION   tmnxDot1agCfmMepSlmTestRsltTable
            DESCRIPTION
                 "tmnxDot1agCfmMepSlmTestRsltTable supports two-way tests only.
                  The index, tmnxDot1agCfmMepSlmTestType, is fixed to the value
                  'twoWayTest (2)'."

    ::= { tmnxSROSAgentV14v0  60 }

--
-- SROS DOT3_OAM CAPABILITIES
--
tmnxSROSDot3OamV14v0              AGENT-CAPABILITIES
    PRODUCT-RELEASE "Nokia SROS"
    STATUS          current
    DESCRIPTION
         "Implementation of Ethernet OAM (802.3ah) capabilities for Nokia SROS
          systems release 14.0."

    SUPPORTS        DOT3-OAM-MIB
        INCLUDES {
           dot3OamControlGroup,
           dot3OamErrFrameEventGroup,
           dot3OamEventLogGroup,
           dot3OamLoopbackGroup,
           dot3OamNotificationGroup,
           dot3OamPeerGroup,
           dot3OamStatsBaseGroup
        }

        VARIATION   dot3OamCriticalEventEnable
            DEFVAL  { false  }
            DESCRIPTION
                 "dot3OamCriticalEventEnable defaults to 'false (2)'."

        VARIATION   dot3OamDyingGaspEnable
            DEFVAL  { false  }
            DESCRIPTION
                 "dot3OamDyingGaspEnable defaults to 'false (2)'."

        VARIATION   dot3OamErrFramePeriodThreshold
            SYNTAX  Unsigned32 (1..1000000)
            DEFVAL  { 1  }
            DESCRIPTION
                 "The value of dot3OamErrFramePeriodThreshold specifies the
                  Signal Failure (SF) threshold for the errored frame period
                  (frame errors over a number of received frames). This object's
                  value must be higher than the Signal Degrade (SD) threshold,
                  tmnxDot3OamErrFrmPrdSdThreshold.

                  This object supports a range from 1 to 1000000 frames and
                  defaults to 1.

                  If the number of errored frames within
                  dot3OamErrFramePeriodWindow is equal to or greater than
                  dot3OamErrFramePeriodThreshold and tmnxDot3OamErrFrmPrdEnabled
                  is set to 'enabled (1)', a dot3OamThresholdEvent notification
                  is generated for an Errored Frame Period Signal Failure where
                  the operator may take further actions to shutdown the port and
                  alert the remote OAM peer."

        VARIATION   dot3OamErrFramePeriodWindow
            SYNTAX  Unsigned32 (1..4294967295)
            DEFVAL  { 1488095  }
            DESCRIPTION
                 "dot3OamErrFramePeriodWindow supports a range from 1 to
                  4294967295 frames and defaults to 1488095."

        VARIATION   dot3OamErrFrameSecsSummaryThreshold
            DESCRIPTION
                 "The value of dot3OamErrFrameSecsSummaryThreshold specifies the
                  Signal Failure (SF) threshold for errored frame seconds. This
                  object's value must be higher than the Signal Degrade (SD)
                  threshold, tmnxDot3OamErrFrmSecSdThreshold.

                  If the number of errored frames seconds within
                  dot3OamErrFrameSecsSummaryWindow is equal to or greater than
                  dot3OamErrFrameSecsSummaryThreshold and
                  tmnxDot3OamErrFrmSecEnabled is set to 'enabled (1)', a
                  dot3OamThresholdEvent notification is generated for an Errored
                  Frame Seconds Summary Signal Failure where the operator may
                  take further actions to shutdown the port and alert the remote
                  OAM peer."

        VARIATION   dot3OamErrFrameSecsSummaryWindow
            DEFVAL  { 600  }
            DESCRIPTION
                 "dot3OamErrFrameSecsSummaryWindow defaults to 600 deciseconds.
                  This object's value must be specified in increments of 10."

        VARIATION   dot3OamErrFrameThreshold
            SYNTAX  Unsigned32 (1..1000000)
            DESCRIPTION
                 "The value of dot3OamErrFrameThreshold specifies the Signal
                  Failure (SF) threshold for frame errors over a period of time.
                  This object's value must be higher than the Signal Degrade
                  (SD) threshold, tmnxDot3OamErrFrmSdThreshold.

                  This object supports a range from 1 to 1000000 frames.

                  If the number of errored frames within dot3OamErrFrameWindow
                  is equal to or greater than dot3OamErrFrameThreshold and
                  tmnxDot3OamErrFrmEnabled is set to 'enabled (1)', a
                  dot3OamThresholdEvent notification is generated for an Errored
                  Frame Signal Failure where the operator may take further
                  actions to shutdown the port and alert the remote OAM peer."

        VARIATION   dot3OamErrFrameWindow
            SYNTAX  Unsigned32 (10..600)
            DESCRIPTION
                 "dot3OamErrFrameWindow supports a range from 10 to 600
                  deciseconds. This object's value must be specified in
                  increments of 10."

        VARIATION   dot3OamErrSymPeriodThresholdHi
            ACCESS  not-implemented
            DESCRIPTION
                 "dot3OamErrSymPeriodThresholdHi is not implemented on Nokia
                  SROS in release 14.0."

        VARIATION   dot3OamErrSymPeriodThresholdLo
            SYNTAX  Unsigned32 (1..1000000)
            DEFVAL  { 1  }
            DESCRIPTION
                 "The value of dot3OamErrSymPeriodThresholdLo specifies the
                  Signal Failure (SF) threshold for symbol period errors. This
                  object's value must be higher than the Symbol Period Error
                  Signal Degrade (SD) threshold,
                  tmnxDot3OamErrSymPrdSdThreshold.

                  This object supports a range from 1 to 1000000 and defaults
                  to 1.

                  If the number of errored frames within
                  dot3OamErrSymPeriodWindowLo is equal to or greater than
                  dot3OamErrSymPeriodThresholdLo and tmnxDot3OamErrSymPrdEnabled
                  is set to 'enabled (1)', a dot3OamThresholdEvent notification
                  is generated for an Errored Symbol Period Signal Failure where
                  the operator may take further actions to shutdown the port and
                  alert the remote OAM peer."

        VARIATION   dot3OamErrSymPeriodWindowHi
            ACCESS  read-only
            DESCRIPTION
                 "dot3OamErrSymPeriodWindowHi is implemented as read-only on
                  Nokia SROS in release 14.0."

        VARIATION   dot3OamErrSymPeriodWindowLo
            ACCESS  read-only
            DESCRIPTION
                 "dot3OamErrSymPeriodWindowLo is implemented as read-only on
                  Nokia SROS in release 14.0."

        VARIATION   dot3OamThresholdEvent
            DESCRIPTION
                 "A dot3OamThresholdEvent notification is sent when a local or
                  remote Signal Failure (SF) threshold crossing event is
                  detected."

    SUPPORTS        TIMETRA-DOT3-OAM-MIB
        INCLUDES {
           tmnxDot3OamGraceGroup,
           tmnxDot3OamGroupV14v0,
           tmnxDot3OamLinkMonGroupV12v0,
           tmnxDot3OamLinkMonGroupV13v0,
           tmnxDot3OamLoopbackGroup,
           tmnxDot3OamNotificationGrpV13v0,
           tmnxDot3OamNotificationV6v0Group,
           tmnxDot3OamV11v0Group,
           tmnxDot3OamV6v0Group,
           tmnxDot3OamV6v1Group
        }

    ::= { tmnxSROSAgentV14v0  54 }

--
-- SROS DS0 CAPABILITIES
--
tmnxSROSDs0V14v0                  AGENT-CAPABILITIES
    PRODUCT-RELEASE "Nokia SROS"
    STATUS          current
    DESCRIPTION
         "Implementation of DS0 Interface Types capabilities for Nokia SROS
          systems release 14.0"

    SUPPORTS        DS0-MIB
        INCLUDES {
           ds0ConfigGroup
        }

        VARIATION   dsx0CircuitIdentifier
            ACCESS  read-only
            DESCRIPTION
                 "dsx0CircuitIdentifier is implemented as read-only on Nokia
                  SROS in release 14.0."

        VARIATION   dsx0IdleCode
            ACCESS  read-only
            DESCRIPTION
                 "dsx0IdleCode is implemented as read-only on Nokia SROS in
                  release 14.0."

        VARIATION   dsx0RobbedBitSignalling
            ACCESS  read-only
            DESCRIPTION
                 "dsx0RobbedBitSignalling is implemented as read-only on Nokia
                  SROS in release 14.0."

        VARIATION   dsx0SeizedCode
            ACCESS  read-only
            DESCRIPTION
                 "dsx0SeizedCode is implemented as read-only on Nokia SROS in
                  release 14.0."

        VARIATION   dsx0TransmitCodesEnable
            ACCESS  read-only
            DESCRIPTION
                 "dsx0TransmitCodesEnable is implemented as read-only on Nokia
                  SROS in release 14.0."

    ::= { tmnxSROSAgentV14v0   8 }

--
-- SROS DS1 CAPABILITIES
--
tmnxSROSDs1V14v0                  AGENT-CAPABILITIES
    PRODUCT-RELEASE "Nokia SROS"
    STATUS          current
    DESCRIPTION
         "Implementation of DS1, E1, DS2 and E2 Interface Types capabilities for
          Nokia SROS systems release 14.0"

    SUPPORTS        DS1-MIB
        INCLUDES {
           ds1ChanMappingGroup,
           ds1FarEndGroup,
           ds1NearEndConfigurationGroup,
           ds1NearEndOptionalConfigGroup,
           ds1NearEndOptionalTrapGroup,
           ds1NearEndStatisticsGroup,
           ds1TransStatsGroup
        }

        VARIATION   dsx1Channelization
            ACCESS  read-only
            DESCRIPTION
                 "dsx1Channelization is implemented as read-only on Nokia SROS
                  in release 14.0."

        VARIATION   dsx1CircuitIdentifier
            ACCESS  read-only
            DESCRIPTION
                 "dsx1CircuitIdentifier is implemented as read-only on Nokia
                  SROS in release 14.0."

        VARIATION   dsx1Fdl
            ACCESS  read-only
            DESCRIPTION
                 "dsx1Fdl is implemented as read-only on Nokia SROS in release
                  14.0."

        VARIATION   dsx1IfIndex
            ACCESS  not-implemented
            DESCRIPTION
                 "dsx1IfIndex is not implemented on Nokia SROS in release 14.0.

                  Deprecated object"

        VARIATION   dsx1LineBuildOut
            ACCESS  not-implemented
            DESCRIPTION
                 "dsx1LineBuildOut notification is not implemented."

        VARIATION   dsx1LineCoding
            ACCESS  read-only
            DESCRIPTION
                 "dsx1LineCoding is implemented as read-only on Nokia SROS in
                  release 14.0."

        VARIATION   dsx1LineLength
            ACCESS  read-only
            DESCRIPTION
                 "dsx1LineLength is implemented as read-only on Nokia SROS in
                  release 14.0."

        VARIATION   dsx1LineMode
            ACCESS  not-implemented
            DESCRIPTION
                 "dsx1LineMode notification is not implemented."

        VARIATION   dsx1LineStatusChange
            ACCESS  not-implemented
            DESCRIPTION
                 "dsx1LineStatusChange notification is not implemented."

        VARIATION   dsx1LineStatusChangeTrapEnable
            ACCESS  read-only
            DESCRIPTION
                 "dsx1LineStatusChangeTrapEnable is implemented as read-only on
                  Nokia SROS in release 14.0."

        VARIATION   dsx1LineType
            ACCESS  read-only
            DESCRIPTION
                 "dsx1LineType is implemented as read-only on Nokia SROS in
                  release 14.0."

        VARIATION   dsx1LoopbackConfig
            ACCESS  read-only
            DESCRIPTION
                 "dsx1LoopbackConfig is implemented as read-only on Nokia SROS
                  in release 14.0."

        VARIATION   dsx1SendCode
            ACCESS  read-only
            DESCRIPTION
                 "dsx1SendCode is implemented as read-only on Nokia SROS in
                  release 14.0."

        VARIATION   dsx1SignalMode
            ACCESS  read-only
            DESCRIPTION
                 "dsx1SignalMode is implemented as read-only on Nokia SROS in
                  release 14.0."

        VARIATION   dsx1TransmitClockSource
            ACCESS  read-only
            DESCRIPTION
                 "dsx1TransmitClockSource is implemented as read-only on Nokia
                  SROS in release 14.0."

    ::= { tmnxSROSAgentV14v0   9 }

--
-- SROS DS3 CAPABILITIES
--
tmnxSROSDs3V14v0                  AGENT-CAPABILITIES
    PRODUCT-RELEASE "Nokia SROS"
    STATUS          current
    DESCRIPTION
         "Implementation of DS3 and E3 Interface Types capabilities for Nokia
          SROS systems release 14.0."

    SUPPORTS        DS3-MIB
        INCLUDES {
           ds3FarEndGroup,
           ds3NearEndConfigGroup,
           ds3NearEndOptionalConfigGroup,
           ds3NearEndOptionalTrapGroup,
           ds3NearEndStatisticsGroup
        }

        VARIATION   dsx3Channelization
            ACCESS  read-only
            DESCRIPTION
                 "dsx3Channelization is implemented as read-only on Nokia SROS
                  in release 14.0."

        VARIATION   dsx3CircuitIdentifier
            ACCESS  read-only
            DESCRIPTION
                 "dsx3CircuitIdentifier is implemented as read-only on Nokia
                  SROS in release 14.0."

        VARIATION   dsx3Ds1ForRemoteLoop
            ACCESS  read-only
            DESCRIPTION
                 "dsx3Ds1ForRemoteLoop is implemented as read-only on Nokia SROS
                  in release 14.0."

        VARIATION   dsx3FarEndEquipCode
            ACCESS  read-only
            DESCRIPTION
                 "dsx3FarEndEquipCode is implemented as read-only on Nokia SROS
                  in release 14.0."

        VARIATION   dsx3FarEndFacilityIDCode
            ACCESS  read-only
            DESCRIPTION
                 "dsx3FarEndFacilityIDCode is implemented as read-only on Nokia
                  SROS in release 14.0."

        VARIATION   dsx3FarEndFrameIDCode
            ACCESS  read-only
            DESCRIPTION
                 "dsx3FarEndFrameIDCode is implemented as read-only on Nokia
                  SROS in release 14.0."

        VARIATION   dsx3FarEndLocationIDCode
            ACCESS  read-only
            DESCRIPTION
                 "dsx3FarEndLocationIDCode is implemented as read-only on Nokia
                  SROS in release 14.0."

        VARIATION   dsx3FarEndUnitCode
            ACCESS  read-only
            DESCRIPTION
                 "dsx3FarEndUnitCode is implemented as read-only on Nokia SROS
                  in release 14.0."

        VARIATION   dsx3IfIndex
            ACCESS  not-implemented
            DESCRIPTION
                 "Deprecated object"

        VARIATION   dsx3LineCoding
            ACCESS  read-only
            DESCRIPTION
                 "dsx3LineCoding is implemented as read-only on Nokia SROS in
                  release 14.0."

        VARIATION   dsx3LineLength
            ACCESS  read-only
            DESCRIPTION
                 "dsx3LineLength is implemented as read-only on Nokia SROS in
                  release 14.0."

        VARIATION   dsx3LineStatusChange
            ACCESS  not-implemented
            DESCRIPTION
                 "dsx3LineStatusChange notification is not implemented."

        VARIATION   dsx3LineStatusChangeTrapEnable
            ACCESS  read-only
            DESCRIPTION
                 "dsx3LineStatusChangeTrapEnable is implemented as read-only on
                  Nokia SROS in release 14.0."

        VARIATION   dsx3LineType
            ACCESS  read-only
            DESCRIPTION
                 "dsx3LineType is implemented as read-only on Nokia SROS in
                  release 14.0."

        VARIATION   dsx3LoopbackConfig
            ACCESS  read-only
            DESCRIPTION
                 "dsx3LoopbackConfig is implemented as read-only on Nokia SROS
                  in release 14.0."

        VARIATION   dsx3SendCode
            ACCESS  read-only
            DESCRIPTION
                 "dsx3SendCode is implemented as read-only on Nokia SROS in
                  release 14.0."

        VARIATION   dsx3TransmitClockSource
            ACCESS  read-only
            DESCRIPTION
                 "dsx3TransmitClockSource is implemented as read-only on Nokia
                  SROS in release 14.0."

    ::= { tmnxSROSAgentV14v0  10 }

--
-- SROS DYN_SRV CAPABILITIES
--
tmnxSROSDynSrvV14v0               AGENT-CAPABILITIES
    PRODUCT-RELEASE "Nokia SROS"
    STATUS          current
    DESCRIPTION
         "Implementation of Dynamic Services on Nokia SROS release R11.0."

    SUPPORTS        TIMETRA-DYNAMIC-SERVICES-MIB
        INCLUDES {
           tmnxDynSvcNotifyGroup,
           tmnxDynSvcV14v0Group
        }

        VARIATION   tmnxDynSvcCaptureSapAdminState
            SYNTAX  INTEGER {
                    -- noop                 (1)
                       inService            (2),
                       outOfService         (3)
                    }
            DESCRIPTION
                 "tmnxDynSvcCaptureSapAdminState supports only the values
                  'inService (2)' and 'outOfService (3)'."

        VARIATION   tmnxDynSvcLocADbUsrAdminState
            SYNTAX  INTEGER {
                    -- noop                 (1)
                       inService            (2),
                       outOfService         (3)
                    }
            DESCRIPTION
                 "tmnxDynSvcLocADbUsrAdminState supports only the values
                  'inService (2)' and 'outOfService (3)'."

        VARIATION   tmnxDynSvcLocAuthDbAdminState
            SYNTAX  INTEGER {
                    -- noop                 (1)
                       inService            (2),
                       outOfService         (3)
                    }
            DESCRIPTION
                 "tmnxDynSvcLocAuthDbAdminState supports only the values
                  'inService (2)' and 'outOfService (3)'."

        VARIATION   tmnxDynSvcPlcyRowStatus
            SYNTAX  RowStatus {
                       active               (1),
                    -- notInService         (2)
                    -- notReady             (3)
                       createAndGo          (4),
                    -- createAndWait        (5)
                       destroy              (6)
                    }
            DESCRIPTION
                 "tmnxDynSvcPlcyRowStatus supports only 'active (1)',
                  'createAndGo (4)', and 'destroy (6)'."

    ::= { tmnxSROSAgentV14v0  85 }

--
-- SROS ELMI CAPABILITIES
--
tmnxSROSElmiV14v0                 AGENT-CAPABILITIES
    PRODUCT-RELEASE "Nokia SROS"
    STATUS          current
    DESCRIPTION
         "Implementation of the E-LMI features on Nokia SROS systems release
          14.0."

    SUPPORTS        TIMETRA-ELMI-MIB
        INCLUDES {
           tmnxElmiEvcConfigGroup,
           tmnxElmiEventGroup,
           tmnxElmiIfConfigGroup,
           tmnxElmiStatsGroup,
           tmnxElmiTimeStampGroup
        }

        VARIATION   tmnxElmiEvcCfgIdentifier
            ACCESS  read-only
            DESCRIPTION
                 "tmnxElmiEvcCfgIdentifier is implemented as read-only on Nokia
                  SROS in release 14.0."

        VARIATION   tmnxElmiIfCfgMode
            SYNTAX  INTEGER {
                       none                 (0),
                       uniN                 (1)
                    -- uniC                 (2)
                    }
            DESCRIPTION
                 "tmnxElmiIfCfgMode supports the values 'none (0)' and 'uniN
                  (1)' only."

        VARIATION   tmnxElmiIfCfgUniIdentifier
            ACCESS  read-only
            DESCRIPTION
                 "tmnxElmiIfCfgUniIdentifier is implemented as read-only on
                  Nokia SROS in release 14.0."

    ::= { tmnxSROSAgentV14v0  73 }

--
-- SROS ETHER_LIKE CAPABILITIES
--
tmnxSROSEtherLikeV14v0            AGENT-CAPABILITIES
    PRODUCT-RELEASE "Nokia SROS"
    STATUS          current
    DESCRIPTION
         "Implementation of Ethernet-like network interfaces capabilities for
          Nokia SROS systems release 14.0"

    SUPPORTS        EtherLike-MIB
        INCLUDES {
-- EXCLUDE etherCollisionTableGroup
           etherControlGroup,
           etherControlPauseGroup,
           etherDuplexGroup,
           etherHCControlPauseGroup,
-- EXCLUDE etherHCStatsGroup
-- EXCLUDE etherRateControlGroup
           etherStatsBaseGroup,
           etherStatsHighSpeedGroup,
           etherStatsLowSpeedGroup
        }

        VARIATION   dot3ControlInUnknownOpcodes
            ACCESS  not-implemented
            DESCRIPTION
                 "dot3ControlInUnknownOpcodes is not implemented on Nokia SROS
                  in release 14.0."

        VARIATION   dot3HCControlInUnknownOpcodes
            ACCESS  not-implemented
            DESCRIPTION
                 "dot3HCControlInUnknownOpcodes is not implemented on Nokia SROS
                  in release 14.0."

        VARIATION   dot3PauseAdminMode
            ACCESS  not-implemented
            DESCRIPTION
                 "dot3PauseAdminMode is not implemented on Nokia SROS in release
                  14.0."

        VARIATION   dot3PauseOperMode
            ACCESS  not-implemented
            DESCRIPTION
                 "dot3PauseOperMode is not implemented on Nokia SROS in release
                  14.0."

    ::= { tmnxSROSAgentV14v0  11 }

--
-- SROS ETHER_WIS CAPABILITIES
--
tmnxSROSEtherWisV14v0             AGENT-CAPABILITIES
    PRODUCT-RELEASE "Nokia SROS"
    STATUS          current
    DESCRIPTION
         "Implementation of Ethernet WIS capabilities for Nokia SROS systems
          release 14.0"

    SUPPORTS        ETHER-WIS
        INCLUDES {
           etherWisDeviceGroupBasic,
           etherWisFarEndPathGroup,
           etherWisPathGroup,
           etherWisSectionGroup
        }

        VARIATION   etherWisDeviceRxTestPatternErrors
            ACCESS  read-only
            DESCRIPTION
                 "etherWisDeviceRxTestPatternErrors is implemented as read-only
                  on Nokia SROS in release 14.0."

        VARIATION   etherWisDeviceRxTestPatternMode
            ACCESS  read-only
            DESCRIPTION
                 "etherWisDeviceRxTestPatternMode is implemented as read-only on
                  Nokia SROS in release 14.0."

        VARIATION   etherWisDeviceTxTestPatternMode
            ACCESS  read-only
            DESCRIPTION
                 "etherWisDeviceTxTestPatternMode is implemented as read-only on
                  Nokia SROS in release 14.0."

        VARIATION   etherWisPathCurrentJ1Transmitted
            ACCESS  read-only
            DESCRIPTION
                 "etherWisPathCurrentJ1Transmitted is implemented as read-only
                  on Nokia SROS in release 14.0."

        VARIATION   etherWisSectionCurrentJ0Transmitted
            ACCESS  read-only
            DESCRIPTION
                 "etherWisSectionCurrentJ0Transmitted is implemented as
                  read-only on Nokia SROS in release 14.0."

    ::= { tmnxSROSAgentV14v0  12 }

--
-- SROS ETH_RING CAPABILITIES
--
tmnxSROSEthRingV14v0              AGENT-CAPABILITIES
    PRODUCT-RELEASE "Nokia SROS"
    STATUS          current
    DESCRIPTION
         "Implementation of Ethernet Ring capabilities for Nokia SROS systems
          release 14.0."

    SUPPORTS        TIMETRA-ETH-RING-MIB
        INCLUDES {
           tmnxEthRingApsNotifyGroup,
           tmnxEthRingBaseConfigGroup,
           tmnxEthRingBaseConfigV9v0Group,
           tmnxEthRingBasePathGroup,
           tmnxEthRingCommandV9v0Group,
           tmnxEthRingOperNotifyGroup,
           tmnxEthRingSAPPathGroup,
           tmnxEthRingSubRingV9v0Group,
           tmnxEthRingTimeStampGroup
        }

    ::= { tmnxSROSAgentV14v0  76 }

--
-- 7750c12 ETH_RING CAPABILITIES
--
tmnx7750c12EthRingV14v0           AGENT-CAPABILITIES
    PRODUCT-RELEASE "Nokia SROS"
    STATUS          current
    DESCRIPTION
         "Implementation of Ethernet Ring capabilities for Nokia 7750 c12
          systems release 14.0."

--    SUPPORTS        TIMETRA-ETH-RING-MIB
--        INCLUDES {
--        }

    ::= { tmnx7750c12AgentV14v0  76 }

--
-- 7750c4 ETH_RING CAPABILITIES
--
tmnx7750c4EthRingV14v0            AGENT-CAPABILITIES
    PRODUCT-RELEASE "Nokia SROS"
    STATUS          current
    DESCRIPTION
         "Implementation of Ethernet Ring capabilities for Nokia 7750 c4 systems
          release 14.0."

--    SUPPORTS        TIMETRA-ETH-RING-MIB
--        INCLUDES {
--        }

    ::= { tmnx7750c4AgentV14v0  76 }

--
-- 7710 ETH_RING CAPABILITIES
--
tmnx7710EthRingV14v0              AGENT-CAPABILITIES
    PRODUCT-RELEASE "Nokia SROS"
    STATUS          current
    DESCRIPTION
         "Implementation of Ethernet Ring capabilities for Nokia 7710 systems
          release 14.0."

--    SUPPORTS        TIMETRA-ETH-RING-MIB
--        INCLUDES {
--        }

    ::= { tmnx7710AgentV14v0  76 }

--
-- SROS ETH_TUNNEL CAPABILITIES
--
tmnxSROSEthTunnelV14v0            AGENT-CAPABILITIES
    PRODUCT-RELEASE "Nokia SROS"
    STATUS          current
    DESCRIPTION
         "Implementation of the Ethernet Tunnel feature on Nokia SROS systems
          release 14.0."

    SUPPORTS        TIMETRA-ETH-TUNNEL-MIB
        INCLUDES {
           tmnxEthTunnelAPSNotifyGroup,
           tmnxEthTunnelBaseAPSGroup,
           tmnxEthTunnelBaseAPSV8v0Group,
           tmnxEthTunnelBaseConfigGroup,
           tmnxEthTunnelBaseConfigV8v0Group,
           tmnxEthTunnelBaseMemberGroup,
           tmnxEthTunnelBaseOperGroup,
           tmnxEthTunnelLEGroup,
           tmnxEthTunnelSAPMemberGroup,
           tmnxEthTunnelTimeStampGroup,
           tmnxEthTunnelTimeStampV8v0Group
        }

        VARIATION   tmnxEthTunnelIndex
            SYNTAX  Unsigned32 (1..1024)
            DESCRIPTION
                 "The tmnxEthTunnelIndex is restricted to the values 1 to 1024.
                  If the tmnxChassisAdminMode is set to a value less than 'modeD
                  (4)' the tmnxEthTunnelIndex is restricted to a maximum value
                  of 128.

                  tmnxGmplsTunGrpId and tmnxEthTunnelIndex share the same
                  number space and must be unique. For example, if a GMPLS
                  Tunnel Group exists with tmnxGmplsTunGrpId = 1, an Ethernet
                  Tunnel cannot be created with tmnxEthTunnelIndex = 1."

        VARIATION   tmnxEthTunnelLEMbrThreshold
            SYNTAX  Unsigned32 (0..15)
            DESCRIPTION
                 "The tmnxEthTunnelLEMbrThreshold is restricted to the values 0
                  to one less than the maximum value of
                  tmnxEthTunnelMemberIndex. "

        VARIATION   tmnxEthTunnelMemberIndex
            SYNTAX  Unsigned32 (1..16)
            DESCRIPTION
                 "The tmnxEthTunnelMemberIndex is restricted to the values 1 to
                  16. If the tmnxChassisAdminMode is set to a value less than
                  'modeD (4)' the tmnxEthTunnelMemberIndex is restricted to a
                  maximum value of 8."

        VARIATION   tmnxEthTunnelMemberRowStatus
            SYNTAX  RowStatus {
                       active               (1),
                    -- notInService         (2)
                    -- notReady             (3)
                       createAndGo          (4),
                    -- createAndWait        (5)
                       destroy              (6)
                    }
            DESCRIPTION
                 "tmnxEthTunnelMemberRowStatus supports only 'active (1)',
                  'createAndGo (4)', and 'destroy (6)'."

        VARIATION   tmnxEthTunnelRowStatus
            SYNTAX  RowStatus {
                       active               (1),
                    -- notInService         (2)
                    -- notReady             (3)
                       createAndGo          (4),
                    -- createAndWait        (5)
                       destroy              (6)
                    }
            DESCRIPTION
                 "tmnxEthTunnelRowStatus supports only 'active (1)',
                  'createAndGo (4)', and 'destroy (6)'."

    ::= { tmnxSROSAgentV14v0  70 }

--
-- 7750c12 ETH_TUNNEL CAPABILITIES
--
tmnx7750c12EthTunnelV14v0         AGENT-CAPABILITIES
    PRODUCT-RELEASE "Nokia SROS"
    STATUS          current
    DESCRIPTION
         "Implementation of the Ethernet Tunnel feature on Nokia 7750 c12
          systems release 14.0."

--    SUPPORTS        TIMETRA-ETH-TUNNEL-MIB
--        INCLUDES {
--        }

    ::= { tmnx7750c12AgentV14v0  70 }

--
-- 7750c4 ETH_TUNNEL CAPABILITIES
--
tmnx7750c4EthTunnelV14v0          AGENT-CAPABILITIES
    PRODUCT-RELEASE "Nokia SROS"
    STATUS          current
    DESCRIPTION
         "Implementation of the Ethernet Tunnel feature on Nokia 7750 c4 systems
          release 14.0."

--    SUPPORTS        TIMETRA-ETH-TUNNEL-MIB
--        INCLUDES {
--        }

    ::= { tmnx7750c4AgentV14v0  70 }

--
-- 7710 ETH_TUNNEL CAPABILITIES
--
tmnx7710EthTunnelV14v0            AGENT-CAPABILITIES
    PRODUCT-RELEASE "Nokia SROS"
    STATUS          current
    DESCRIPTION
         "Implementation of the Ethernet Tunnel feature on Nokia 7710 systems
          release 14.0."

--    SUPPORTS        TIMETRA-ETH-TUNNEL-MIB
--        INCLUDES {
--        }

    ::= { tmnx7710AgentV14v0  70 }

--
-- SROS FILTER CAPABILITIES
--
tmnxSROSFilterV14v0               AGENT-CAPABILITIES
    PRODUCT-RELEASE "Nokia SROS"
    STATUS          current
    DESCRIPTION
         "Implementation of ACL filters capabilities for Nokia SROS systems
          release 14.0"

    SUPPORTS        TIMETRA-FILTER-MIB
        INCLUDES {
           tDhcpFilterV10v0Group,
           tDhcpFilterV13v0Group,
           tFilterEmbedFlowspecGroup,
           tFilterEmbedVsdGroup,
           tFilterEmbeddedInsertV11v0Group,
           tFilterEmbeddedInsertV12v0Group,
           tFilterEmbeddedInsertV13v0Group,
           tFilterEmbeddedRefGroup,
           tFilterEntryStatGroup,
           tFilterIPvXRedundantActionGroup,
           tFilterLogGroup,
           tFilterLogV5v0Group,
           tFilterMacRedundantActionGroup,
           tFilterNameV10v0Group,
           tFilterNotificationObjV12v0Group,
           tFilterNotificationsV11v0Group,
           tFilterNotificationsV12v0Group,
           tFilterNotificationsV14v0Group,
           tFilterPortListV11v0Group,
           tFilterPrefListInfoGroup,
           tFilterPrefixListV11v0Group,
           tFilterRedirectPolicyV13v0Group,
           tFilterRemarkDscpExtGroup,
           tFilterRemarkDscpGroup,
           tFilterScalarGroup,
           tFilterSystemFilterV13v0Group,
           tIPFilterV13v0Group,
           tIPFilterV14v0Group,
           tIPv6FilterV13v0Group,
           tIPv6FilterV14v0Group,
           tLiFilterV12v0Group,
           tMacFilterV13v0Group,
           tMacFilterV8v0Group,
           tMacFilterVidFilteringV9v0Group
        }

        VARIATION   tAutoIPFilterEntryTable
            ACCESS  not-implemented
            DESCRIPTION
                 "The tAutoIPFilterEntryTable was made obsolete in release 3.0."

        VARIATION   tFilterEmbedFlowspecFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedFlowspecFilterType supports only the values
                  'fltrtypeselIp(1)' and 'fltrtypeselIpv6(4)'."

        VARIATION   tFilterEmbedFlowspecRowStatus
            SYNTAX  RowStatus {
                       active               (1),
                    -- notInService         (2)
                    -- notReady             (3)
                       createAndGo          (4),
                    -- createAndWait        (5)
                       destroy              (6)
                    }
            DESCRIPTION
                 "tFilterEmbedFlowspecRowStatus supports only 'active (1)',
                  'createAndGo (4)', and 'destroy (6)'."

        VARIATION   tFilterEmbedOpenflowFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedOpenflowFilterType supports only the values
                  'fltrtypeselIp(1)' and 'fltrtypeselIpv6(4)'."

        VARIATION   tFilterEmbedOpenflowRowStatus
            SYNTAX  RowStatus {
                       active               (1),
                    -- notInService         (2)
                    -- notReady             (3)
                       createAndGo          (4),
                    -- createAndWait        (5)
                       destroy              (6)
                    }
            DESCRIPTION
                 "tFilterEmbedOpenflowRowStatus supports only 'active (1)',
                  'createAndGo (4)', and 'destroy (6)'."

        VARIATION   tFilterEmbedVsdFilterType
            SYNTAX  INTEGER {
                    -- fltrtypeselNone      (0)
                       fltrtypeselIp        (1),
                       fltrtypeselMac       (2),
                    -- fltrtypeselCpm       (3)
                       fltrtypeselIpv6      (4)
                    -- fltrtypeselCpm6      (5)
                    -- fltrtypeselCpmMac    (6)
                    }
            DESCRIPTION
                 "tFilterEmbedVsdFilterType supports only the values
                  'fltrtypeselIp(1)', 'fltrtypeselIpv6(4)' and
                  'fltrtypeselMac(2)'."

        VARIATION   tFilterEmbedVsdRowStatus
            SYNTAX  RowStatus {
                       active               (1),
                    -- notInService         (2)
                    -- notReady             (3)
                       createAndGo          (4),
                    -- createAndWait        (5)
                       destroy              (6)
                    }
            DESCRIPTION
                 "tFilterEmbedVsdRowStatus supports only 'active (1)',
                  'createAndGo (4)', and 'destroy (6)'."

        VARIATION   tFilterLogDestination
            DESCRIPTION
                 "The value 'file (3)' is not supported."

        VARIATION   tFilterRPRowStatus
            SYNTAX  RowStatus {
                       active               (1),
                    -- notInService         (2)
                    -- notReady             (3)
                       createAndGo          (4),
                    -- createAndWait        (5)
                       destroy              (6)
                    }
            DESCRIPTION
                 "tFilterRPRowStatus supports only 'active (1)', 'createAndGo
                  (4)', and 'destroy (6)'."

        VARIATION   tFilterSystemFilterRowStatus
            SYNTAX  RowStatus {
                       active               (1),
                    -- notInService         (2)
                    -- notReady             (3)
                       createAndGo          (4),
                    -- createAndWait        (5)
                       destroy              (6)
                    }
            DESCRIPTION
                 "tFilterSystemFilterRowStatus supports only 'active (1)',
                  'createAndGo (4)', and 'destroy (6)'."

        VARIATION   tFilterSystemFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterSystemFilterType supports only the values
                  'fltrtypeselIp(1)' and 'fltrtypeselIpv6(4)'."

        VARIATION   tFltrRPDstAddrType
            SYNTAX  InetAddressType {
                    -- unknown              (0)
                       ipv4                 (1),
                       ipv6                 (2)
                    -- ipv4z                (3)
                    -- ipv6z                (4)
                    -- dns                  (16)
                    }
            DESCRIPTION
                 "tFltrRPDstAddrType supports only the InetAddressType values
                  'ipv4 (1)', and 'ipv6 (2)'."

        VARIATION   tFltrRPDstRowStatus
            SYNTAX  RowStatus {
                       active               (1),
                    -- notInService         (2)
                    -- notReady             (3)
                       createAndGo          (4),
                    -- createAndWait        (5)
                       destroy              (6)
                    }
            DESCRIPTION
                 "tFltrRPDstRowStatus supports only 'active (1)', 'createAndGo
                  (4)', and 'destroy (6)'."

        VARIATION   tFltrRPPingTRowStatus
            SYNTAX  RowStatus {
                       active               (1),
                    -- notInService         (2)
                    -- notReady             (3)
                       createAndGo          (4),
                    -- createAndWait        (5)
                       destroy              (6)
                    }
            DESCRIPTION
                 "tFltrRPPingTRowStatus supports only 'active (1)', 'createAndGo
                  (4)', and 'destroy (6)'."

        VARIATION   tFltrRPSnmpRspCounter64Val
            ACCESS  not-implemented
            DESCRIPTION
                 "tFltrRPSnmpRspCounter64Val is not implemented on Nokia SROS in
                  release 14.0."

        VARIATION   tFltrRPSnmpRspOidVal
            ACCESS  not-implemented
            DESCRIPTION
                 "tFltrRPSnmpRspOidVal is not implemented on Nokia SROS in
                  release 14.0."

        VARIATION   tFltrRPSnmpRspRowStatus
            SYNTAX  RowStatus {
                       active               (1),
                    -- notInService         (2)
                    -- notReady             (3)
                       createAndGo          (4),
                    -- createAndWait        (5)
                       destroy              (6)
                    }
            DESCRIPTION
                 "tFltrRPSnmpRspRowStatus supports only 'active (1)',
                  'createAndGo (4)', and 'destroy (6)'."

        VARIATION   tFltrRPSnmpRspType
            SYNTAX  INTEGER {
                       counter32            (1),
                       unsigned32           (2),
                       timeTicks            (3),
                       integer32            (4),
                       ipAddress            (5),
                       octedString          (6),
                    -- objectId             (7)
                    -- counter64            (8)
                       opaque               (9)
                    }
            DESCRIPTION
                 "The values 'counter64' (7) and 'objectId' (8) are not
                  supported."

        VARIATION   tFltrRPSnmpTRowStatus
            SYNTAX  RowStatus {
                       active               (1),
                    -- notInService         (2)
                    -- notReady             (3)
                       createAndGo          (4),
                    -- createAndWait        (5)
                       destroy              (6)
                    }
            DESCRIPTION
                 "tFltrRPSnmpTRowStatus supports only 'active (1)', 'createAndGo
                  (4)', and 'destroy (6)'."

        VARIATION   tFltrRPSnmpTSnmpVersion
            SYNTAX  INTEGER {
                    -- snmpv1               (1)
                       snmpv2c              (2)
                    -- snmpv3               (3)
                    }
            DESCRIPTION
                 "The values 'snmpv1' (1) and snmpv3 (3) are not supported."

        VARIATION   tFltrRPUcastRtTRowStatus
            SYNTAX  RowStatus {
                       active               (1),
                    -- notInService         (2)
                    -- notReady             (3)
                       createAndGo          (4),
                    -- createAndWait        (5)
                       destroy              (6)
                    }
            DESCRIPTION
                 "tFltrRPUcastRtTRowStatus supports only 'active (1)',
                  'createAndGo (4)', and 'destroy (6)'."

        VARIATION   tFltrRPUrlTRowStatus
            SYNTAX  RowStatus {
                       active               (1),
                    -- notInService         (2)
                    -- notReady             (3)
                       createAndGo          (4),
                    -- createAndWait        (5)
                       destroy              (6)
                    }
            DESCRIPTION
                 "tFltrRPUrlTRowStatus supports only 'active (1)', 'createAndGo
                  (4)', and 'destroy (6)'."

        VARIATION   tFltrRPUrlTRspRowStatus
            SYNTAX  RowStatus {
                       active               (1),
                    -- notInService         (2)
                    -- notReady             (3)
                       createAndGo          (4),
                    -- createAndWait        (5)
                       destroy              (6)
                    }
            DESCRIPTION
                 "tFltrRPUrlTRspRowStatus supports only 'active (1)',
                  'createAndGo (4)', and 'destroy (6)'."

        VARIATION   tIPv6FilterParamsCflowdIfSample
            DESCRIPTION
                 "The object tIPv6FilterParamsCflowdIfSample is added for future
                  use. The corresponding functionality is not offered in this
                  release. The only actions allowed on this object will
                  therefore be GET and SET to its default value."

        VARIATION   tIPv6FilterParamsCflowdSample
            DESCRIPTION
                 "The object tIPv6FilterParamsCflowdSample is added for future
                  use. The corresponding functionality is not offered in this
                  release. The only actions allowed on this object will
                  therefore be GET and SET to its default value."

        VARIATION   tIPvXFltrEntryActFltrType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tIPvXFltrEntryActFltrType supports only the values
                  'fltrtypeselIp(1)' and 'fltrtypeselIpv6(4)'."

        VARIATION   tIPvXFltrEntryActFwdEsiSFIpType
            SYNTAX  InetAddressType {
                       unknown              (0),
                       ipv4                 (1),
                       ipv6                 (2)
                    -- ipv4z                (3)
                    -- ipv6z                (4)
                    -- dns                  (16)
                    }
            DESCRIPTION
                 "tIPvXFltrEntryActFwdEsiSFIpType supports only the
                  InetAddressType values 'unknown (0)', 'ipv4 (1)', and 'ipv6
                  (2)'."

        VARIATION   tIPvXFltrEntryActFwdNHIpAddrType
            SYNTAX  InetAddressType {
                       unknown              (0),
                       ipv4                 (1),
                       ipv6                 (2)
                    -- ipv4z                (3)
                    -- ipv6z                (4)
                    -- dns                  (16)
                    }
            DESCRIPTION
                 "tIPvXFltrEntryActFwdNHIpAddrType supports only the
                  InetAddressType values 'unknown (0)', 'ipv4 (1)', and 'ipv6
                  (2)'."

        VARIATION   tIPvXFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

        VARIATION   tLiFilterType
            DESCRIPTION
                 "Only values 'fltrtypeselIp (1)', 'fltrtypeselMac (2)' and
                  'fltrtypeselIpv6 (4)' are supported."

        VARIATION   tLiIpFilterParamsDstIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tLiIpFilterParamsSrcIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tMacFilterParamsAction
            DESCRIPTION
                 "The value 'default' (3) is not supported."

        VARIATION   tMacFilterScope
            SYNTAX  INTEGER {
                       exclusive            (1),
                       template             (2),
                       embedded             (3)
                    -- system               (4)
                    }
            DESCRIPTION
                 "The value 'system(4)' is not supported."

        VARIATION   tMacFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

    ::= { tmnxSROSAgentV14v0  13 }

--
-- 7750SR-1 FILTER CAPABILITIES
--
tmnx7750SR1FilterV14v0            AGENT-CAPABILITIES
    PRODUCT-RELEASE "Nokia SROS"
    STATUS          current
    DESCRIPTION
         "Implementation of ACL filters capabilities for Nokia 7750 SR-1 systems
          release 14.0"

    SUPPORTS        TIMETRA-FILTER-MIB
        INCLUDES {
           tDhcpFilterV10v0Group,
           tDhcpFilterV13v0Group,
           tFilterEmbedFlowspecGroup,
           tFilterEmbedVsdGroup,
           tFilterEmbeddedInsertV11v0Group,
           tFilterEmbeddedInsertV12v0Group,
           tFilterEmbeddedInsertV13v0Group,
           tFilterEmbeddedRefGroup,
           tFilterEntryStatGroup,
           tFilterIPvXRedundantActionGroup,
           tFilterLogGroup,
           tFilterLogV5v0Group,
           tFilterMacRedundantActionGroup,
           tFilterNameV10v0Group,
           tFilterNotificationObjV12v0Group,
           tFilterNotificationsV11v0Group,
           tFilterNotificationsV12v0Group,
           tFilterNotificationsV14v0Group,
           tFilterPortListV11v0Group,
           tFilterPrefListInfoGroup,
           tFilterPrefixListV11v0Group,
           tFilterRedirectPolicyV13v0Group,
           tFilterRemarkDscpExtGroup,
           tFilterRemarkDscpGroup,
           tFilterScalarGroup,
           tFilterSystemFilterV13v0Group,
           tIPFilterV13v0Group,
           tIPFilterV14v0Group,
           tIPv6FilterV13v0Group,
           tIPv6FilterV14v0Group,
           tLiFilterV12v0Group,
           tMacFilterV13v0Group,
           tMacFilterV8v0Group,
           tMacFilterVidFilteringV9v0Group
        }

        VARIATION   tAutoIPFilterEntryTable
            ACCESS  not-implemented
            DESCRIPTION
                 "The tAutoIPFilterEntryTable was made obsolete in release 3.0."

        VARIATION   tFilterEmbedFlowspecFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedFlowspecFilterType supports only the values
                  'fltrtypeselIp(1)' and 'fltrtypeselIpv6(4)'."

        VARIATION   tFilterEmbedFlowspecRowStatus
            SYNTAX  RowStatus {
                       active               (1),
                    -- notInService         (2)
                    -- notReady             (3)
                       createAndGo          (4),
                    -- createAndWait        (5)
                       destroy              (6)
                    }
            DESCRIPTION
                 "tFilterEmbedFlowspecRowStatus supports only 'active (1)',
                  'createAndGo (4)', and 'destroy (6)'."

        VARIATION   tFilterEmbedOpenflowFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedOpenflowFilterType supports only the values
                  'fltrtypeselIp(1)' and 'fltrtypeselIpv6(4)'."

        VARIATION   tFilterEmbedOpenflowRowStatus
            SYNTAX  RowStatus {
                       active               (1),
                    -- notInService         (2)
                    -- notReady             (3)
                       createAndGo          (4),
                    -- createAndWait        (5)
                       destroy              (6)
                    }
            DESCRIPTION
                 "tFilterEmbedOpenflowRowStatus supports only 'active (1)',
                  'createAndGo (4)', and 'destroy (6)'."

        VARIATION   tFilterEmbedVsdFilterType
            SYNTAX  INTEGER {
                    -- fltrtypeselNone      (0)
                       fltrtypeselIp        (1),
                       fltrtypeselMac       (2),
                    -- fltrtypeselCpm       (3)
                       fltrtypeselIpv6      (4)
                    -- fltrtypeselCpm6      (5)
                    -- fltrtypeselCpmMac    (6)
                    }
            DESCRIPTION
                 "tFilterEmbedVsdFilterType supports only the values
                  'fltrtypeselIp(1)', 'fltrtypeselIpv6(4)' and
                  'fltrtypeselMac(2)'."

        VARIATION   tFilterEmbedVsdRowStatus
            SYNTAX  RowStatus {
                       active               (1),
                    -- notInService         (2)
                    -- notReady             (3)
                       createAndGo          (4),
                    -- createAndWait        (5)
                       destroy              (6)
                    }
            DESCRIPTION
                 "tFilterEmbedVsdRowStatus supports only 'active (1)',
                  'createAndGo (4)', and 'destroy (6)'."

        VARIATION   tFilterLogDestination
            DESCRIPTION
                 "The value 'file (3)' is not supported."

        VARIATION   tFilterRPRowStatus
            SYNTAX  RowStatus {
                       active               (1),
                    -- notInService         (2)
                    -- notReady             (3)
                       createAndGo          (4),
                    -- createAndWait        (5)
                       destroy              (6)
                    }
            DESCRIPTION
                 "tFilterRPRowStatus supports only 'active (1)', 'createAndGo
                  (4)', and 'destroy (6)'."

        VARIATION   tFilterSystemFilterRowStatus
            SYNTAX  RowStatus {
                       active               (1),
                    -- notInService         (2)
                    -- notReady             (3)
                       createAndGo          (4),
                    -- createAndWait        (5)
                       destroy              (6)
                    }
            DESCRIPTION
                 "tFilterSystemFilterRowStatus supports only 'active (1)',
                  'createAndGo (4)', and 'destroy (6)'."

        VARIATION   tFilterSystemFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterSystemFilterType supports only the values
                  'fltrtypeselIp(1)' and 'fltrtypeselIpv6(4)'."

        VARIATION   tFltrRPDstAddrType
            SYNTAX  InetAddressType {
                    -- unknown              (0)
                       ipv4                 (1),
                       ipv6                 (2)
                    -- ipv4z                (3)
                    -- ipv6z                (4)
                    -- dns                  (16)
                    }
            DESCRIPTION
                 "tFltrRPDstAddrType supports only the InetAddressType values
                  'ipv4 (1)', and 'ipv6 (2)'."

        VARIATION   tFltrRPDstRowStatus
            SYNTAX  RowStatus {
                       active               (1),
                    -- notInService         (2)
                    -- notReady             (3)
                       createAndGo          (4),
                    -- createAndWait        (5)
                       destroy              (6)
                    }
            DESCRIPTION
                 "tFltrRPDstRowStatus supports only 'active (1)', 'createAndGo
                  (4)', and 'destroy (6)'."

        VARIATION   tFltrRPPingTRowStatus
            SYNTAX  RowStatus {
                       active               (1),
                    -- notInService         (2)
                    -- notReady             (3)
                       createAndGo          (4),
                    -- createAndWait        (5)
                       destroy              (6)
                    }
            DESCRIPTION
                 "tFltrRPPingTRowStatus supports only 'active (1)', 'createAndGo
                  (4)', and 'destroy (6)'."

        VARIATION   tFltrRPSnmpRspCounter64Val
            ACCESS  not-implemented
            DESCRIPTION
                 "tFltrRPSnmpRspCounter64Val is not implemented on Nokia 7750
                  SR-1 in release 14.0."

        VARIATION   tFltrRPSnmpRspOidVal
            ACCESS  not-implemented
            DESCRIPTION
                 "tFltrRPSnmpRspOidVal is not implemented on Nokia 7750 SR-1 in
                  release 14.0."

        VARIATION   tFltrRPSnmpRspRowStatus
            SYNTAX  RowStatus {
                       active               (1),
                    -- notInService         (2)
                    -- notReady             (3)
                       createAndGo          (4),
                    -- createAndWait        (5)
                       destroy              (6)
                    }
            DESCRIPTION
                 "tFltrRPSnmpRspRowStatus supports only 'active (1)',
                  'createAndGo (4)', and 'destroy (6)'."

        VARIATION   tFltrRPSnmpRspType
            SYNTAX  INTEGER {
                       counter32            (1),
                       unsigned32           (2),
                       timeTicks            (3),
                       integer32            (4),
                       ipAddress            (5),
                       octedString          (6),
                    -- objectId             (7)
                    -- counter64            (8)
                       opaque               (9)
                    }
            DESCRIPTION
                 "The values 'counter64' (7) and 'objectId' (8) are not
                  supported."

        VARIATION   tFltrRPSnmpTRowStatus
            SYNTAX  RowStatus {
                       active               (1),
                    -- notInService         (2)
                    -- notReady             (3)
                       createAndGo          (4),
                    -- createAndWait        (5)
                       destroy              (6)
                    }
            DESCRIPTION
                 "tFltrRPSnmpTRowStatus supports only 'active (1)', 'createAndGo
                  (4)', and 'destroy (6)'."

        VARIATION   tFltrRPSnmpTSnmpVersion
            SYNTAX  INTEGER {
                    -- snmpv1               (1)
                       snmpv2c              (2)
                    -- snmpv3               (3)
                    }
            DESCRIPTION
                 "The values 'snmpv1' (1) and snmpv3 (3) are not supported."

        VARIATION   tFltrRPUcastRtTRowStatus
            SYNTAX  RowStatus {
                       active               (1),
                    -- notInService         (2)
                    -- notReady             (3)
                       createAndGo          (4),
                    -- createAndWait        (5)
                       destroy              (6)
                    }
            DESCRIPTION
                 "tFltrRPUcastRtTRowStatus supports only 'active (1)',
                  'createAndGo (4)', and 'destroy (6)'."

        VARIATION   tFltrRPUrlTRowStatus
            SYNTAX  RowStatus {
                       active               (1),
                    -- notInService         (2)
                    -- notReady             (3)
                       createAndGo          (4),
                    -- createAndWait        (5)
                       destroy              (6)
                    }
            DESCRIPTION
                 "tFltrRPUrlTRowStatus supports only 'active (1)', 'createAndGo
                  (4)', and 'destroy (6)'."

        VARIATION   tFltrRPUrlTRspRowStatus
            SYNTAX  RowStatus {
                       active               (1),
                    -- notInService         (2)
                    -- notReady             (3)
                       createAndGo          (4),
                    -- createAndWait        (5)
                       destroy              (6)
                    }
            DESCRIPTION
                 "tFltrRPUrlTRspRowStatus supports only 'active (1)',
                  'createAndGo (4)', and 'destroy (6)'."

        VARIATION   tIPv6FilterParamsCflowdIfSample
            DESCRIPTION
                 "The object tIPv6FilterParamsCflowdIfSample is added for future
                  use. The corresponding functionality is not offered in this
                  release. The only actions allowed on this object will
                  therefore be GET and SET to its default value."

        VARIATION   tIPv6FilterParamsCflowdSample
            DESCRIPTION
                 "The object tIPv6FilterParamsCflowdSample is added for future
                  use. The corresponding functionality is not offered in this
                  release. The only actions allowed on this object will
                  therefore be GET and SET to its default value."

        VARIATION   tIPvXFltrEntryActFltrType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tIPvXFltrEntryActFltrType supports only the values
                  'fltrtypeselIp(1)' and 'fltrtypeselIpv6(4)'."

        VARIATION   tIPvXFltrEntryActFwdEsiSFIpType
            SYNTAX  InetAddressType {
                       unknown              (0),
                       ipv4                 (1),
                       ipv6                 (2)
                    -- ipv4z                (3)
                    -- ipv6z                (4)
                    -- dns                  (16)
                    }
            DESCRIPTION
                 "tIPvXFltrEntryActFwdEsiSFIpType supports only the
                  InetAddressType values 'unknown (0)', 'ipv4 (1)', and 'ipv6
                  (2)'."

        VARIATION   tIPvXFltrEntryActFwdNHIpAddrType
            SYNTAX  InetAddressType {
                       unknown              (0),
                       ipv4                 (1),
                       ipv6                 (2)
                    -- ipv4z                (3)
                    -- ipv6z                (4)
                    -- dns                  (16)
                    }
            DESCRIPTION
                 "tIPvXFltrEntryActFwdNHIpAddrType supports only the
                  InetAddressType values 'unknown (0)', 'ipv4 (1)', and 'ipv6
                  (2)'."

        VARIATION   tIPvXFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

        VARIATION   tLiFilterType
            DESCRIPTION
                 "Only values 'fltrtypeselIp (1)', 'fltrtypeselMac (2)' and
                  'fltrtypeselIpv6 (4)' are supported."

        VARIATION   tLiIpFilterParamsDstIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tLiIpFilterParamsSrcIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tMacFilterParamsAction
            DESCRIPTION
                 "The value 'default' (3) is not supported."

        VARIATION   tMacFilterScope
            SYNTAX  INTEGER {
                       exclusive            (1),
                       template             (2),
                       embedded             (3)
                    -- system               (4)
                    }
            DESCRIPTION
                 "The value 'system(4)' is not supported."

        VARIATION   tMacFilterType
            DESCRIPTION
                 "The value 'vid' is not supported on Nokia 7750 SR-1."

        VARIATION   tMacFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

    ::= { tmnx7750SR1AgentV14v0  13 }

--
-- 7450ESS-1 FILTER CAPABILITIES
--
tmnx7450ESS1FilterV14v0           AGENT-CAPABILITIES
    PRODUCT-RELEASE "Nokia SROS"
    STATUS          current
    DESCRIPTION
         "Implementation of ACL filters capabilities for Nokia 7450 ESS-1
          systems release 14.0"

    SUPPORTS        TIMETRA-FILTER-MIB
        INCLUDES {
           tDhcpFilterV10v0Group,
           tDhcpFilterV13v0Group,
           tFilterEmbedFlowspecGroup,
           tFilterEmbedVsdGroup,
           tFilterEmbeddedInsertV11v0Group,
           tFilterEmbeddedInsertV12v0Group,
           tFilterEmbeddedInsertV13v0Group,
           tFilterEmbeddedRefGroup,
           tFilterEntryStatGroup,
           tFilterIPvXRedundantActionGroup,
           tFilterLogGroup,
           tFilterLogV5v0Group,
           tFilterMacRedundantActionGroup,
           tFilterNameV10v0Group,
           tFilterNotificationObjV12v0Group,
           tFilterNotificationsV11v0Group,
           tFilterNotificationsV12v0Group,
           tFilterNotificationsV14v0Group,
           tFilterPortListV11v0Group,
           tFilterPrefListInfoGroup,
           tFilterPrefixListV11v0Group,
           tFilterRedirectPolicyV13v0Group,
           tFilterRemarkDscpExtGroup,
           tFilterRemarkDscpGroup,
           tFilterScalarGroup,
           tFilterSystemFilterV13v0Group,
           tIPFilterV13v0Group,
           tIPFilterV14v0Group,
           tIPv6FilterV13v0Group,
           tIPv6FilterV14v0Group,
           tLiFilterV12v0Group,
           tMacFilterV13v0Group,
           tMacFilterV8v0Group,
           tMacFilterVidFilteringV9v0Group
        }

        VARIATION   tAutoIPFilterEntryTable
            ACCESS  not-implemented
            DESCRIPTION
                 "The tAutoIPFilterEntryTable was made obsolete in release 3.0."

        VARIATION   tFilterEmbedFlowspecFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedFlowspecFilterType supports only the values
                  'fltrtypeselIp(1)' and 'fltrtypeselIpv6(4)'."

        VARIATION   tFilterEmbedFlowspecRowStatus
            SYNTAX  RowStatus {
                       active               (1),
                    -- notInService         (2)
                    -- notReady             (3)
                       createAndGo          (4),
                    -- createAndWait        (5)
                       destroy              (6)
                    }
            DESCRIPTION
                 "tFilterEmbedFlowspecRowStatus supports only 'active (1)',
                  'createAndGo (4)', and 'destroy (6)'."

        VARIATION   tFilterEmbedOpenflowFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedOpenflowFilterType supports only the values
                  'fltrtypeselIp(1)' and 'fltrtypeselIpv6(4)'."

        VARIATION   tFilterEmbedOpenflowRowStatus
            SYNTAX  RowStatus {
                       active               (1),
                    -- notInService         (2)
                    -- notReady             (3)
                       createAndGo          (4),
                    -- createAndWait        (5)
                       destroy              (6)
                    }
            DESCRIPTION
                 "tFilterEmbedOpenflowRowStatus supports only 'active (1)',
                  'createAndGo (4)', and 'destroy (6)'."

        VARIATION   tFilterEmbedVsdFilterType
            SYNTAX  INTEGER {
                    -- fltrtypeselNone      (0)
                       fltrtypeselIp        (1),
                       fltrtypeselMac       (2),
                    -- fltrtypeselCpm       (3)
                       fltrtypeselIpv6      (4)
                    -- fltrtypeselCpm6      (5)
                    -- fltrtypeselCpmMac    (6)
                    }
            DESCRIPTION
                 "tFilterEmbedVsdFilterType supports only the values
                  'fltrtypeselIp(1)', 'fltrtypeselIpv6(4)' and
                  'fltrtypeselMac(2)'."

        VARIATION   tFilterEmbedVsdRowStatus
            SYNTAX  RowStatus {
                       active               (1),
                    -- notInService         (2)
                    -- notReady             (3)
                       createAndGo          (4),
                    -- createAndWait        (5)
                       destroy              (6)
                    }
            DESCRIPTION
                 "tFilterEmbedVsdRowStatus supports only 'active (1)',
                  'createAndGo (4)', and 'destroy (6)'."

        VARIATION   tFilterLogDestination
            DESCRIPTION
                 "The value 'file (3)' is not supported."

        VARIATION   tFilterRPRowStatus
            SYNTAX  RowStatus {
                       active               (1),
                    -- notInService         (2)
                    -- notReady             (3)
                       createAndGo          (4),
                    -- createAndWait        (5)
                       destroy              (6)
                    }
            DESCRIPTION
                 "tFilterRPRowStatus supports only 'active (1)', 'createAndGo
                  (4)', and 'destroy (6)'."

        VARIATION   tFilterSystemFilterRowStatus
            SYNTAX  RowStatus {
                       active               (1),
                    -- notInService         (2)
                    -- notReady             (3)
                       createAndGo          (4),
                    -- createAndWait        (5)
                       destroy              (6)
                    }
            DESCRIPTION
                 "tFilterSystemFilterRowStatus supports only 'active (1)',
                  'createAndGo (4)', and 'destroy (6)'."

        VARIATION   tFilterSystemFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterSystemFilterType supports only the values
                  'fltrtypeselIp(1)' and 'fltrtypeselIpv6(4)'."

        VARIATION   tFltrRPDstAddrType
            SYNTAX  InetAddressType {
                    -- unknown              (0)
                       ipv4                 (1),
                       ipv6                 (2)
                    -- ipv4z                (3)
                    -- ipv6z                (4)
                    -- dns                  (16)
                    }
            DESCRIPTION
                 "tFltrRPDstAddrType supports only the InetAddressType values
                  'ipv4 (1)', and 'ipv6 (2)'."

        VARIATION   tFltrRPDstRowStatus
            SYNTAX  RowStatus {
                       active               (1),
                    -- notInService         (2)
                    -- notReady             (3)
                       createAndGo          (4),
                    -- createAndWait        (5)
                       destroy              (6)
                    }
            DESCRIPTION
                 "tFltrRPDstRowStatus supports only 'active (1)', 'createAndGo
                  (4)', and 'destroy (6)'."

        VARIATION   tFltrRPPingTRowStatus
            SYNTAX  RowStatus {
                       active               (1),
                    -- notInService         (2)
                    -- notReady             (3)
                       createAndGo          (4),
                    -- createAndWait        (5)
                       destroy              (6)
                    }
            DESCRIPTION
                 "tFltrRPPingTRowStatus supports only 'active (1)', 'createAndGo
                  (4)', and 'destroy (6)'."

        VARIATION   tFltrRPSnmpRspCounter64Val
            ACCESS  not-implemented
            DESCRIPTION
                 "tFltrRPSnmpRspCounter64Val is not implemented on Nokia 7450
                  ESS-1 in release 14.0."

        VARIATION   tFltrRPSnmpRspOidVal
            ACCESS  not-implemented
            DESCRIPTION
                 "tFltrRPSnmpRspOidVal is not implemented on Nokia 7450 ESS-1 in
                  release 14.0."

        VARIATION   tFltrRPSnmpRspRowStatus
            SYNTAX  RowStatus {
                       active               (1),
                    -- notInService         (2)
                    -- notReady             (3)
                       createAndGo          (4),
                    -- createAndWait        (5)
                       destroy              (6)
                    }
            DESCRIPTION
                 "tFltrRPSnmpRspRowStatus supports only 'active (1)',
                  'createAndGo (4)', and 'destroy (6)'."

        VARIATION   tFltrRPSnmpRspType
            SYNTAX  INTEGER {
                       counter32            (1),
                       unsigned32           (2),
                       timeTicks            (3),
                       integer32            (4),
                       ipAddress            (5),
                       octedString          (6),
                    -- objectId             (7)
                    -- counter64            (8)
                       opaque               (9)
                    }
            DESCRIPTION
                 "The values 'counter64' (7) and 'objectId' (8) are not
                  supported."

        VARIATION   tFltrRPSnmpTRowStatus
            SYNTAX  RowStatus {
                       active               (1),
                    -- notInService         (2)
                    -- notReady             (3)
                       createAndGo          (4),
                    -- createAndWait        (5)
                       destroy              (6)
                    }
            DESCRIPTION
                 "tFltrRPSnmpTRowStatus supports only 'active (1)', 'createAndGo
                  (4)', and 'destroy (6)'."

        VARIATION   tFltrRPSnmpTSnmpVersion
            SYNTAX  INTEGER {
                    -- snmpv1               (1)
                       snmpv2c              (2)
                    -- snmpv3               (3)
                    }
            DESCRIPTION
                 "The values 'snmpv1' (1) and snmpv3 (3) are not supported."

        VARIATION   tFltrRPUcastRtTRowStatus
            SYNTAX  RowStatus {
                       active               (1),
                    -- notInService         (2)
                    -- notReady             (3)
                       createAndGo          (4),
                    -- createAndWait        (5)
                       destroy              (6)
                    }
            DESCRIPTION
                 "tFltrRPUcastRtTRowStatus supports only 'active (1)',
                  'createAndGo (4)', and 'destroy (6)'."

        VARIATION   tFltrRPUrlTRowStatus
            SYNTAX  RowStatus {
                       active               (1),
                    -- notInService         (2)
                    -- notReady             (3)
                       createAndGo          (4),
                    -- createAndWait        (5)
                       destroy              (6)
                    }
            DESCRIPTION
                 "tFltrRPUrlTRowStatus supports only 'active (1)', 'createAndGo
                  (4)', and 'destroy (6)'."

        VARIATION   tFltrRPUrlTRspRowStatus
            SYNTAX  RowStatus {
                       active               (1),
                    -- notInService         (2)
                    -- notReady             (3)
                       createAndGo          (4),
                    -- createAndWait        (5)
                       destroy              (6)
                    }
            DESCRIPTION
                 "tFltrRPUrlTRspRowStatus supports only 'active (1)',
                  'createAndGo (4)', and 'destroy (6)'."

        VARIATION   tIPv6FilterParamsCflowdIfSample
            DESCRIPTION
                 "The object tIPv6FilterParamsCflowdIfSample is added for future
                  use. The corresponding functionality is not offered in this
                  release. The only actions allowed on this object will
                  therefore be GET and SET to its default value."

        VARIATION   tIPv6FilterParamsCflowdSample
            DESCRIPTION
                 "The object tIPv6FilterParamsCflowdSample is added for future
                  use. The corresponding functionality is not offered in this
                  release. The only actions allowed on this object will
                  therefore be GET and SET to its default value."

        VARIATION   tIPvXFltrEntryActFltrType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tIPvXFltrEntryActFltrType supports only the values
                  'fltrtypeselIp(1)' and 'fltrtypeselIpv6(4)'."

        VARIATION   tIPvXFltrEntryActFwdEsiSFIpType
            SYNTAX  InetAddressType {
                       unknown              (0),
                       ipv4                 (1),
                       ipv6                 (2)
                    -- ipv4z                (3)
                    -- ipv6z                (4)
                    -- dns                  (16)
                    }
            DESCRIPTION
                 "tIPvXFltrEntryActFwdEsiSFIpType supports only the
                  InetAddressType values 'unknown (0)', 'ipv4 (1)', and 'ipv6
                  (2)'."

        VARIATION   tIPvXFltrEntryActFwdNHIpAddrType
            SYNTAX  InetAddressType {
                       unknown              (0),
                       ipv4                 (1),
                       ipv6                 (2)
                    -- ipv4z                (3)
                    -- ipv6z                (4)
                    -- dns                  (16)
                    }
            DESCRIPTION
                 "tIPvXFltrEntryActFwdNHIpAddrType supports only the
                  InetAddressType values 'unknown (0)', 'ipv4 (1)', and 'ipv6
                  (2)'."

        VARIATION   tIPvXFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

        VARIATION   tLiFilterType
            DESCRIPTION
                 "Only values 'fltrtypeselIp (1)', 'fltrtypeselMac (2)' and
                  'fltrtypeselIpv6 (4)' are supported."

        VARIATION   tLiIpFilterParamsDstIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tLiIpFilterParamsSrcIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tMacFilterParamsAction
            DESCRIPTION
                 "The value 'default' (3) is not supported."

        VARIATION   tMacFilterScope
            SYNTAX  INTEGER {
                       exclusive            (1),
                       template             (2),
                       embedded             (3)
                    -- system               (4)
                    }
            DESCRIPTION
                 "The value 'system(4)' is not supported."

        VARIATION   tMacFilterType
            DESCRIPTION
                 "The value 'vid' is not supported on Nokia 7450 ESS-1."

        VARIATION   tMacFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

    ::= { tmnx7450ESS1AgentV14v0  13 }

--
-- 7710 FILTER CAPABILITIES
--
tmnx7710FilterV14v0               AGENT-CAPABILITIES
    PRODUCT-RELEASE "Nokia SROS"
    STATUS          current
    DESCRIPTION
         "Implementation of ACL filters capabilities for Nokia 7710 systems
          release 14.0"

    SUPPORTS        TIMETRA-FILTER-MIB
        INCLUDES {
           tDhcpFilterV10v0Group,
           tDhcpFilterV13v0Group,
           tFilterEmbedFlowspecGroup,
           tFilterEmbedVsdGroup,
           tFilterEmbeddedInsertV11v0Group,
           tFilterEmbeddedInsertV12v0Group,
           tFilterEmbeddedInsertV13v0Group,
           tFilterEmbeddedRefGroup,
           tFilterEntryStatGroup,
           tFilterIPvXRedundantActionGroup,
           tFilterLogGroup,
           tFilterLogV5v0Group,
           tFilterMacRedundantActionGroup,
           tFilterNameV10v0Group,
           tFilterNotificationObjV12v0Group,
           tFilterNotificationsV11v0Group,
           tFilterNotificationsV12v0Group,
           tFilterNotificationsV14v0Group,
           tFilterPortListV11v0Group,
           tFilterPrefListInfoGroup,
           tFilterPrefixListV11v0Group,
           tFilterRedirectPolicyV13v0Group,
           tFilterRemarkDscpExtGroup,
           tFilterRemarkDscpGroup,
           tFilterScalarGroup,
           tFilterSystemFilterV13v0Group,
           tIPFilterV13v0Group,
           tIPFilterV14v0Group,
           tIPv6FilterV13v0Group,
           tIPv6FilterV14v0Group,
           tLiFilterV12v0Group,
           tMacFilterV13v0Group,
           tMacFilterV8v0Group,
           tMacFilterVidFilteringV9v0Group
        }

        VARIATION   tAutoIPFilterEntryTable
            ACCESS  not-implemented
            DESCRIPTION
                 "The tAutoIPFilterEntryTable was made obsolete in release 3.0."

        VARIATION   tFilterEmbedFlowspecFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedFlowspecFilterType supports only the values
                  'fltrtypeselIp(1)' and 'fltrtypeselIpv6(4)'."

        VARIATION   tFilterEmbedFlowspecRowStatus
            SYNTAX  RowStatus {
                       active               (1),
                    -- notInService         (2)
                    -- notReady             (3)
                       createAndGo          (4),
                    -- createAndWait        (5)
                       destroy              (6)
                    }
            DESCRIPTION
                 "tFilterEmbedFlowspecRowStatus supports only 'active (1)',
                  'createAndGo (4)', and 'destroy (6)'."

        VARIATION   tFilterEmbedOpenflowFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedOpenflowFilterType supports only the values
                  'fltrtypeselIp(1)' and 'fltrtypeselIpv6(4)'."

        VARIATION   tFilterEmbedOpenflowRowStatus
            SYNTAX  RowStatus {
                       active               (1),
                    -- notInService         (2)
                    -- notReady             (3)
                       createAndGo          (4),
                    -- createAndWait        (5)
                       destroy              (6)
                    }
            DESCRIPTION
                 "tFilterEmbedOpenflowRowStatus supports only 'active (1)',
                  'createAndGo (4)', and 'destroy (6)'."

        VARIATION   tFilterEmbedVsdFilterType
            SYNTAX  INTEGER {
                    -- fltrtypeselNone      (0)
                       fltrtypeselIp        (1),
                       fltrtypeselMac       (2),
                    -- fltrtypeselCpm       (3)
                       fltrtypeselIpv6      (4)
                    -- fltrtypeselCpm6      (5)
                    -- fltrtypeselCpmMac    (6)
                    }
            DESCRIPTION
                 "tFilterEmbedVsdFilterType supports only the values
                  'fltrtypeselIp(1)', 'fltrtypeselIpv6(4)' and
                  'fltrtypeselMac(2)'."

        VARIATION   tFilterEmbedVsdRowStatus
            SYNTAX  RowStatus {
                       active               (1),
                    -- notInService         (2)
                    -- notReady             (3)
                       createAndGo          (4),
                    -- createAndWait        (5)
                       destroy              (6)
                    }
            DESCRIPTION
                 "tFilterEmbedVsdRowStatus supports only 'active (1)',
                  'createAndGo (4)', and 'destroy (6)'."

        VARIATION   tFilterLogDestination
            DESCRIPTION
                 "The value 'file (3)' is not supported."

        VARIATION   tFilterRPRowStatus
            SYNTAX  RowStatus {
                       active               (1),
                    -- notInService         (2)
                    -- notReady             (3)
                       createAndGo          (4),
                    -- createAndWait        (5)
                       destroy              (6)
                    }
            DESCRIPTION
                 "tFilterRPRowStatus supports only 'active (1)', 'createAndGo
                  (4)', and 'destroy (6)'."

        VARIATION   tFilterSystemFilterRowStatus
            SYNTAX  RowStatus {
                       active               (1),
                    -- notInService         (2)
                    -- notReady             (3)
                       createAndGo          (4),
                    -- createAndWait        (5)
                       destroy              (6)
                    }
            DESCRIPTION
                 "tFilterSystemFilterRowStatus supports only 'active (1)',
                  'createAndGo (4)', and 'destroy (6)'."

        VARIATION   tFilterSystemFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterSystemFilterType supports only the values
                  'fltrtypeselIp(1)' and 'fltrtypeselIpv6(4)'."

        VARIATION   tFltrRPDstAddrType
            SYNTAX  InetAddressType {
                    -- unknown              (0)
                       ipv4                 (1),
                       ipv6                 (2)
                    -- ipv4z                (3)
                    -- ipv6z                (4)
                    -- dns                  (16)
                    }
            DESCRIPTION
                 "tFltrRPDstAddrType supports only the InetAddressType values
                  'ipv4 (1)', and 'ipv6 (2)'."

        VARIATION   tFltrRPDstRowStatus
            SYNTAX  RowStatus {
                       active               (1),
                    -- notInService         (2)
                    -- notReady             (3)
                       createAndGo          (4),
                    -- createAndWait        (5)
                       destroy              (6)
                    }
            DESCRIPTION
                 "tFltrRPDstRowStatus supports only 'active (1)', 'createAndGo
                  (4)', and 'destroy (6)'."

        VARIATION   tFltrRPPingTRowStatus
            SYNTAX  RowStatus {
                       active               (1),
                    -- notInService         (2)
                    -- notReady             (3)
                       createAndGo          (4),
                    -- createAndWait        (5)
                       destroy              (6)
                    }
            DESCRIPTION
                 "tFltrRPPingTRowStatus supports only 'active (1)', 'createAndGo
                  (4)', and 'destroy (6)'."

        VARIATION   tFltrRPSnmpRspCounter64Val
            ACCESS  not-implemented
            DESCRIPTION
                 "tFltrRPSnmpRspCounter64Val is not implemented on Nokia 7710 in
                  release 14.0."

        VARIATION   tFltrRPSnmpRspOidVal
            ACCESS  not-implemented
            DESCRIPTION
                 "tFltrRPSnmpRspOidVal is not implemented on Nokia 7710 in
                  release 14.0."

        VARIATION   tFltrRPSnmpRspRowStatus
            SYNTAX  RowStatus {
                       active               (1),
                    -- notInService         (2)
                    -- notReady             (3)
                       createAndGo          (4),
                    -- createAndWait        (5)
                       destroy              (6)
                    }
            DESCRIPTION
                 "tFltrRPSnmpRspRowStatus supports only 'active (1)',
                  'createAndGo (4)', and 'destroy (6)'."

        VARIATION   tFltrRPSnmpRspType
            SYNTAX  INTEGER {
                       counter32            (1),
                       unsigned32           (2),
                       timeTicks            (3),
                       integer32            (4),
                       ipAddress            (5),
                       octedString          (6),
                    -- objectId             (7)
                    -- counter64            (8)
                       opaque               (9)
                    }
            DESCRIPTION
                 "The values 'counter64' (7) and 'objectId' (8) are not
                  supported."

        VARIATION   tFltrRPSnmpTRowStatus
            SYNTAX  RowStatus {
                       active               (1),
                    -- notInService         (2)
                    -- notReady             (3)
                       createAndGo          (4),
                    -- createAndWait        (5)
                       destroy              (6)
                    }
            DESCRIPTION
                 "tFltrRPSnmpTRowStatus supports only 'active (1)', 'createAndGo
                  (4)', and 'destroy (6)'."

        VARIATION   tFltrRPSnmpTSnmpVersion
            SYNTAX  INTEGER {
                    -- snmpv1               (1)
                       snmpv2c              (2)
                    -- snmpv3               (3)
                    }
            DESCRIPTION
                 "The values 'snmpv1' (1) and snmpv3 (3) are not supported."

        VARIATION   tFltrRPUcastRtTRowStatus
            SYNTAX  RowStatus {
                       active               (1),
                    -- notInService         (2)
                    -- notReady             (3)
                       createAndGo          (4),
                    -- createAndWait        (5)
                       destroy              (6)
                    }
            DESCRIPTION
                 "tFltrRPUcastRtTRowStatus supports only 'active (1)',
                  'createAndGo (4)', and 'destroy (6)'."

        VARIATION   tFltrRPUrlTRowStatus
            SYNTAX  RowStatus {
                       active               (1),
                    -- notInService         (2)
                    -- notReady             (3)
                       createAndGo          (4),
                    -- createAndWait        (5)
                       destroy              (6)
                    }
            DESCRIPTION
                 "tFltrRPUrlTRowStatus supports only 'active (1)', 'createAndGo
                  (4)', and 'destroy (6)'."

        VARIATION   tFltrRPUrlTRspRowStatus
            SYNTAX  RowStatus {
                       active               (1),
                    -- notInService         (2)
                    -- notReady             (3)
                       createAndGo          (4),
                    -- createAndWait        (5)
                       destroy              (6)
                    }
            DESCRIPTION
                 "tFltrRPUrlTRspRowStatus supports only 'active (1)',
                  'createAndGo (4)', and 'destroy (6)'."

        VARIATION   tIPv6FilterParamsCflowdIfSample
            DESCRIPTION
                 "The object tIPv6FilterParamsCflowdIfSample is added for future
                  use. The corresponding functionality is not offered in this
                  release. The only actions allowed on this object will
                  therefore be GET and SET to its default value."

        VARIATION   tIPv6FilterParamsCflowdSample
            DESCRIPTION
                 "The object tIPv6FilterParamsCflowdSample is added for future
                  use. The corresponding functionality is not offered in this
                  release. The only actions allowed on this object will
                  therefore be GET and SET to its default value."

        VARIATION   tIPvXFltrEntryActFltrType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tIPvXFltrEntryActFltrType supports only the values
                  'fltrtypeselIp(1)' and 'fltrtypeselIpv6(4)'."

        VARIATION   tIPvXFltrEntryActFwdEsiSFIpType
            SYNTAX  InetAddressType {
                       unknown              (0),
                       ipv4                 (1),
                       ipv6                 (2)
                    -- ipv4z                (3)
                    -- ipv6z                (4)
                    -- dns                  (16)
                    }
            DESCRIPTION
                 "tIPvXFltrEntryActFwdEsiSFIpType supports only the
                  InetAddressType values 'unknown (0)', 'ipv4 (1)', and 'ipv6
                  (2)'."

        VARIATION   tIPvXFltrEntryActFwdNHIpAddrType
            SYNTAX  InetAddressType {
                       unknown              (0),
                       ipv4                 (1),
                       ipv6                 (2)
                    -- ipv4z                (3)
                    -- ipv6z                (4)
                    -- dns                  (16)
                    }
            DESCRIPTION
                 "tIPvXFltrEntryActFwdNHIpAddrType supports only the
                  InetAddressType values 'unknown (0)', 'ipv4 (1)', and 'ipv6
                  (2)'."

        VARIATION   tIPvXFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

        VARIATION   tLiFilterType
            DESCRIPTION
                 "Only values 'fltrtypeselIp (1)', 'fltrtypeselMac (2)' and
                  'fltrtypeselIpv6 (4)' are supported."

        VARIATION   tLiIpFilterParamsDstIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tLiIpFilterParamsSrcIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tMacFilterParamsAction
            DESCRIPTION
                 "The value 'default' (3) is not supported."

        VARIATION   tMacFilterScope
            SYNTAX  INTEGER {
                       exclusive            (1),
                       template             (2),
                       embedded             (3)
                    -- system               (4)
                    }
            DESCRIPTION
                 "The value 'system(4)' is not supported."

        VARIATION   tMacFilterType
            DESCRIPTION
                 "The value 'vid' is not supported on Nokia 7710."

        VARIATION   tMacFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

    ::= { tmnx7710AgentV14v0  13 }

--
-- 7950 FILTER CAPABILITIES
--
tmnx7950FilterV14v0               AGENT-CAPABILITIES
    PRODUCT-RELEASE "Nokia SROS"
    STATUS          current
    DESCRIPTION
         "Implementation of ACL filters capabilities for Nokia 7950 systems
          release 14.0"

    SUPPORTS        TIMETRA-FILTER-MIB
        INCLUDES {
           tDhcpFilterV10v0Group,
           tDhcpFilterV13v0Group,
           tFilterEmbedFlowspecGroup,
           tFilterEmbedVsdGroup,
           tFilterEmbeddedInsertV11v0Group,
           tFilterEmbeddedInsertV12v0Group,
           tFilterEmbeddedInsertV13v0Group,
           tFilterEmbeddedRefGroup,
           tFilterEntryStatGroup,
           tFilterIPvXRedundantActionGroup,
           tFilterLogGroup,
           tFilterLogV5v0Group,
           tFilterMacRedundantActionGroup,
           tFilterNameV10v0Group,
           tFilterNotificationObjV12v0Group,
           tFilterNotificationsV11v0Group,
           tFilterNotificationsV12v0Group,
           tFilterNotificationsV14v0Group,
           tFilterPortListV11v0Group,
           tFilterPrefListInfoGroup,
           tFilterPrefixListV11v0Group,
           tFilterRedirectPolicyV13v0Group,
           tFilterRemarkDscpExtGroup,
           tFilterRemarkDscpGroup,
           tFilterScalarGroup,
           tFilterSystemFilterV13v0Group,
           tIPFilterV13v0Group,
           tIPFilterV14v0Group,
           tIPv6FilterV13v0Group,
           tIPv6FilterV14v0Group,
           tLiFilterV12v0Group,
           tMacFilterV13v0Group,
           tMacFilterV8v0Group,
           tMacFilterVidFilteringV9v0Group
        }

        VARIATION   tAutoIPFilterEntryTable
            ACCESS  not-implemented
            DESCRIPTION
                 "The tAutoIPFilterEntryTable was made obsolete in release 3.0."

        VARIATION   tFilterEmbedFlowspecFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedFlowspecFilterType supports only the values
                  'fltrtypeselIp(1)' and 'fltrtypeselIpv6(4)'."

        VARIATION   tFilterEmbedFlowspecRowStatus
            SYNTAX  RowStatus {
                       active               (1),
                    -- notInService         (2)
                    -- notReady             (3)
                       createAndGo          (4),
                    -- createAndWait        (5)
                       destroy              (6)
                    }
            DESCRIPTION
                 "tFilterEmbedFlowspecRowStatus supports only 'active (1)',
                  'createAndGo (4)', and 'destroy (6)'."

        VARIATION   tFilterEmbedOpenflowFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterEmbedOpenflowFilterType supports only the values
                  'fltrtypeselIp(1)' and 'fltrtypeselIpv6(4)'."

        VARIATION   tFilterEmbedOpenflowRowStatus
            SYNTAX  RowStatus {
                       active               (1),
                    -- notInService         (2)
                    -- notReady             (3)
                       createAndGo          (4),
                    -- createAndWait        (5)
                       destroy              (6)
                    }
            DESCRIPTION
                 "tFilterEmbedOpenflowRowStatus supports only 'active (1)',
                  'createAndGo (4)', and 'destroy (6)'."

        VARIATION   tFilterEmbedVsdFilterType
            SYNTAX  INTEGER {
                    -- fltrtypeselNone      (0)
                       fltrtypeselIp        (1),
                       fltrtypeselMac       (2),
                    -- fltrtypeselCpm       (3)
                       fltrtypeselIpv6      (4)
                    -- fltrtypeselCpm6      (5)
                    -- fltrtypeselCpmMac    (6)
                    }
            DESCRIPTION
                 "tFilterEmbedVsdFilterType supports only the values
                  'fltrtypeselIp(1)', 'fltrtypeselIpv6(4)' and
                  'fltrtypeselMac(2)'."

        VARIATION   tFilterEmbedVsdRowStatus
            SYNTAX  RowStatus {
                       active               (1),
                    -- notInService         (2)
                    -- notReady             (3)
                       createAndGo          (4),
                    -- createAndWait        (5)
                       destroy              (6)
                    }
            DESCRIPTION
                 "tFilterEmbedVsdRowStatus supports only 'active (1)',
                  'createAndGo (4)', and 'destroy (6)'."

        VARIATION   tFilterLogDestination
            DESCRIPTION
                 "The value 'file (3)' is not supported."

        VARIATION   tFilterRPRowStatus
            SYNTAX  RowStatus {
                       active               (1),
                    -- notInService         (2)
                    -- notReady             (3)
                       createAndGo          (4),
                    -- createAndWait        (5)
                       destroy              (6)
                    }
            DESCRIPTION
                 "tFilterRPRowStatus supports only 'active (1)', 'createAndGo
                  (4)', and 'destroy (6)'."

        VARIATION   tFilterSystemFilterRowStatus
            SYNTAX  RowStatus {
                       active               (1),
                    -- notInService         (2)
                    -- notReady             (3)
                       createAndGo          (4),
                    -- createAndWait        (5)
                       destroy              (6)
                    }
            DESCRIPTION
                 "tFilterSystemFilterRowStatus supports only 'active (1)',
                  'createAndGo (4)', and 'destroy (6)'."

        VARIATION   tFilterSystemFilterType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tFilterSystemFilterType supports only the values
                  'fltrtypeselIp(1)' and 'fltrtypeselIpv6(4)'."

        VARIATION   tFltrRPDstAddrType
            SYNTAX  InetAddressType {
                    -- unknown              (0)
                       ipv4                 (1),
                       ipv6                 (2)
                    -- ipv4z                (3)
                    -- ipv6z                (4)
                    -- dns                  (16)
                    }
            DESCRIPTION
                 "tFltrRPDstAddrType supports only the InetAddressType values
                  'ipv4 (1)', and 'ipv6 (2)'."

        VARIATION   tFltrRPDstRowStatus
            SYNTAX  RowStatus {
                       active               (1),
                    -- notInService         (2)
                    -- notReady             (3)
                       createAndGo          (4),
                    -- createAndWait        (5)
                       destroy              (6)
                    }
            DESCRIPTION
                 "tFltrRPDstRowStatus supports only 'active (1)', 'createAndGo
                  (4)', and 'destroy (6)'."

        VARIATION   tFltrRPPingTRowStatus
            SYNTAX  RowStatus {
                       active               (1),
                    -- notInService         (2)
                    -- notReady             (3)
                       createAndGo          (4),
                    -- createAndWait        (5)
                       destroy              (6)
                    }
            DESCRIPTION
                 "tFltrRPPingTRowStatus supports only 'active (1)', 'createAndGo
                  (4)', and 'destroy (6)'."

        VARIATION   tFltrRPSnmpRspCounter64Val
            ACCESS  not-implemented
            DESCRIPTION
                 "tFltrRPSnmpRspCounter64Val is not implemented on Nokia 7950 in
                  release 14.0."

        VARIATION   tFltrRPSnmpRspOidVal
            ACCESS  not-implemented
            DESCRIPTION
                 "tFltrRPSnmpRspOidVal is not implemented on Nokia 7950 in
                  release 14.0."

        VARIATION   tFltrRPSnmpRspRowStatus
            SYNTAX  RowStatus {
                       active               (1),
                    -- notInService         (2)
                    -- notReady             (3)
                       createAndGo          (4),
                    -- createAndWait        (5)
                       destroy              (6)
                    }
            DESCRIPTION
                 "tFltrRPSnmpRspRowStatus supports only 'active (1)',
                  'createAndGo (4)', and 'destroy (6)'."

        VARIATION   tFltrRPSnmpRspType
            SYNTAX  INTEGER {
                       counter32            (1),
                       unsigned32           (2),
                       timeTicks            (3),
                       integer32            (4),
                       ipAddress            (5),
                       octedString          (6),
                    -- objectId             (7)
                    -- counter64            (8)
                       opaque               (9)
                    }
            DESCRIPTION
                 "The values 'counter64' (7) and 'objectId' (8) are not
                  supported."

        VARIATION   tFltrRPSnmpTRowStatus
            SYNTAX  RowStatus {
                       active               (1),
                    -- notInService         (2)
                    -- notReady             (3)
                       createAndGo          (4),
                    -- createAndWait        (5)
                       destroy              (6)
                    }
            DESCRIPTION
                 "tFltrRPSnmpTRowStatus supports only 'active (1)', 'createAndGo
                  (4)', and 'destroy (6)'."

        VARIATION   tFltrRPSnmpTSnmpVersion
            SYNTAX  INTEGER {
                    -- snmpv1               (1)
                       snmpv2c              (2)
                    -- snmpv3               (3)
                    }
            DESCRIPTION
                 "The values 'snmpv1' (1) and snmpv3 (3) are not supported."

        VARIATION   tFltrRPUcastRtTRowStatus
            SYNTAX  RowStatus {
                       active               (1),
                    -- notInService         (2)
                    -- notReady             (3)
                       createAndGo          (4),
                    -- createAndWait        (5)
                       destroy              (6)
                    }
            DESCRIPTION
                 "tFltrRPUcastRtTRowStatus supports only 'active (1)',
                  'createAndGo (4)', and 'destroy (6)'."

        VARIATION   tFltrRPUrlTRowStatus
            SYNTAX  RowStatus {
                       active               (1),
                    -- notInService         (2)
                    -- notReady             (3)
                       createAndGo          (4),
                    -- createAndWait        (5)
                       destroy              (6)
                    }
            DESCRIPTION
                 "tFltrRPUrlTRowStatus supports only 'active (1)', 'createAndGo
                  (4)', and 'destroy (6)'."

        VARIATION   tFltrRPUrlTRspRowStatus
            SYNTAX  RowStatus {
                       active               (1),
                    -- notInService         (2)
                    -- notReady             (3)
                       createAndGo          (4),
                    -- createAndWait        (5)
                       destroy              (6)
                    }
            DESCRIPTION
                 "tFltrRPUrlTRspRowStatus supports only 'active (1)',
                  'createAndGo (4)', and 'destroy (6)'."

        VARIATION   tIPFilterParamsAction
            DESCRIPTION
                 "The value 'default' (3) is not supported. The value nat(5) is
                  not supported on Nokia 7950"

        VARIATION   tIPFilterParamsNatPolicyName
            ACCESS  not-implemented
            DESCRIPTION
                 "tIPFilterParamsNatPolicyName is not implemented on Nokia 7950
                  in release 14.0."

        VARIATION   tIPv6FilterParamsAction
            DESCRIPTION
                 "The value 'default' (3) is not supported. The value nat(5) is
                  not supported on Nokia 7950"

        VARIATION   tIPv6FilterParamsCflowdIfSample
            DESCRIPTION
                 "The object tIPv6FilterParamsCflowdIfSample is added for future
                  use. The corresponding functionality is not offered in this
                  release. The only actions allowed on this object will
                  therefore be GET and SET to its default value."

        VARIATION   tIPv6FilterParamsCflowdSample
            DESCRIPTION
                 "The object tIPv6FilterParamsCflowdSample is added for future
                  use. The corresponding functionality is not offered in this
                  release. The only actions allowed on this object will
                  therefore be GET and SET to its default value."

        VARIATION   tIPv6FilterParamsExtNatType
            ACCESS  not-implemented
            DESCRIPTION
                 "tIPv6FilterParamsExtNatType is not implemented on Nokia 7950
                  in release 14.0."

        VARIATION   tIPv6FilterParamsNatPolicyName
            ACCESS  not-implemented
            DESCRIPTION
                 "tIPv6FilterParamsNatPolicyName is not implemented on Nokia
                  7950 in release 14.0."

        VARIATION   tIPvXFltrEntryActAction
            DESCRIPTION
                 "The value nat(5) is not supported on Nokia 7950"

        VARIATION   tIPvXFltrEntryActFltrType
            SYNTAX  INTEGER {
                    -- fltrtypeselNone      (0)
                       fltrtypeselIp        (1),
                    -- fltrtypeselMac       (2)
                    -- fltrtypeselCpm       (3)
                       fltrtypeselIpv6      (4)
                    -- fltrtypeselCpm6      (5)
                    -- fltrtypeselCpmMac    (6)
                    }
            DESCRIPTION
                 "tIPvXFltrEntryActFltrType supports only the values
                  'fltrtypeselIp(1)' and 'fltrtypeselIpv6(4)'."

        VARIATION   tIPvXFltrEntryActFwdEsiSFIpType
            SYNTAX  InetAddressType {
                       unknown              (0),
                       ipv4                 (1),
                       ipv6                 (2)
                    -- ipv4z                (3)
                    -- ipv6z                (4)
                    -- dns                  (16)
                    }
            DESCRIPTION
                 "tIPvXFltrEntryActFwdEsiSFIpType supports only the
                  InetAddressType values 'unknown (0)', 'ipv4 (1)', and 'ipv6
                  (2)'."

        VARIATION   tIPvXFltrEntryActFwdNHIpAddrType
            SYNTAX  InetAddressType {
                       unknown              (0),
                       ipv4                 (1),
                       ipv6                 (2)
                    -- ipv4z                (3)
                    -- ipv6z                (4)
                    -- dns                  (16)
                    }
            DESCRIPTION
                 "tIPvXFltrEntryActFwdNHIpAddrType supports only the
                  InetAddressType values 'unknown (0)', 'ipv4 (1)', and 'ipv6
                  (2)'."

        VARIATION   tIPvXFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

        VARIATION   tLiFilterType
            DESCRIPTION
                 "Only values 'fltrtypeselIp (1)', 'fltrtypeselMac (2)' and
                  'fltrtypeselIpv6 (4)' are supported."

        VARIATION   tLiIpFilterParamsDstIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tLiIpFilterParamsSrcIpAddrType
            DESCRIPTION
                 "Support of InetAddressType values depends on the filter type
                  specified by the value of the object tLiFilterType.

                  For 'fltrtypeselIp' only 'unknown (0)' and 'ipv4 (1)' values
                  are supported.

                  For 'fltrtypeselIpv6' only 'unknown (0)' and 'ipv6 (2)'
                  values are supported."

        VARIATION   tMacFilterParamsAction
            DESCRIPTION
                 "The value 'default' (3) is not supported."

        VARIATION   tMacFilterScope
            SYNTAX  INTEGER {
                       exclusive            (1),
                       template             (2),
                       embedded             (3)
                    -- system               (4)
                    }
            DESCRIPTION
                 "The value 'system(4)' is not supported."

        VARIATION   tMacFltrEntryActRowStatus
            SYNTAX  INTEGER {
                       active               (1),
                       notInService         (2),
                    -- notReady             (3)
                       createAndGo          (4),
                       createAndWait(5),
                       destroy              (6)
                    }
            DESCRIPTION
                 "Only values 'active', 'notInService', 'createAndGo',
                  'createAndWait' and 'destroy' are supported."

    ::= { tmnx7950AgentV14v0  13 }

--
-- SROS FRAME_RELAY_DTE CAPABILITIES
--
tmnxSROSFrameRelayDteV14v0        AGENT-CAPABILITIES
    PRODUCT-RELEASE "Nokia SROS"
    STATUS          current
    DESCRIPTION
         "Implementation of Frame Relay DTE capabilities for Nokia SROS systems
          release 14.0"

    SUPPORTS        FRAME-RELAY-DTE-MIB
        INCLUDES {
           frCircuitGroup,
-- EXCLUDE frErrGroup,
-- EXCLUDE frNotificationGroup
           frPortGroup
-- EXCLUDE frTrapGroup,
        }

        VARIATION   frCircuitCommittedBurst
            ACCESS  read-only
            DESCRIPTION
                 "frCircuitCommittedBurst is implemented as read-only on Nokia
                  SROS in release 14.0."

        VARIATION   frCircuitExcessBurst
            ACCESS  read-only
            DESCRIPTION
                 "frCircuitExcessBurst is implemented as read-only on Nokia SROS
                  in release 14.0."

        VARIATION   frCircuitLogicalIfIndex
            ACCESS  read-only
            DESCRIPTION
                 "frCircuitLogicalIfIndex is implemented as read-only on Nokia
                  SROS in release 14.0."

        VARIATION   frCircuitMulticast
            ACCESS  read-only
            DESCRIPTION
                 "frCircuitMulticast is implemented as read-only on Nokia SROS
                  in release 14.0."

        VARIATION   frCircuitRowStatus
            ACCESS  read-only
            DESCRIPTION
                 "frCircuitRowStatus is implemented as read-only on Nokia SROS
                  in release 14.0.

                  New entries in this table cannot be created via SNMP SET
                  requests."

        VARIATION   frCircuitState
            ACCESS  read-only
            DESCRIPTION
                 "frCircuitState is implemented as read-only on Nokia SROS in
                  release 14.0."

        VARIATION   frCircuitThroughput
            ACCESS  read-only
            DESCRIPTION
                 "frCircuitThroughput is implemented as read-only on Nokia SROS
                  in release 14.0."

        VARIATION   frDLCIStatusChange
            ACCESS  not-implemented
            DESCRIPTION
                 "frDLCIStatusChange is not implemented on Nokia SROS in release
                  14.0."

        VARIATION   frDlcmiAddress
            ACCESS  read-only
            DESCRIPTION
                 "frDlcmiAddress is implemented as read-only on Nokia SROS in
                  release 14.0."

        VARIATION   frDlcmiAddressLen
            ACCESS  read-only
            DESCRIPTION
                 "frDlcmiAddressLen is implemented as read-only on Nokia SROS in
                  release 14.0."

        VARIATION   frDlcmiMaxSupportedVCs
            ACCESS  read-only
            DESCRIPTION
                 "frDlcmiMaxSupportedVCs is implemented as read-only on Nokia
                  SROS in release 14.0."

        VARIATION   frDlcmiMulticast
            ACCESS  read-only
            DESCRIPTION
                 "frDlcmiMulticast is implemented as read-only on Nokia SROS in
                  release 14.0."

        VARIATION   frDlcmiRowStatus
            ACCESS  read-only
            DESCRIPTION
                 "frDlcmiRowStatus is implemented as read-only on Nokia SROS in
                  release 14.0.

                  New entries in this table cannot be created via SNMP SET
                  requests."

    ::= { tmnxSROSAgentV14v0  14 }

--
-- 7750SR-7 GMPLS_UNI CAPABILITIES
--
tmnx7750SR7GmplsUniV14v0          AGENT-CAPABILITIES
    PRODUCT-RELEASE "Nokia SROS"
    STATUS          current
    DESCRIPTION
         "Implementation of GMPLS-UNI protocol capabilities for Nokia 7750 SR-7
          systems release 14.0."

    SUPPORTS        TIMETRA-GMPLS-MIB
        INCLUDES {
           tmnxGmplsARHopV13v0Group,
           tmnxGmplsCommandGroup,
           tmnxGmplsGeneralV13v0Group,
           tmnxGmplsLspV13v0Group,
           tmnxGmplsNotificationV13v0Group,
           tmnxGmplsPathV13v0Group,
           tmnxGmplsPeerV13v0Group,
           tmnxGmplsSessionV13v0Group,
           tmnxGmplsTeLinkV13v0Group,
           tmnxGmplsTunGrpMemberV13v0Group,
           tmnxGmplsTunGrpV13v0Group,
           tmnxGmplsV13v1Group
        }

        VARIATION   tmnxGmplsTunGrpMemberRowStatus
            SYNTAX  RowStatus {
                       active               (1),
                    -- notInService         (2)
                    -- notReady             (3)
                       createAndGo          (4),
                    -- createAndWait        (5)
                       destroy              (6)
                    }
            DESCRIPTION
                 "tmnxGmplsTunGrpMemberRowStatus supports only 'active (1)',
                  'createAndGo (4)', and 'destroy (6)'."

        VARIATION   tmnxGmplsTunGrpRowStatus
            SYNTAX  RowStatus {
                       active               (1),
                    -- notInService         (2)
                    -- notReady             (3)
                       createAndGo          (4),
                    -- createAndWait        (5)
                       destroy              (6)
                    }
            DESCRIPTION
                 "tmnxGmplsTunGrpRowStatus supports only 'active (1)',
                  'createAndGo (4)', and 'destroy (6)'."

        VARIATION   vRtrGmplsGeneralRowStatus
            SYNTAX  RowStatus {
                       active               (1),
                    -- notInService         (2)
                    -- notReady             (3)
                       createAndGo          (4),
                    -- createAndWait        (5)
                       destroy              (6)
                    }
            DESCRIPTION
                 "vRtrGmplsGeneralRowStatus supports only 'active (1)',
                  'createAndGo (4)', and 'destroy (6)'."

        VARIATION   vRtrGmplsLspAdminState
            SYNTAX  INTEGER {
                    -- noop                 (1)
                       inService            (2),
                       outOfService         (3)
                    }
            DESCRIPTION
                 "vRtrGmplsLspAdminState supports only the values 'inService
                  (2)' and 'outOfService (3)'."

        VARIATION   vRtrGmplsLspPathAdminState
            SYNTAX  INTEGER {
                    -- noop                 (1)
                       inService            (2),
                       outOfService         (3)
                    }
            DESCRIPTION
                 "vRtrGmplsLspPathAdminState supports only the values 'inService
                  (2)' and 'outOfService (3)'."

        VARIATION   vRtrGmplsLspRowStatus
            SYNTAX  RowStatus {
                       active               (1),
                    -- notInService         (2)
                    -- notReady             (3)
                       createAndGo          (4),
                    -- createAndWait        (5)
                       destroy              (6)
                    }
            DESCRIPTION
                 "vRtrGmplsLspRowStatus supports only 'active (1)', 'createAndGo
                  (4)', and 'destroy (6)'."

        VARIATION   vRtrGmplsLspToAddrType
            SYNTAX  InetAddressType {
                       unknown              (0),
                       ipv4                 (1)
                    -- ipv6                 (2)
                    -- ipv4z                (3)
                    -- ipv6z                (4)
                    -- dns                  (16)
                    }
            DESCRIPTION
                 "vRtrGmplsLspToAddrType supports only the InetAddressType
                  values 'unknown (0)' and 'ipv4 (1)'."

        VARIATION   vRtrGmplsPathHopRowStatus
            SYNTAX  RowStatus {
                       active               (1),
                    -- notInService         (2)
                    -- notReady             (3)
                       createAndGo          (4),
                    -- createAndWait        (5)
                       destroy              (6)
                    }
            DESCRIPTION
                 "vRtrGmplsPathHopRowStatus supports only 'active (1)',
                  'createAndGo (4)', and 'destroy (6)'."

        VARIATION   vRtrGmplsPathRowStatus
            SYNTAX  RowStatus {
                       active               (1),
                    -- notInService         (2)
                    -- notReady             (3)
                       createAndGo          (4),
                    -- createAndWait        (5)
                       destroy              (6)
                    }
            DESCRIPTION
                 "vRtrGmplsPathRowStatus supports only 'active (1)',
                  'createAndGo (4)', and 'destroy (6)'."

        VARIATION   vRtrGmplsPeerDestIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerDestIpAddrType supports only the InetAddressType
                  values 'unknown (0)' and 'ipv4 (1)'."

        VARIATION   vRtrGmplsPeerNextHopIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerNextHopIpAddrType supports only the
                  InetAddressType values 'unknown (0)' and 'ipv4 (1)'."

        VARIATION   vRtrGmplsPeerRowStatus
            SYNTAX  RowStatus {
                       active               (1),
                    -- notInService         (2)
                    -- notReady             (3)
                       createAndGo          (4),
                    -- createAndWait        (5)
                       destroy              (6)
                    }
            DESCRIPTION
                 "vRtrGmplsPeerRowStatus supports only 'active (1)',
                  'createAndGo (4)', and 'destroy (6)'."

    SUPPORTS        TIMETRA-LMP-MIB
        INCLUDES {
           tmnxLmpVRtrCcGroupV13v0,
           tmnxLmpVRtrCcStatsGroupV13v0,
           tmnxLmpVRtrDbLinkGroupV13v0,
           tmnxLmpVRtrGroupV13v0,
           tmnxLmpVRtrNotifGroupV13v0,
           tmnxLmpVRtrPeerGroupV13v0,
           tmnxLmpVRtrTeLinkGroupV13v0,
           tmnxLmpVRtrTeLinkStatsGroupV13v0
        }

        VARIATION   tmnxLmpVRtrCcRowStatus
            SYNTAX  RowStatus {
                       active               (1),
                    -- notInService         (2)
                    -- notReady             (3)
                       createAndGo          (4),
                    -- createAndWait        (5)
                       destroy              (6)
                    }
            DESCRIPTION
                 "tmnxLmpVRtrCcRowStatus supports only 'active (1)',
                  'createAndGo (4)', and 'destroy (6)'."

        VARIATION   tmnxLmpVRtrDbLinkRowStatus
            SYNTAX  RowStatus {
                       active               (1),
                    -- notInService         (2)
                    -- notReady             (3)
                       createAndGo          (4),
                    -- createAndWait        (5)
                       destroy              (6)
                    }
            DESCRIPTION
                 "tmnxLmpVRtrDbLinkRowStatus supports only 'active (1)',
                  'createAndGo (4)', and 'destroy (6)'."

        VARIATION   tmnxLmpVRtrGmplsLoopbackAddrType
            SYNTAX  InetAddressType {
                    -- unknown              (0)
                       ipv4                 (1)
                    -- ipv6                 (2)
                    -- ipv4z                (3)
                    -- ipv6z                (4)
                    -- dns                  (16)
                    }
            DESCRIPTION
                 "tmnxLmpVRtrGmplsLoopbackAddrType supports only the
                  InetAddressType value 'ipv4 (1)'."

        VARIATION   tmnxLmpVRtrPeerRowStatus
            SYNTAX  RowStatus {
                       active               (1),
                    -- notInService         (2)
                    -- notReady             (3)
                       createAndGo          (4),
                    -- createAndWait        (5)
                       destroy              (6)
                    }
            DESCRIPTION
                 "tmnxLmpVRtrPeerRowStatus supports only 'active (1)',
                  'createAndGo (4)', and 'destroy (6)'."

        VARIATION   tmnxLmpVRtrRowStatus
            SYNTAX  RowStatus {
                       active               (1),
                    -- notInService         (2)
                    -- notReady             (3)
                       createAndGo          (4),
                    -- createAndWait        (5)
                       destroy              (6)
                    }
            DESCRIPTION
                 "tmnxLmpVRtrRowStatus supports only 'active (1)', 'createAndGo
                  (4)', and 'destroy (6)'."

        VARIATION   tmnxLmpVRtrTeLinkRowStatus
            SYNTAX  RowStatus {
                       active               (1),
                    -- notInService         (2)
                    -- notReady             (3)
                       createAndGo          (4),
                    -- createAndWait        (5)
                       destroy              (6)
                    }
            DESCRIPTION
                 "tmnxLmpVRtrTeLinkRowStatus supports only 'active (1)',
                  'createAndGo (4)', and 'destroy (6)'."

    ::= { tmnx7750SR7AgentV14v0  17 }

--
-- 7750SR-12 GMPLS_UNI CAPABILITIES
--
tmnx7750SR12GmplsUniV14v0         AGENT-CAPABILITIES
    PRODUCT-RELEASE "Nokia SROS"
    STATUS          current
    DESCRIPTION
         "Implementation of GMPLS-UNI protocol capabilities for Nokia 7750 SR-12
          systems release 14.0."

    SUPPORTS        TIMETRA-GMPLS-MIB
        INCLUDES {
           tmnxGmplsARHopV13v0Group,
           tmnxGmplsCommandGroup,
           tmnxGmplsGeneralV13v0Group,
           tmnxGmplsLspV13v0Group,
           tmnxGmplsNotificationV13v0Group,
           tmnxGmplsPathV13v0Group,
           tmnxGmplsPeerV13v0Group,
           tmnxGmplsSessionV13v0Group,
           tmnxGmplsTeLinkV13v0Group,
           tmnxGmplsTunGrpMemberV13v0Group,
           tmnxGmplsTunGrpV13v0Group,
           tmnxGmplsV13v1Group
        }

        VARIATION   tmnxGmplsTunGrpMemberRowStatus
            SYNTAX  RowStatus {
                       active               (1),
                    -- notInService         (2)
                    -- notReady             (3)
                       createAndGo          (4),
                    -- createAndWait        (5)
                       destroy              (6)
                    }
            DESCRIPTION
                 "tmnxGmplsTunGrpMemberRowStatus supports only 'active (1)',
                  'createAndGo (4)', and 'destroy (6)'."

        VARIATION   tmnxGmplsTunGrpRowStatus
            SYNTAX  RowStatus {
                       active               (1),
                    -- notInService         (2)
                    -- notReady             (3)
                       createAndGo          (4),
                    -- createAndWait        (5)
                       destroy              (6)
                    }
            DESCRIPTION
                 "tmnxGmplsTunGrpRowStatus supports only 'active (1)',
                  'createAndGo (4)', and 'destroy (6)'."

        VARIATION   vRtrGmplsGeneralRowStatus
            SYNTAX  RowStatus {
                       active               (1),
                    -- notInService         (2)
                    -- notReady             (3)
                       createAndGo          (4),
                    -- createAndWait        (5)
                       destroy              (6)
                    }
            DESCRIPTION
                 "vRtrGmplsGeneralRowStatus supports only 'active (1)',
                  'createAndGo (4)', and 'destroy (6)'."

        VARIATION   vRtrGmplsLspAdminState
            SYNTAX  INTEGER {
                    -- noop                 (1)
                       inService            (2),
                       outOfService         (3)
                    }
            DESCRIPTION
                 "vRtrGmplsLspAdminState supports only the values 'inService
                  (2)' and 'outOfService (3)'."

        VARIATION   vRtrGmplsLspPathAdminState
            SYNTAX  INTEGER {
                    -- noop                 (1)
                       inService            (2),
                       outOfService         (3)
                    }
            DESCRIPTION
                 "vRtrGmplsLspPathAdminState supports only the values 'inService
                  (2)' and 'outOfService (3)'."

        VARIATION   vRtrGmplsLspRowStatus
            SYNTAX  RowStatus {
                       active               (1),
                    -- notInService         (2)
                    -- notReady             (3)
                       createAndGo          (4),
                    -- createAndWait        (5)
                       destroy              (6)
                    }
            DESCRIPTION
                 "vRtrGmplsLspRowStatus supports only 'active (1)', 'createAndGo
                  (4)', and 'destroy (6)'."

        VARIATION   vRtrGmplsLspToAddrType
            SYNTAX  InetAddressType {
                       unknown              (0),
                       ipv4                 (1)
                    -- ipv6                 (2)
                    -- ipv4z                (3)
                    -- ipv6z                (4)
                    -- dns                  (16)
                    }
            DESCRIPTION
                 "vRtrGmplsLspToAddrType supports only the InetAddressType
                  values 'unknown (0)' and 'ipv4 (1)'."

        VARIATION   vRtrGmplsPathHopRowStatus
            SYNTAX  RowStatus {
                       active               (1),
                    -- notInService         (2)
                    -- notReady             (3)
                       createAndGo          (4),
                    -- createAndWait        (5)
                       destroy              (6)
                    }
            DESCRIPTION
                 "vRtrGmplsPathHopRowStatus supports only 'active (1)',
                  'createAndGo (4)', and 'destroy (6)'."

        VARIATION   vRtrGmplsPathRowStatus
            SYNTAX  RowStatus {
                       active               (1),
                    -- notInService         (2)
                    -- notReady             (3)
                       createAndGo          (4),
                    -- createAndWait        (5)
                       destroy              (6)
                    }
            DESCRIPTION
                 "vRtrGmplsPathRowStatus supports only 'active (1)',
                  'createAndGo (4)', and 'destroy (6)'."

        VARIATION   vRtrGmplsPeerDestIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerDestIpAddrType supports only the InetAddressType
                  values 'unknown (0)' and 'ipv4 (1)'."

        VARIATION   vRtrGmplsPeerNextHopIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerNextHopIpAddrType supports only the
                  InetAddressType values 'unknown (0)' and 'ipv4 (1)'."

        VARIATION   vRtrGmplsPeerRowStatus
            SYNTAX  RowStatus {
                       active               (1),
                    -- notInService         (2)
                    -- notReady             (3)
                       createAndGo          (4),
                    -- createAndWait        (5)
                       destroy              (6)
                    }
            DESCRIPTION
                 "vRtrGmplsPeerRowStatus supports only 'active (1)',
                  'createAndGo (4)', and 'destroy (6)'."

    SUPPORTS        TIMETRA-LMP-MIB
        INCLUDES {
           tmnxLmpVRtrCcGroupV13v0,
           tmnxLmpVRtrCcStatsGroupV13v0,
           tmnxLmpVRtrDbLinkGroupV13v0,
           tmnxLmpVRtrGroupV13v0,
           tmnxLmpVRtrNotifGroupV13v0,
           tmnxLmpVRtrPeerGroupV13v0,
           tmnxLmpVRtrTeLinkGroupV13v0,
           tmnxLmpVRtrTeLinkStatsGroupV13v0
        }

        VARIATION   tmnxLmpVRtrCcRowStatus
            SYNTAX  RowStatus {
                       active               (1),
                    -- notInService         (2)
                    -- notReady             (3)
                       createAndGo          (4),
                    -- createAndWait        (5)
                       destroy              (6)
                    }
            DESCRIPTION
                 "tmnxLmpVRtrCcRowStatus supports only 'active (1)',
                  'createAndGo (4)', and 'destroy (6)'."

        VARIATION   tmnxLmpVRtrDbLinkRowStatus
            SYNTAX  RowStatus {
                       active               (1),
                    -- notInService         (2)
                    -- notReady             (3)
                       createAndGo          (4),
                    -- createAndWait        (5)
                       destroy              (6)
                    }
            DESCRIPTION
                 "tmnxLmpVRtrDbLinkRowStatus supports only 'active (1)',
                  'createAndGo (4)', and 'destroy (6)'."

        VARIATION   tmnxLmpVRtrGmplsLoopbackAddrType
            SYNTAX  InetAddressType {
                    -- unknown              (0)
                       ipv4                 (1)
                    -- ipv6                 (2)
                    -- ipv4z                (3)
                    -- ipv6z                (4)
                    -- dns                  (16)
                    }
            DESCRIPTION
                 "tmnxLmpVRtrGmplsLoopbackAddrType supports only the
                  InetAddressType value 'ipv4 (1)'."

        VARIATION   tmnxLmpVRtrPeerRowStatus
            SYNTAX  RowStatus {
                       active               (1),
                    -- notInService         (2)
                    -- notReady             (3)
                       createAndGo          (4),
                    -- createAndWait        (5)
                       destroy              (6)
                    }
            DESCRIPTION
                 "tmnxLmpVRtrPeerRowStatus supports only 'active (1)',
                  'createAndGo (4)', and 'destroy (6)'."

        VARIATION   tmnxLmpVRtrRowStatus
            SYNTAX  RowStatus {
                       active               (1),
                    -- notInService         (2)
                    -- notReady             (3)
                       createAndGo          (4),
                    -- createAndWait        (5)
                       destroy              (6)
                    }
            DESCRIPTION
                 "tmnxLmpVRtrRowStatus supports only 'active (1)', 'createAndGo
                  (4)', and 'destroy (6)'."

        VARIATION   tmnxLmpVRtrTeLinkRowStatus
            SYNTAX  RowStatus {
                       active               (1),
                    -- notInService         (2)
                    -- notReady             (3)
                       createAndGo          (4),
                    -- createAndWait        (5)
                       destroy              (6)
                    }
            DESCRIPTION
                 "tmnxLmpVRtrTeLinkRowStatus supports only 'active (1)',
                  'createAndGo (4)', and 'destroy (6)'."

    ::= { tmnx7750SR12AgentV14v0  17 }

--
-- 7750SR-12e GMPLS_UNI CAPABILITIES
--
tmnx7750SR12eGmplsUniV14v0        AGENT-CAPABILITIES
    PRODUCT-RELEASE "Nokia SROS"
    STATUS          current
    DESCRIPTION
         "Implementation of GMPLS-UNI protocol capabilities for Nokia 7750
          SR-12e systems release 14.0."

    SUPPORTS        TIMETRA-GMPLS-MIB
        INCLUDES {
           tmnxGmplsARHopV13v0Group,
           tmnxGmplsCommandGroup,
           tmnxGmplsGeneralV13v0Group,
           tmnxGmplsLspV13v0Group,
           tmnxGmplsNotificationV13v0Group,
           tmnxGmplsPathV13v0Group,
           tmnxGmplsPeerV13v0Group,
           tmnxGmplsSessionV13v0Group,
           tmnxGmplsTeLinkV13v0Group,
           tmnxGmplsTunGrpMemberV13v0Group,
           tmnxGmplsTunGrpV13v0Group,
           tmnxGmplsV13v1Group
        }

        VARIATION   tmnxGmplsTunGrpMemberRowStatus
            SYNTAX  RowStatus {
                       active               (1),
                    -- notInService         (2)
                    -- notReady             (3)
                       createAndGo          (4),
                    -- createAndWait        (5)
                       destroy              (6)
                    }
            DESCRIPTION
                 "tmnxGmplsTunGrpMemberRowStatus supports only 'active (1)',
                  'createAndGo (4)', and 'destroy (6)'."

        VARIATION   tmnxGmplsTunGrpRowStatus
            SYNTAX  RowStatus {
                       active               (1),
                    -- notInService         (2)
                    -- notReady             (3)
                       createAndGo          (4),
                    -- createAndWait        (5)
                       destroy              (6)
                    }
            DESCRIPTION
                 "tmnxGmplsTunGrpRowStatus supports only 'active (1)',
                  'createAndGo (4)', and 'destroy (6)'."

        VARIATION   vRtrGmplsGeneralRowStatus
            SYNTAX  RowStatus {
                       active               (1),
                    -- notInService         (2)
                    -- notReady             (3)
                       createAndGo          (4),
                    -- createAndWait        (5)
                       destroy              (6)
                    }
            DESCRIPTION
                 "vRtrGmplsGeneralRowStatus supports only 'active (1)',
                  'createAndGo (4)', and 'destroy (6)'."

        VARIATION   vRtrGmplsLspAdminState
            SYNTAX  INTEGER {
                    -- noop                 (1)
                       inService            (2),
                       outOfService         (3)
                    }
            DESCRIPTION
                 "vRtrGmplsLspAdminState supports only the values 'inService
                  (2)' and 'outOfService (3)'."

        VARIATION   vRtrGmplsLspPathAdminState
            SYNTAX  INTEGER {
                    -- noop                 (1)
                       inService            (2),
                       outOfService         (3)
                    }
            DESCRIPTION
                 "vRtrGmplsLspPathAdminState supports only the values 'inService
                  (2)' and 'outOfService (3)'."

        VARIATION   vRtrGmplsLspRowStatus
            SYNTAX  RowStatus {
                       active               (1),
                    -- notInService         (2)
                    -- notReady             (3)
                       createAndGo          (4),
                    -- createAndWait        (5)
                       destroy              (6)
                    }
            DESCRIPTION
                 "vRtrGmplsLspRowStatus supports only 'active (1)', 'createAndGo
                  (4)', and 'destroy (6)'."

        VARIATION   vRtrGmplsLspToAddrType
            SYNTAX  InetAddressType {
                       unknown              (0),
                       ipv4                 (1)
                    -- ipv6                 (2)
                    -- ipv4z                (3)
                    -- ipv6z                (4)
                    -- dns                  (16)
                    }
            DESCRIPTION
                 "vRtrGmplsLspToAddrType supports only the InetAddressType
                  values 'unknown (0)' and 'ipv4 (1)'."

        VARIATION   vRtrGmplsPathHopRowStatus
            SYNTAX  RowStatus {
                       active               (1),
                    -- notInService         (2)
                    -- notReady             (3)
                       createAndGo          (4),
                    -- createAndWait        (5)
                       destroy              (6)
                    }
            DESCRIPTION
                 "vRtrGmplsPathHopRowStatus supports only 'active (1)',
                  'createAndGo (4)', and 'destroy (6)'."

        VARIATION   vRtrGmplsPathRowStatus
            SYNTAX  RowStatus {
                       active               (1),
                    -- notInService         (2)
                    -- notReady             (3)
                       createAndGo          (4),
                    -- createAndWait        (5)
                       destroy              (6)
                    }
            DESCRIPTION
                 "vRtrGmplsPathRowStatus supports only 'active (1)',
                  'createAndGo (4)', and 'destroy (6)'."

        VARIATION   vRtrGmplsPeerDestIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerDestIpAddrType supports only the InetAddressType
                  values 'unknown (0)' and 'ipv4 (1)'."

        VARIATION   vRtrGmplsPeerNextHopIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerNextHopIpAddrType supports only the
                  InetAddressType values 'unknown (0)' and 'ipv4 (1)'."

        VARIATION   vRtrGmplsPeerRowStatus
            SYNTAX  RowStatus {
                       active               (1),
                    -- notInService         (2)
                    -- notReady             (3)
                       createAndGo          (4),
                    -- createAndWait        (5)
                       destroy              (6)
                    }
            DESCRIPTION
                 "vRtrGmplsPeerRowStatus supports only 'active (1)',
                  'createAndGo (4)', and 'destroy (6)'."

    SUPPORTS        TIMETRA-LMP-MIB
        INCLUDES {
           tmnxLmpVRtrCcGroupV13v0,
           tmnxLmpVRtrCcStatsGroupV13v0,
           tmnxLmpVRtrDbLinkGroupV13v0,
           tmnxLmpVRtrGroupV13v0,
           tmnxLmpVRtrNotifGroupV13v0,
           tmnxLmpVRtrPeerGroupV13v0,
           tmnxLmpVRtrTeLinkGroupV13v0,
           tmnxLmpVRtrTeLinkStatsGroupV13v0
        }

        VARIATION   tmnxLmpVRtrCcRowStatus
            SYNTAX  RowStatus {
                       active               (1),
                    -- notInService         (2)
                    -- notReady             (3)
                       createAndGo          (4),
                    -- createAndWait        (5)
                       destroy              (6)
                    }
            DESCRIPTION
                 "tmnxLmpVRtrCcRowStatus supports only 'active (1)',
                  'createAndGo (4)', and 'destroy (6)'."

        VARIATION   tmnxLmpVRtrDbLinkRowStatus
            SYNTAX  RowStatus {
                       active               (1),
                    -- notInService         (2)
                    -- notReady             (3)
                       createAndGo          (4),
                    -- createAndWait        (5)
                       destroy              (6)
                    }
            DESCRIPTION
                 "tmnxLmpVRtrDbLinkRowStatus supports only 'active (1)',
                  'createAndGo (4)', and 'destroy (6)'."

        VARIATION   tmnxLmpVRtrGmplsLoopbackAddrType
            SYNTAX  InetAddressType {
                    -- unknown              (0)
                       ipv4                 (1)
                    -- ipv6                 (2)
                    -- ipv4z                (3)
                    -- ipv6z                (4)
                    -- dns                  (16)
                    }
            DESCRIPTION
                 "tmnxLmpVRtrGmplsLoopbackAddrType supports only the
                  InetAddressType value 'ipv4 (1)'."

        VARIATION   tmnxLmpVRtrPeerRowStatus
            SYNTAX  RowStatus {
                       active               (1),
                    -- notInService         (2)
                    -- notReady             (3)
                       createAndGo          (4),
                    -- createAndWait        (5)
                       destroy              (6)
                    }
            DESCRIPTION
                 "tmnxLmpVRtrPeerRowStatus supports only 'active (1)',
                  'createAndGo (4)', and 'destroy (6)'."

        VARIATION   tmnxLmpVRtrRowStatus
            SYNTAX  RowStatus {
                       active               (1),
                    -- notInService         (2)
                    -- notReady             (3)
                       createAndGo          (4),
                    -- createAndWait        (5)
                       destroy              (6)
                    }
            DESCRIPTION
                 "tmnxLmpVRtrRowStatus supports only 'active (1)', 'createAndGo
                  (4)', and 'destroy (6)'."

        VARIATION   tmnxLmpVRtrTeLinkRowStatus
            SYNTAX  RowStatus {
                       active               (1),
                    -- notInService         (2)
                    -- notReady             (3)
                       createAndGo          (4),
                    -- createAndWait        (5)
                       destroy              (6)
                    }
            DESCRIPTION
                 "tmnxLmpVRtrTeLinkRowStatus supports only 'active (1)',
                  'createAndGo (4)', and 'destroy (6)'."

    ::= { tmnx7750SR12eAgentV14v0  17 }

--
-- 7950 GMPLS_UNI CAPABILITIES
--
tmnx7950GmplsUniV14v0             AGENT-CAPABILITIES
    PRODUCT-RELEASE "Nokia SROS"
    STATUS          current
    DESCRIPTION
         "Implementation of GMPLS-UNI protocol capabilities for Nokia 7950
          systems release 14.0."

    SUPPORTS        TIMETRA-GMPLS-MIB
        INCLUDES {
           tmnxGmplsARHopV13v0Group,
           tmnxGmplsCommandGroup,
           tmnxGmplsGeneralV13v0Group,
           tmnxGmplsLspV13v0Group,
           tmnxGmplsNotificationV13v0Group,
           tmnxGmplsPathV13v0Group,
           tmnxGmplsPeerV13v0Group,
           tmnxGmplsSessionV13v0Group,
           tmnxGmplsTeLinkV13v0Group,
           tmnxGmplsTunGrpMemberV13v0Group,
           tmnxGmplsTunGrpV13v0Group,
           tmnxGmplsV13v1Group
        }

        VARIATION   tmnxGmplsTunGrpMemberRowStatus
            SYNTAX  RowStatus {
                       active               (1),
                    -- notInService         (2)
                    -- notReady             (3)
                       createAndGo          (4),
                    -- createAndWait        (5)
                       destroy              (6)
                    }
            DESCRIPTION
                 "tmnxGmplsTunGrpMemberRowStatus supports only 'active (1)',
                  'createAndGo (4)', and 'destroy (6)'."

        VARIATION   tmnxGmplsTunGrpRowStatus
            SYNTAX  RowStatus {
                       active               (1),
                    -- notInService         (2)
                    -- notReady             (3)
                       createAndGo          (4),
                    -- createAndWait        (5)
                       destroy              (6)
                    }
            DESCRIPTION
                 "tmnxGmplsTunGrpRowStatus supports only 'active (1)',
                  'createAndGo (4)', and 'destroy (6)'."

        VARIATION   vRtrGmplsGeneralRowStatus
            SYNTAX  RowStatus {
                       active               (1),
                    -- notInService         (2)
                    -- notReady             (3)
                       createAndGo          (4),
                    -- createAndWait        (5)
                       destroy              (6)
                    }
            DESCRIPTION
                 "vRtrGmplsGeneralRowStatus supports only 'active (1)',
                  'createAndGo (4)', and 'destroy (6)'."

        VARIATION   vRtrGmplsLspAdminState
            SYNTAX  INTEGER {
                    -- noop                 (1)
                       inService            (2),
                       outOfService         (3)
                    }
            DESCRIPTION
                 "vRtrGmplsLspAdminState supports only the values 'inService
                  (2)' and 'outOfService (3)'."

        VARIATION   vRtrGmplsLspPathAdminState
            SYNTAX  INTEGER {
                    -- noop                 (1)
                       inService            (2),
                       outOfService         (3)
                    }
            DESCRIPTION
                 "vRtrGmplsLspPathAdminState supports only the values 'inService
                  (2)' and 'outOfService (3)'."

        VARIATION   vRtrGmplsLspRowStatus
            SYNTAX  RowStatus {
                       active               (1),
                    -- notInService         (2)
                    -- notReady             (3)
                       createAndGo          (4),
                    -- createAndWait        (5)
                       destroy              (6)
                    }
            DESCRIPTION
                 "vRtrGmplsLspRowStatus supports only 'active (1)', 'createAndGo
                  (4)', and 'destroy (6)'."

        VARIATION   vRtrGmplsLspToAddrType
            SYNTAX  InetAddressType {
                       unknown              (0),
                       ipv4                 (1)
                    -- ipv6                 (2)
                    -- ipv4z                (3)
                    -- ipv6z                (4)
                    -- dns                  (16)
                    }
            DESCRIPTION
                 "vRtrGmplsLspToAddrType supports only the InetAddressType
                  values 'unknown (0)' and 'ipv4 (1)'."

        VARIATION   vRtrGmplsPathHopRowStatus
            SYNTAX  RowStatus {
                       active               (1),
                    -- notInService         (2)
                    -- notReady             (3)
                       createAndGo          (4),
                    -- createAndWait        (5)
                       destroy              (6)
                    }
            DESCRIPTION
                 "vRtrGmplsPathHopRowStatus supports only 'active (1)',
                  'createAndGo (4)', and 'destroy (6)'."

        VARIATION   vRtrGmplsPathRowStatus
            SYNTAX  RowStatus {
                       active               (1),
                    -- notInService         (2)
                    -- notReady             (3)
                       createAndGo          (4),
                    -- createAndWait        (5)
                       destroy              (6)
                    }
            DESCRIPTION
                 "vRtrGmplsPathRowStatus supports only 'active (1)',
                  'createAndGo (4)', and 'destroy (6)'."

        VARIATION   vRtrGmplsPeerDestIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerDestIpAddrType supports only the InetAddressType
                  values 'unknown (0)' and 'ipv4 (1)'."

        VARIATION   vRtrGmplsPeerNextHopIpAddrType
            SYNTAX  InetAddressType {
                       unknown              (0),
                       ipv4                 (1)
                    -- ipv6                 (2)
                    -- ipv4z                (3)
                    -- ipv6z                (4)
                    -- dns                  (16)
                    }
            DESCRIPTION
                 "vRtrGmplsPeerNextHopIpAddrType supports only the
                  InetAddressType values 'unknown (0)' and 'ipv4 (1)'."

        VARIATION   vRtrGmplsPeerRowStatus
            SYNTAX  RowStatus {
                       active               (1),
                    -- notInService         (2)
                    -- notReady             (3)
                       createAndGo          (4),
                    -- createAndWait        (5)
                       destroy              (6)
                    }
            DESCRIPTION
                 "vRtrGmplsPeerRowStatus supports only 'active (1)',
                  'createAndGo (4)', and 'destroy (6)'."

    SUPPORTS        TIMETRA-LMP-MIB
        INCLUDES {
           tmnxLmpVRtrCcGroupV13v0,
           tmnxLmpVRtrCcStatsGroupV13v0,
           tmnxLmpVRtrDbLinkGroupV13v0,
           tmnxLmpVRtrGroupV13v0,
           tmnxLmpVRtrNotifGroupV13v0,
           tmnxLmpVRtrPeerGroupV13v0,
           tmnxLmpVRtrTeLinkGroupV13v0,
           tmnxLmpVRtrTeLinkStatsGroupV13v0
        }

        VARIATION   tmnxLmpVRtrCcRowStatus
            SYNTAX  RowStatus {
                       active               (1),
                    -- notInService         (2)
                    -- notReady             (3)
                       createAndGo          (4),
                    -- createAndWait        (5)
                       destroy              (6)
                    }
            DESCRIPTION
                 "tmnxLmpVRtrCcRowStatus supports only 'active (1)',
                  'createAndGo (4)', and 'destroy (6)'."

        VARIATION   tmnxLmpVRtrDbLinkRowStatus
            SYNTAX  RowStatus {
                       active               (1),
                    -- notInService         (2)
                    -- notReady             (3)
                       createAndGo          (4),
                    -- createAndWait        (5)
                       destroy              (6)
                    }
            DESCRIPTION
                 "tmnxLmpVRtrDbLinkRowStatus supports only 'active (1)',
                  'createAndGo (4)', and 'destroy (6)'."

        VARIATION   tmnxLmpVRtrGmplsLoopbackAddrType
            SYNTAX  InetAddressType {
                    -- unknown              (0)
                       ipv4                 (1)
                    -- ipv6                 (2)
                    -- ipv4z                (3)
                    -- ipv6z                (4)
                    -- dns                  (16)
                    }
            DESCRIPTION
                 "tmnxLmpVRtrGmplsLoopbackAddrType supports only the
                  InetAddressType value 'ipv4 (1)'."

        VARIATION   tmnxLmpVRtrPeerRowStatus
            SYNTAX  RowStatus {
                       active               (1),
                    -- notInService         (2)
                    -- notReady             (3)
                       createAndGo          (4),
                    -- createAndWait        (5)
                       destroy              (6)
                    }
            DESCRIPTION
                 "tmnxLmpVRtrPeerRowStatus supports only 'active (1)',
                  'createAndGo (4)', and 'destroy (6)'."

        VARIATION   tmnxLmpVRtrRowStatus
            SYNTAX  RowStatus {
                       active               (1),
                    -- notInService         (2)
                    -- notReady             (3)
                       createAndGo          (4),
                    -- createAndWait        (5)
                       destroy              (6)
                    }
            DESCRIPTION
                 "tmnxLmpVRtrRowStatus supports only 'active (1)', 'createAndGo
                  (4)', and 'destroy (6)'."

        VARIATION   tmnxLmpVRtrTeLinkRowStatus
            SYNTAX  RowStatus {
                       active               (1),
                    -- notInService         (2)
                    -- notReady             (3)
                       createAndGo          (4),
                    -- createAndWait        (5)
                       destroy              (6)
                    }
            DESCRIPTION
                 "tmnxLmpVRtrTeLinkRowStatus supports only 'active (1)',
                  'createAndGo (4)', and 'destroy (6)'."

    ::= { tmnx7950AgentV14v0  17 }

--
-- SROS GSMP CAPABILITIES
--
tmnxSROSGsmpV14v0                 AGENT-CAPABILITIES
    PRODUCT-RELEASE "Nokia SROS"
    STATUS          current
    DESCRIPTION
         "Implementation of the General Switch Management Protocol (GSMP) and
          the Access Node Control Protocol (ANCP) on Nokia SROS systems release
          14.0."

    SUPPORTS        TIMETRA-GSMP-MIB
        INCLUDES {
           tmnxGsmpQosV13v0Group,
           tmnxGsmpSchedulerRateV11v0Group,
           tmnxGsmpV13v0Group,
           tmnxGsmpV5v0GNotificationGroup
        }

        VARIATION   tmnxAncpPlcyRowStatus
            SYNTAX  RowStatus {
                       active               (1),
                    -- notInService         (2)
                    -- notReady             (3)
                       createAndGo          (4),
                    -- createAndWait        (5)
                       destroy              (6)
                    }
            DESCRIPTION
                 "tmnxAncpPlcyRowStatus supports only 'active (1)', 'createAndGo
                  (4)', and 'destroy (6)'."

        VARIATION   tmnxAncpStaticMapMssRowStatus
            SYNTAX  RowStatus {
                       active               (1),
                    -- notInService         (2)
                    -- notReady             (3)
                       createAndGo          (4),
                    -- createAndWait        (5)
                       destroy              (6)
                    }
            DESCRIPTION
                 "tmnxAncpStaticMapMssRowStatus supports only 'active (1)',
                  'createAndGo (4)', and 'destroy (6)'."

        VARIATION   tmnxAncpStaticMapSapRowStatus
            SYNTAX  RowStatus {
                       active               (1),
                    -- notInService         (2)
                    -- notReady             (3)
                       createAndGo          (4),
                    -- createAndWait        (5)
                       destroy              (6)
                    }
            DESCRIPTION
                 "tmnxAncpStaticMapSapRowStatus supports only 'active (1)',
                  'createAndGo (4)', and 'destroy (6)'."

        VARIATION   tmnxGsmpCfgAdminState
            SYNTAX  INTEGER {
                    -- noop                 (1)
                       inService            (2),
                       outOfService         (3)
                    }
            DESCRIPTION
                 "tmnxGsmpCfgAdminState supports only the values 'inService (2)'
                  and 'outOfService (3)'."

        VARIATION   tmnxGsmpGrpCfgAdminState
            SYNTAX  INTEGER {
                    -- noop                 (1)
                       inService            (2),
                       outOfService         (3)
                    }
            DESCRIPTION
                 "tmnxGsmpGrpCfgAdminState supports only the values 'inService
                  (2)' and 'outOfService (3)'."

        VARIATION   tmnxGsmpGrpCfgAncpDynTopoDiscCap
            SYNTAX  INTEGER {
                    -- noop                 (1)
                       inService            (2),
                       outOfService         (3)
                    }
            DESCRIPTION
                 "tmnxGsmpGrpCfgAncpDynTopoDiscCap supports only the values
                  'inService (2)' and 'outOfService (3)'."

        VARIATION   tmnxGsmpGrpCfgAncpOamCap
            SYNTAX  INTEGER {
                    -- noop                 (1)
                       inService            (2),
                       outOfService         (3)
                    }
            DESCRIPTION
                 "tmnxGsmpGrpCfgAncpOamCap supports only the values 'inService
                  (2)' and 'outOfService (3)'."

        VARIATION   tmnxGsmpGrpCfgRowStatus
            SYNTAX  RowStatus {
                       active               (1),
                    -- notInService         (2)
                    -- notReady             (3)
                       createAndGo          (4),
                    -- createAndWait        (5)
                       destroy              (6)
                    }
            DESCRIPTION
                 "tmnxGsmpGrpCfgRowStatus supports only 'active (1)',
                  'createAndGo (4)', and 'destroy (6)'."

        VARIATION   tmnxGsmpGrpNbrAdminState
            SYNTAX  INTEGER {
                    -- noop                 (1)
                       inService            (2),
                       outOfService         (3)
                    }
            DESCRIPTION
                 "tmnxGsmpGrpNbrAdminState supports only the values 'inService
                  (2)' and 'outOfService (3)'."

        VARIATION   tmnxGsmpGrpNbrRowStatus
            SYNTAX  RowStatus {
                       active               (1),
                    -- notInService         (2)
                    -- notReady             (3)
                       createAndGo          (4),
                    -- createAndWait        (5)
                       destroy              (6)
                    }
            DESCRIPTION
                 "tmnxGsmpGrpNbrRowStatus supports only 'active (1)',
                  'createAndGo (4)', and 'destroy (6)'."

    ::= { tmnxSROSAgentV14v0  50 }

--
-- SROS IEEE8021_PAE CAPABILITIES
--
tmnxSROSIeee8021PaeV14v0          AGENT-CAPABILITIES
    PRODUCT-RELEASE "Nokia SROS"
    STATUS          current
    DESCRIPTION
         "Implementation of IEEE 8021 PAE protocol capabilities for Nokia SROS
          systems release 14.0."

    SUPPORTS        ALCATEL-IEEE8021-PAE-MIB
        INCLUDES {
           alxDot1xAuthConfigGroup,
           alxDot1xRadiusPlcyGroup
        }

    SUPPORTS        IEEE8021-PAE-MIB
        INCLUDES {
           dot1xPaeAuthConfigGroup,
           dot1xPaeAuthDiagGroup,
           dot1xPaeAuthSessionStatsGroup,
           dot1xPaeAuthStatsGroup,
-- EXCLUDE dot1xPaeSuppConfigGroup,
-- EXCLUDE dot1xPaeSuppStatsGroup
           dot1xPaeSystemGroup
        }

        VARIATION   dot1xAuthAdminControlledDirections
            ACCESS  read-only
            DESCRIPTION
                 "dot1xAuthAdminControlledDirections is implemented as read-only
                  on Nokia SROS in release 14.0."

        VARIATION   dot1xAuthKeyTxEnabled
            SYNTAX  TruthValue
            ACCESS  read-only
            DESCRIPTION
                 "dot1xAuthKeyTxEnabled is read-only. The value returned is
                  always false."

    ::= { tmnxSROSAgentV14v0  15 }

--
-- SROS IF_GRP_HANDLER CAPABILITIES
--
tmnxSROSIfGrpHandlerV14v0         AGENT-CAPABILITIES
    PRODUCT-RELEASE "Nokia SROS"
    STATUS          current
    DESCRIPTION
         "Implementation of Interface Group Handler capabilities for Nokia SROS
          systems release 14.0."

    SUPPORTS        TIMETRA-IF-GROUP-HANDLER-MIB
        INCLUDES {
           tmnxIfGroupHandlerConfigGroup,
           tmnxIfGroupHandlerMemberGroup,
           tmnxIfGroupHandlerProtocolGroup,
           tmnxIfGroupHandlerTimeStampGroup,
           tmnxIfGroupHdlrNotificationGroup
        }

    ::= { tmnxSROSAgentV14v0  75 }

--
-- SROS IGMP CAPABILITIES
--
tmnxSROSIgmpV14v0                 AGENT-CAPABILITIES
    PRODUCT-RELEASE "Nokia SROS"
    STATUS          current
    DESCRIPTION
         "Implementation of IGMP protocol capabilities for Nokia SROS systems
          release 14.0."

    SUPPORTS        IGMP-STD-MIB
        INCLUDES {
           igmpBaseMIBGroup,
           igmpHostOptMIBGroup,
           igmpRouterMIBGroup,
           igmpV2HostMIBGroup,
           igmpV2ProxyMIBGroup,
           igmpV2RouterMIBGroup
        }

        VARIATION   igmpCacheSelf
            ACCESS  read-only
            DESCRIPTION
                 "igmpCacheSelf is implemented as read-only on Nokia SROS in
                  release 14.0."

        VARIATION   igmpCacheStatus
            ACCESS  read-only
            DESCRIPTION
                 "igmpCacheStatus is implemented as read-only on Nokia SROS in
                  release 14.0."

        VARIATION   igmpInterfaceGroups
            ACCESS  not-implemented
            DESCRIPTION
                 "igmpInterfaceGroups is not implemented on Nokia SROS in
                  release 14.0."

        VARIATION   igmpInterfaceJoins
            ACCESS  not-implemented
            DESCRIPTION
                 "igmpInterfaceJoins is not implemented on Nokia SROS in release
                  14.0."

        VARIATION   igmpInterfaceLastMembQueryIntvl
            ACCESS  not-implemented
            DESCRIPTION
                 "igmpInterfaceLastMembQueryIntvl is not implemented on Nokia
                  SROS in release 14.0."

        VARIATION   igmpInterfaceProxyIfIndex
            ACCESS  not-implemented
            DESCRIPTION
                 "igmpInterfaceProxyIfIndex is not implemented on Nokia SROS in
                  release 14.0."

        VARIATION   igmpInterfaceQuerier
            ACCESS  not-implemented
            DESCRIPTION
                 "igmpInterfaceQuerier is not implemented on Nokia SROS in
                  release 14.0."

        VARIATION   igmpInterfaceQuerierExpiryTime
            ACCESS  not-implemented
            DESCRIPTION
                 "igmpInterfaceQuerierExpiryTime is not implemented on Nokia
                  SROS in release 14.0."

        VARIATION   igmpInterfaceQuerierUpTime
            ACCESS  not-implemented
            DESCRIPTION
                 "igmpInterfaceQuerierUpTime is not implemented on Nokia SROS in
                  release 14.0."

        VARIATION   igmpInterfaceQueryInterval
            ACCESS  not-implemented
            DESCRIPTION
                 "igmpInterfaceQueryInterval is not implemented on Nokia SROS in
                  release 14.0."

        VARIATION   igmpInterfaceQueryMaxResponseTime
            ACCESS  not-implemented
            DESCRIPTION
                 "igmpInterfaceQueryMaxResponseTime is not implemented on Nokia
                  SROS in release 14.0."

        VARIATION   igmpInterfaceRobustness
            ACCESS  not-implemented
            DESCRIPTION
                 "igmpInterfaceRobustness is not implemented on Nokia SROS in
                  release 14.0."

        VARIATION   igmpInterfaceStatus
            ACCESS  not-implemented
            DESCRIPTION
                 "igmpInterfaceStatus is not implemented on Nokia SROS in
                  release 14.0."

        VARIATION   igmpInterfaceVersion
            ACCESS  not-implemented
            DESCRIPTION
                 "igmpInterfaceVersion is not implemented on Nokia SROS in
                  release 14.0."

        VARIATION   igmpInterfaceVersion1QuerierTimer
            ACCESS  not-implemented
            DESCRIPTION
                 "igmpInterfaceVersion1QuerierTimer is not implemented on Nokia
                  SROS in release 14.0."

        VARIATION   igmpInterfaceWrongVersionQueries
            ACCESS  not-implemented
            DESCRIPTION
                 "igmpInterfaceWrongVersionQueries is not implemented on Nokia
                  SROS in release 14.0."

    SUPPORTS        TIMETRA-IGMP-MIB
        INCLUDES {
           tmnxIgmpGlobalGroup,
           tmnxIgmpGlobalV10v0Group,
           tmnxIgmpIfV10v0Group,
           tmnxIgmpIfV11v0Group,
           tmnxIgmpIfV12v0Group,
           tmnxIgmpIfV14v0Group,
           tmnxIgmpIfV5v0Group,
           tmnxIgmpIfV6v1Group,
           tmnxIgmpIfV7v0Group,
           tmnxIgmpIfV8v0Group,
           tmnxIgmpIfV9v0Group,
           tmnxIgmpNotificationV11v0Group,
           tmnxIgmpNotificationV14v0Group
        }

        VARIATION   vRtrIgmpGrpIfMcacConstAdminState
            SYNTAX  INTEGER {
                    -- noop                 (1)
                       inService            (2),
                       outOfService         (3)
                    }
            DESCRIPTION
                 "vRtrIgmpGrpIfMcacConstAdminState supports only the values
                  'inService (2)' and 'outOfService (3)'."

        VARIATION   vRtrIgmpGrpIfRowStatus
            SYNTAX  RowStatus {
                       active               (1),
                    -- notInService         (2)
                    -- notReady             (3)
                       createAndGo          (4),
                    -- createAndWait        (5)
                       destroy              (6)
                    }
            DESCRIPTION
                 "vRtrIgmpGrpIfRowStatus supports only 'active (1)',
                  'createAndGo (4)', and 'destroy (6)'."

        VARIATION   vRtrIgmpIfMcacConstAdminState
            SYNTAX  INTEGER {
                    -- noop                 (1)
                       inService            (2),
                       outOfService         (3)
                    }
            DESCRIPTION
                 "vRtrIgmpIfMcacConstAdminState supports only the values
                  'inService (2)' and 'outOfService (3)'."

        VARIATION   vRtrIgmpIfMcacLagRowStatus
            SYNTAX  RowStatus {
                       active               (1),
                    -- notInService         (2)
                    -- notReady             (3)
                       createAndGo          (4),
                    -- createAndWait        (5)
                       destroy              (6)
                    }
            DESCRIPTION
                 "vRtrIgmpIfMcacLagRowStatus supports only 'active (1)',
                  'createAndGo (4)', and 'destroy (6)'."

        VARIATION   vRtrIgmpIfMcacLevelRowStatus
            SYNTAX  RowStatus {
                       active               (1),
                    -- notInService         (2)
                    -- notReady             (3)
                       createAndGo          (4),
                    -- createAndWait        (5)
                       destroy              (6)
                    }
            DESCRIPTION
                 "vRtrIgmpIfMcacLevelRowStatus supports only 'active (1)',
                  'createAndGo (4)', and 'destroy (6)'."

        VARIATION   vRtrIgmpIfRowStatus
            SYNTAX  RowStatus {
                       active               (1),
                    -- notInService         (2)
                    -- notReady             (3)
                       createAndGo          (4),
                    -- createAndWait        (5)
                       destroy              (6)
                    }
            DESCRIPTION
                 "vRtrIgmpIfRowStatus supports only 'active (1)', 'createAndGo
                  (4)', and 'destroy (6)'."

        VARIATION   vRtrIgmpIfSGrpRangeSrcRowStatus
            SYNTAX  RowStatus {
                       active               (1),
                    -- notInService         (2)
                    -- notReady             (3)
                       createAndGo          (4),
                    -- createAndWait        (5)
                       destroy              (6)
                    }
            DESCRIPTION
                 "vRtrIgmpIfSGrpRangeSrcRowStatus supports only 'active (1)',
                  'createAndGo (4)', and 'destroy (6)'."

        VARIATION   vRtrIgmpIfSSMTransRowStatus
            SYNTAX  RowStatus {
                       active               (1),
                    -- notInService         (2)
                    -- notReady             (3)
                       createAndGo          (4),
                    -- createAndWait        (5)
                       destroy              (6)
                    }
            DESCRIPTION
                 "vRtrIgmpIfSSMTransRowStatus supports only 'active (1)',
                  'createAndGo (4)', and 'destroy (6)'."

        VARIATION   vRtrIgmpIfStaticGrpSrcRowStatus
            SYNTAX  RowStatus {
                       active               (1),
                    -- notInService         (2)
                    -- notReady             (3)
                       createAndGo          (4),
                    -- createAndWait        (5)
                       destroy              (6)
                    }
            DESCRIPTION
                 "vRtrIgmpIfStaticGrpSrcRowStatus supports only 'active (1)',
                  'createAndGo (4)', and 'destroy (6)'."

        VARIATION   vRtrIgmpLdpIfRowStatus
            SYNTAX  RowStatus {
                       active               (1),
                    -- notInService         (2)
                    -- notReady             (3)
                       createAndGo          (4),
                    -- createAndWait        (5)
                       destroy              (6)
                    }
            DESCRIPTION
                 "vRtrIgmpLdpIfRowStatus supports only 'active (1)',
                  'createAndGo (4)', and 'destroy (6)'."

        VARIATION   vRtrIgmpRsvpIfRowStatus
            SYNTAX  RowStatus {
                       active               (1),
                    -- notInService         (2)
                    -- notReady             (3)
                       createAndGo          (4),
                    -- createAndWait        (5)
                       destroy              (6)
                    }
            DESCRIPTION
                 "vRtrIgmpRsvpIfRowStatus supports only 'active (1)',
                  'createAndGo (4)', and 'destroy (6)'."

        VARIATION   vRtrIgmpSSMTranslateRowStatus
            SYNTAX  RowStatus {
                       active               (1),
                    -- notInService         (2)
                    -- notReady             (3)
                       createAndGo          (4),
                    -- createAndWait        (5)
                       destroy              (6)
                    }
            DESCRIPTION
                 "vRtrIgmpSSMTranslateRowStatus supports only 'active (1)',
                  'createAndGo (4)', and 'destroy (6)'."

    ::= { tmnxSROSAgentV14v0  18 }

--
-- SROS IGMP_SNOOPING CAPABILITIES
--
tmnxSROSIgmpSnoopingV14v0         AGENT-CAPABILITIES
    PRODUCT-RELEASE "Nokia SROS"
    STATUS          current
    DESCRIPTION
         "Implementation of IGMP Snooping capabilities for Nokia SROS systems
          release 14.0."

    SUPPORTS        ALCATEL-IGMP-SNOOPING-MIB
        INCLUDES {
           alxEMplsIgmpSnpgNotifyV15v0Group,
           alxEMplsIgmpSnpgStatsV14v0Grp,
           alxSapIgmpSnpgConfigV11v0Group,
           alxSapIgmpSnpgConfigV12v0Group,
           alxSapIgmpSnpgConfigV14v0Group,
           alxSapIgmpSnpgConfigV5v0Group,
           alxSapIgmpSnpgConfigV8v0Group,
           alxSapIgmpSnpgGroupV3v0,
           alxSapIgmpSnpgMaxSrcsNotV11v0Grp,
           alxSapIgmpSnpgMaxSrcsNotV6v1Grp,
           alxSapIgmpSnpgMaxSrcsV6v1Group,
           alxSapIgmpSnpgNotV5v0Group,
           alxSapIgmpSnpgStaticV3v0Group,
           alxSapIgmpSnpgStatsV11v0Group,
           alxSapIgmpSnpgStatsV6v0Group,
           alxSapIgmpSnpgTimeStampGroup,
           alxSapMvrV3v0Group,
           alxSdpBindIgmpSnpgConfV14v0Group,
           alxSdpBindIgmpSnpgConfV5v0Group,
           alxSdpBindIgmpSnpgMaxSrcsV6v1Grp,
           alxSdpBindIgmpSnpgNotV11v0Group,
           alxSdpBindIgmpSnpgNotV5v0Group,
           alxSdpBindIgmpSnpgNotV6v1Group,
           alxSdpBindIgmpSnpgStatV3v0Group,
           alxSdpBindIgmpSnpgStatsV6v0Grp,
           alxSdpBindIgmpSnpgTimeStampGroup,
           alxSdpBindIgmpSnpgV3v0Group,
           alxTlsIgmpSnpgConfigV13v0Group,
           alxTlsIgmpSnpgConfigV6v0Group,
           alxTlsIgmpSnpgMRouterV3v0Group,
           alxTlsIgmpSnpgProxyV3v0Group,
           alxTlsIgmpSnpgQuerierV13v0Group,
           alxTlsIgmpSnpgQuerierV3v0Group,
           alxTlsIgmpSnpgTimeStampGroup,
           alxTlsMvrConfigV3v0Group,
           alxVxlanIgmpSnpgGroupV13v0Grp,
           alxVxlanIgmpSnpgStatsV13v0Grp
        }

        VARIATION   sapIgmpSnpgCfgMcacConstAdmSt
            SYNTAX  INTEGER {
                    -- noop                 (1)
                       inService            (2),
                       outOfService         (3)
                    }
            DESCRIPTION
                 "sapIgmpSnpgCfgMcacConstAdmSt supports only the values
                  'inService (2)' and 'outOfService (3)'."

    ::= { tmnxSROSAgentV14v0  19 }

--
-- SROS INTERFACE CAPABILITIES
--
tmnxSROSInterfaceV14v0            AGENT-CAPABILITIES
    PRODUCT-RELEASE "Nokia SROS"
    STATUS          current
    DESCRIPTION
         "Implementation of Interface capabilities for Nokia SROS systems
          release 14.0."

    SUPPORTS        IF-INVERTED-STACK-MIB
        INCLUDES {
           ifInvStackGroup
        }

    SUPPORTS        IF-MIB
        INCLUDES {
           ifCounterDiscontinuityGroup,
-- EXCLUDE ifFixedLengthGroup
           ifGeneralInformationGroup,
-- EXCLUDE ifHCFixedLengthGroup
           ifHCPacketGroup,
           ifPacketGroup,
-- EXCLUDE ifRcvAddressGroup
           ifStackGroup2,
           ifVHCPacketGroup,
           linkUpDownNotificationsGroup
        }

        VARIATION   ifAdminStatus
            SYNTAX  INTEGER {
                       up                   (1),
                       down                 (2)
                    -- testing              (3)
                    }
            DESCRIPTION
                 "Write access using value 'testing (3)' is not supported."

        VARIATION   ifAlias
            SYNTAX  DisplayString (SIZE(0..160))
            ACCESS  read-only
            DESCRIPTION
                 "ifAlias is supported as read-only. The maximum size string
                  returned has been increased from 64 to 160 characters. The
                  string returned for ifAlias is the user configured port or
                  interface description."

        VARIATION   ifLinkUpDownTrapEnable
            ACCESS  read-only
            DESCRIPTION
                 "ifLinkUpDownTrapEnable is implemented as read-only on Nokia
                  SROS in release 14.0."

        VARIATION   ifPromiscuousMode
            ACCESS  read-only
            DESCRIPTION
                 "ifPromiscuousMode is implemented as read-only on Nokia SROS in
                  release 14.0."

        VARIATION   ifStackStatus
            ACCESS  read-only
            DESCRIPTION
                 "ifStackStatus is implemented as read-only on Nokia SROS in
                  release 14.0."

        VARIATION   linkDown
            DESCRIPTION
                 "The linkDown notification has ifDescr appended to the variable
                  list."

        VARIATION   linkUp
            DESCRIPTION
                 "The linkUp notification has ifDescr appended to the variable
                  list."

    ::= { tmnxSROSAgentV14v0  16 }

--
-- SROS IP CAPABILITIES
--
tmnxSROSIpV14v0                   AGENT-CAPABILITIES
    PRODUCT-RELEASE "Nokia SROS"
    STATUS          current
    DESCRIPTION
         "Implementation of Internet Protocol, IP, capabilities for Nokia SROS
          systems release 14.0."

    SUPPORTS        IP-FORWARD-MIB
        INCLUDES {
           inetForwardCidrRouteGroup,
           ipForwardCidrRouteGroup
        }

        VARIATION   inetCidrRouteIfIndex
            ACCESS  read-only
            DESCRIPTION
                 "inetCidrRouteIfIndex is implemented as read-only on Nokia SROS
                  in release 14.0."

        VARIATION   inetCidrRouteMetric1
            ACCESS  read-only
            DESCRIPTION
                 "inetCidrRouteMetric1 is implemented as read-only on Nokia SROS
                  in release 14.0."

        VARIATION   inetCidrRouteMetric2
            ACCESS  read-only
            DESCRIPTION
                 "inetCidrRouteMetric2 is implemented as read-only on Nokia SROS
                  in release 14.0."

        VARIATION   inetCidrRouteMetric3
            ACCESS  read-only
            DESCRIPTION
                 "inetCidrRouteMetric3 is implemented as read-only on Nokia SROS
                  in release 14.0."

        VARIATION   inetCidrRouteMetric4
            ACCESS  read-only
            DESCRIPTION
                 "inetCidrRouteMetric4 is implemented as read-only on Nokia SROS
                  in release 14.0."

        VARIATION   inetCidrRouteMetric5
            ACCESS  read-only
            DESCRIPTION
                 "inetCidrRouteMetric5 is implemented as read-only on Nokia SROS
                  in release 14.0."

        VARIATION   inetCidrRouteNextHopAS
            ACCESS  read-only
            DESCRIPTION
                 "inetCidrRouteNextHopAS is implemented as read-only on Nokia
                  SROS in release 14.0."

        VARIATION   inetCidrRouteProto
            DESCRIPTION
                 "inetCidrRouteProto supports the values: - 'periodic (247)', -
                  'vpnLeak (249)', - 'ldp (250)', - 'managed (251)', - 'host
                  (252)', - 'ospf3 (253)', - 'bgpVpn (254)', - 'subMgmt (255)',
                  - 'tms (256)', - 'nat (257)', - 'ipsec (258)', - 'dhcpv6Pd
                  (260)', - 'dhcpv6Na (261)', - 'dhcpv6Ta (262)', -
                  'dhcpv6PdExcl (263)', - 'aggregate (264)' - 'ripNg (265)' -
                  'bgpEvpn (266)' - 'bgpLabel (267)' in addition to the
                  enumerations in the IANAipRouteProtocol TC."

        VARIATION   inetCidrRouteStatus
            SYNTAX  INTEGER {
                       active               (1)
                    }
            ACCESS  read-only
            DESCRIPTION
                 "inetCidrRouteTable is implemented as read-only.

                  The indexes inetCidrRouteDestType and
                  inetCidrRouteNextHopType support the values of 'ipv4Mcast
                  (128)' and 'ipv6Mcast (129)' in addition to those defined by
                  the InetAddressType textual convention. 'ipv4Mcast (128)' and
                  'ipv6Mcast (129)' are implemented for 'ipv4'/'ipv6' addresses
                  for multicast extensions."

        VARIATION   inetCidrRouteType
            ACCESS  read-only
            DESCRIPTION
                 "inetCidrRouteType is implemented as read-only on Nokia SROS in
                  release 14.0."

        VARIATION   ipCidrRouteIfIndex
            ACCESS  read-only
            DESCRIPTION
                 "ipCidrRouteIfIndex is implemented as read-only on Nokia SROS
                  in release 14.0."

        VARIATION   ipCidrRouteInfo
            ACCESS  read-only
            DESCRIPTION
                 "ipCidrRouteInfo is implemented as read-only on Nokia SROS in
                  release 14.0."

        VARIATION   ipCidrRouteMetric1
            ACCESS  read-only
            DESCRIPTION
                 "ipCidrRouteMetric1 is implemented as read-only on Nokia SROS
                  in release 14.0."

        VARIATION   ipCidrRouteMetric2
            ACCESS  read-only
            DESCRIPTION
                 "ipCidrRouteMetric2 is implemented as read-only on Nokia SROS
                  in release 14.0."

        VARIATION   ipCidrRouteMetric3
            ACCESS  read-only
            DESCRIPTION
                 "ipCidrRouteMetric3 is implemented as read-only on Nokia SROS
                  in release 14.0."

        VARIATION   ipCidrRouteMetric4
            ACCESS  read-only
            DESCRIPTION
                 "ipCidrRouteMetric4 is implemented as read-only on Nokia SROS
                  in release 14.0."

        VARIATION   ipCidrRouteMetric5
            ACCESS  read-only
            DESCRIPTION
                 "ipCidrRouteMetric5 is implemented as read-only on Nokia SROS
                  in release 14.0."

        VARIATION   ipCidrRouteNextHopAS
            ACCESS  read-only
            DESCRIPTION
                 "ipCidrRouteNextHopAS is implemented as read-only on Nokia SROS
                  in release 14.0."

        VARIATION   ipCidrRouteProto
            DESCRIPTION
                 "ipCidrRouteProto supports the value 'bgpVpn (254)' in addition
                  to the list of enumerations to support rfc2547 VPRNs on Nokia
                  SROS."

        VARIATION   ipCidrRouteStatus
            ACCESS  read-only
            DESCRIPTION
                 "ipCidrRouteStatus is implemented as read-only on Nokia SROS in
                  release 14.0."

        VARIATION   ipCidrRouteType
            ACCESS  read-only
            DESCRIPTION
                 "ipCidrRouteType is implemented as read-only on Nokia SROS in
                  release 14.0."

    SUPPORTS        IP-MIB
        INCLUDES {
           icmpGroup,
           icmpStatsGroup,
           ipAddressGroup,
           ipAddressPrefixGroup,
           ipDefaultRouterGroup,
           ipGroup,
           ipLastChangeGroup,
           ipNetToPhysicalGroup,
           ipSystemStatsGroup,
           ipv4IfGroup,
           ipv6GeneralGroup2,
           ipv6IfGroup,
           ipv6RouterAdvertGroup,
           ipv6ScopeGroup
        }

        VARIATION   ipAddressCreated
            ACCESS  read-only
            DESCRIPTION
                 "ipAddressCreated is implemented as read-only on Nokia SROS in
                  release 14.0."

        VARIATION   ipAddressIfIndex
            ACCESS  read-only
            DESCRIPTION
                 "ipAddressIfIndex is implemented as read-only on Nokia SROS in
                  release 14.0."

        VARIATION   ipAddressOrigin
            ACCESS  read-only
            DESCRIPTION
                 "ipAddressOrigin is implemented as read-only on Nokia SROS in
                  release 14.0."

        VARIATION   ipAddressPrefix
            ACCESS  read-only
            DESCRIPTION
                 "ipAddressPrefix is implemented as read-only on Nokia SROS in
                  release 14.0."

        VARIATION   ipAddressRowStatus
            ACCESS  read-only
            DESCRIPTION
                 "ipAddressRowStatus is implemented as read-only on Nokia SROS
                  in release 14.0."

        VARIATION   ipAddressSpinLock
            ACCESS  read-only
            DESCRIPTION
                 "ipAddressSpinLock is implemented as read-only on Nokia SROS in
                  release 14.0."

        VARIATION   ipAddressStatus
            ACCESS  read-only
            DESCRIPTION
                 "ipAddressStatus is implemented as read-only on Nokia SROS in
                  release 14.0."

        VARIATION   ipAddressStorageType
            ACCESS  read-only
            DESCRIPTION
                 "ipAddressStorageType is implemented as read-only on Nokia SROS
                  in release 14.0."

        VARIATION   ipAddressType
            ACCESS  read-only
            DESCRIPTION
                 "ipAddressType is implemented as read-only on Nokia SROS in
                  release 14.0."

        VARIATION   ipDefaultRouterLifetime
            ACCESS  not-implemented
            DESCRIPTION
                 "ipDefaultRouterLifetime is not implemented because it is meant
                  for hosts."

        VARIATION   ipDefaultRouterPreference
            ACCESS  not-implemented
            DESCRIPTION
                 "ipDefaultRouterPreference is not implemented because it is
                  meant for hosts."

        VARIATION   ipDefaultTTL
            ACCESS  read-only
            DESCRIPTION
                 "ipDefaultTTL is implemented as read-only. It always returns
                  the value '64'."

        VARIATION   ipForwarding
            ACCESS  read-only
            DESCRIPTION
                 "ipForwarding is implemented as read-only. It always returns
                  the value 'forwarding (1)'."

        VARIATION   ipNetToMediaType
            SYNTAX  INTEGER {
                       other                (1),
                       invalid              (2),
                       dynamic              (3),
                       static               (4),
                       managed              (5)
                    }
            DESCRIPTION
                 "The value 'managed (5)' is used to indicate that the ARP entry
                  has been added by: - a static host - a DHCP lease state if
                  TIMETRA-VRTR-MIB::vRtrIfArpPopulate is set to enabled.

                  An attempt to set ipNetToMediaType to the value 'managed'
                  results in an 'inconsistentValue' error."

        VARIATION   ipNetToPhysicalNetAddressType
            SYNTAX  InetAddressType {
                    -- unknown              (0)
                       ipv4                 (1),
                       ipv6                 (2)
                    -- ipv4z                (3)
                    -- ipv6z                (4)
                    -- dns                  (16)
                    }
            DESCRIPTION
                 "ipNetToPhysicalNetAddressType supports only the
                  InetAddressType values 'ipv4 (1)', and 'ipv6 (2)'."

        VARIATION   ipNetToPhysicalType
            SYNTAX  INTEGER {
                       other                (1),
                       invalid              (2),
                       dynamic              (3),
                       static               (4),
                       local                (5),
                       managed              (100),
                       evpn                 (101)
                    }
            DESCRIPTION
                 "The value 'managed (100)' is used to indicate that the ARP
                  entry has been added by:

                  - a static host; or - by a DHCP lease state if
                  TIMETRA-VRTR-MIB::vRtrIfArpPopulate is set to enabled.

                  An attempt to explicitly set the value of ipNetToPhysicalType
                  to 'managed' results in an 'inconsistentValue' error."

        VARIATION   ipv4InterfaceEnableStatus
            ACCESS  read-only
            DESCRIPTION
                 "ipv4InterfaceEnableStatus is implemented as read-only on Nokia
                  SROS in release 14.0."

        VARIATION   ipv6InterfaceEnableStatus
            ACCESS  read-only
            DESCRIPTION
                 "ipv6InterfaceEnableStatus is implemented as read-only on Nokia
                  SROS in release 14.0."

        VARIATION   ipv6InterfaceForwarding
            ACCESS  read-only
            DESCRIPTION
                 "ipv6InterfaceForwarding is implemented as read-only on Nokia
                  SROS in release 14.0."

        VARIATION   ipv6IpDefaultHopLimit
            ACCESS  read-only
            DESCRIPTION
                 "ipv6IpDefaultHopLimit is implemented as read-only on Nokia
                  SROS in release 14.0."

        VARIATION   ipv6IpForwarding
            ACCESS  read-only
            DESCRIPTION
                 "ipv6IpForwarding is implemented as read-only on Nokia SROS in
                  release 14.0."

        VARIATION   ipv6RouterAdvertSpinLock
            ACCESS  read-only
            DESCRIPTION
                 "ipv6RouterAdvertSpinLock is implemented as read-only on Nokia
                  SROS in release 14.0."

        VARIATION   ipv6ScopeZoneIndex3
            ACCESS  not-implemented
            DESCRIPTION
                 "ipv6ScopeZoneIndex3 is not implemented on Nokia SROS in
                  release 14.0."

        VARIATION   ipv6ScopeZoneIndex6
            ACCESS  not-implemented
            DESCRIPTION
                 "ipv6ScopeZoneIndex6 is not implemented on Nokia SROS in
                  release 14.0."

        VARIATION   ipv6ScopeZoneIndex7
            ACCESS  not-implemented
            DESCRIPTION
                 "ipv6ScopeZoneIndex7 is not implemented on Nokia SROS in
                  release 14.0."

        VARIATION   ipv6ScopeZoneIndex9
            ACCESS  not-implemented
            DESCRIPTION
                 "ipv6ScopeZoneIndex9 is not implemented on Nokia SROS in
                  release 14.0."

        VARIATION   ipv6ScopeZoneIndexA
            ACCESS  not-implemented
            DESCRIPTION
                 "ipv6ScopeZoneIndexA is not implemented on Nokia SROS in
                  release 14.0."

        VARIATION   ipv6ScopeZoneIndexAdminLocal
            ACCESS  not-implemented
            DESCRIPTION
                 "ipv6ScopeZoneIndexAdminLocal is not implemented on Nokia SROS
                  in release 14.0."

        VARIATION   ipv6ScopeZoneIndexB
            ACCESS  not-implemented
            DESCRIPTION
                 "ipv6ScopeZoneIndexB is not implemented on Nokia SROS in
                  release 14.0."

        VARIATION   ipv6ScopeZoneIndexC
            ACCESS  not-implemented
            DESCRIPTION
                 "ipv6ScopeZoneIndexC is not implemented on Nokia SROS in
                  release 14.0."

        VARIATION   ipv6ScopeZoneIndexD
            ACCESS  not-implemented
            DESCRIPTION
                 "ipv6ScopeZoneIndexD is not implemented on Nokia SROS in
                  release 14.0."

        VARIATION   ipv6ScopeZoneIndexLinkLocal
            ACCESS  not-implemented
            DESCRIPTION
                 "ipv6ScopeZoneIndexLinkLocal is not implemented on Nokia SROS
                  in release 14.0."

        VARIATION   ipv6ScopeZoneIndexOrganizationLocal
            ACCESS  not-implemented
            DESCRIPTION
                 "ipv6ScopeZoneIndexOrganizationLocal is not implemented on
                  Nokia SROS in release 14.0."

        VARIATION   ipv6ScopeZoneIndexSiteLocal
            ACCESS  not-implemented
            DESCRIPTION
                 "ipv6ScopeZoneIndexSiteLocal is not implemented on Nokia SROS
                  in release 14.0."

    SUPPORTS        TCP-MIB
        INCLUDES {
           tcpConnectionGroup,
           tcpGroup,
-- EXCLUDE tcpHCGroup
           tcpListenerGroup
        }

        VARIATION   tcpConnectionState
            ACCESS  read-only
            DESCRIPTION
                 "tcpConnectionState is implemented as read-only on Nokia SROS
                  in release 14.0."

    SUPPORTS        UDP-MIB
        INCLUDES {
           udpEndpointGroup,
           udpGroup
-- EXCLUDE udpHCGroup
        }

    ::= { tmnxSROSAgentV14v0  20 }

--
-- SROS IPFIX CAPABILITIES
--
tmnxSROSIpfixV14v0                AGENT-CAPABILITIES
    PRODUCT-RELEASE "Nokia SROS"
    STATUS          current
    DESCRIPTION
         "Implementation of the IP Flow Information Export (IPFIX) Protocol for
          the Exchange of IP Traffic Flow Information feature on Nokia SROS
          systems release 14.0."

    SUPPORTS        TIMETRA-IPFIX-MIB
        INCLUDES {
           tmnxIpfixExportGroup
        }

        VARIATION   tmnxIpfixExpPlcyColAdminState
            SYNTAX  INTEGER {
                    -- noop                 (1)
                       inService            (2),
                       outOfService         (3)
                    }
            DESCRIPTION
                 "tmnxIpfixExpPlcyColAdminState supports only the values
                  'inService (2)' and 'outOfService (3)'."

        VARIATION   tmnxIpfixExpPlcyColRowStatus
            SYNTAX  RowStatus {
                       active               (1),
                    -- notInService         (2)
                    -- notReady             (3)
                       createAndGo          (4),
                    -- createAndWait        (5)
                       destroy              (6)
                    }
            DESCRIPTION
                 "tmnxIpfixExpPlcyColRowStatus supports only 'active (1)',
                  'createAndGo (4)', and 'destroy (6)'."

        VARIATION   tmnxIpfixExpPlcyRowStatus
            SYNTAX  RowStatus {
                       active               (1),
                    -- notInService         (2)
                    -- notReady             (3)
                       createAndGo          (4),
                    -- createAndWait        (5)
                       destroy              (6)
                    }
            DESCRIPTION
                 "tmnxIpfixExpPlcyRowStatus supports only 'active (1)',
                  'createAndGo (4)', and 'destroy (6)'."

    ::= { tmnxSROSAgentV14v0  80 }

--
-- 7750 IP_SEC CAPABILITIES
--
tmnx7750IpSecV14v0                AGENT-CAPABILITIES
    PRODUCT-RELEASE "Nokia SROS"
    STATUS          current
    DESCRIPTION
         "Implementation of IPsec tunneling, encryption and other related
          features capabilities for Nokia 7750 systems release 14.0."

    SUPPORTS        TIMETRA-IPSEC-MIB
        INCLUDES {
           tIPSecTrustAnchorProfNotifGroup,
           tIPSecTunnelEncapNotifGroup,
           tIPsecClientDatabaseV14v0Group,
           tIPsecIkev2CertAuthChainGroup,
           tIPsecIkev2CertAuthGroup,
           tIPsecIkev2RaTunNotifGroup,
           tIPsecIkev2RaTunNotifyObjsGroup,
           tIPsecRUSATrafficSelGroup,
           tIPsecRUTnlDhcpLeaseStatV14v0Grp,
           tIPsecTnlTempGroup,
           tIPsecTrafficSelectorV14v0Group,
           tIPsecTsReductionGroup,
           tIkev2SendUnSolCfgAttr12v0Group,
           tmnxIPSecGWNotifV13v0Group,
           tmnxIPSecTunnelNotifV11v0Group,
           tmnxIPsecCertGroup,
           tmnxIPsecEncapNotifyObjsGroup,
           tmnxIPsecGWDhcpGroup,
           tmnxIPsecGWDhcpV6Group,
           tmnxIPsecGWLAAIpPool2V14v0Group,
           tmnxIPsecGWLclAddrGroup,
           tmnxIPsecGWPrivIp2V13v0Group,
           tmnxIPsecGWV12v0Group,
           tmnxIPsecIkeGroup,
           tmnxIPsecIkePolicyV14v0Group,
           tmnxIPsecIkev2IdiGroup,
           tmnxIPsecIkev2RatGroup,
           tmnxIPsecMdaDpGroup,
           tmnxIPsecMdaDpStatsV10v0Group,
           tmnxIPsecMdaDpStatsV14v0Group,
           tmnxIPsecMdaDpStatsV6v1Group,
           tmnxIPsecNotifGroup,
           tmnxIPsecNotifyObjsGroup,
           tmnxIPsecRUSAStatsV12v0Group,
           tmnxIPsecRUTnlInUseCfgsV14v0Grp,
           tmnxIPsecRadInterimUpdGroup,
           tmnxIPsecSAStatsV12v0Group,
           tmnxIPsecTnlBfdGroup,
           tmnxIPsecTnlDstv12v0Group,
           tmnxIPsecTnlOperChgGroup,
           tmnxIPsecV10v0Group,
           tmnxIPsecV11v0Group,
           tmnxIPsecV12v0Group,
           tmnxIPsecV6v0Group,
           tmnxIkePolicyAutoEapGroup,
           tmnxIkePolicyAutoEapRadiusGroup,
           tmnxIkePolicyLockoutV14v0Group,
           tmnxIkePolicyV2FragV14v0Group,
           tmnxSecurityNotificationV13v0Grp
        }

        VARIATION   tIPsecClientDBClientIdPeerPfxTyp
            SYNTAX  InetAddressType {
                       unknown              (0),
                       ipv4                 (1),
                       ipv6                 (2)
                    -- ipv4z                (3)
                    -- ipv6z                (4)
                    -- dns                  (16)
                    }
            DESCRIPTION
                 "tIPsecClientDBClientIdPeerPfxTyp supports only the
                  InetAddressType values 'unknown (0)', 'ipv4 (1)', and 'ipv6
                  (2)'."

        VARIATION   tIPsecClientDBClientRowStatus
            SYNTAX  RowStatus {
                       active               (1),
                    -- notInService         (2)
                    -- notReady             (3)
                       createAndGo          (4),
                    -- createAndWait        (5)
                       destroy              (6)
                    }
            DESCRIPTION
                 "tIPsecClientDBClientRowStatus supports only 'active (1)',
                  'createAndGo (4)', and 'destroy (6)'."

        VARIATION   tIPsecClientDatabaseRowStatus
            SYNTAX  RowStatus {
                       active               (1),
                    -- notInService         (2)
                    -- notReady             (3)
                       createAndGo          (4),
                    -- createAndWait        (5)
                       destroy              (6)
                    }
            DESCRIPTION
                 "tIPsecClientDatabaseRowStatus supports only 'active (1)',
                  'createAndGo (4)', and 'destroy (6)'."

        VARIATION   tIPsecRUTnlPrivateIpAddr2Type
            SYNTAX  InetAddressType {
                       unknown              (0),
                       ipv4                 (1),
                       ipv6                 (2)
                    -- ipv4z                (3)
                    -- ipv6z                (4)
                    -- dns                  (16)
                    }
            DESCRIPTION
                 "tIPsecRUTnlPrivateIpAddr2Type supports only the
                  InetAddressType values 'unknown (0)', 'ipv4 (1)', and 'ipv6
                  (2)'."

        VARIATION   tIPsecTnlTempReverseRoute
            SYNTAX  INTEGER {
                       none                 (0),
                    -- reverseRoute         (1)
                       useSecurityPolicy    (2)
                    }
            DESCRIPTION
                 "tIPsecTnlTempReverseRoute supports only 'none(0)' and
                  'useSecurityPolicy (2)'."

        VARIATION   tIPsecTsListRmtEntryMaxAddrType
            SYNTAX  InetAddressType {
                       unknown              (0),
                       ipv4                 (1),
                       ipv6                 (2)
                    -- ipv4z                (3)
                    -- ipv6z                (4)
                    -- dns                  (16)
                    }
            DESCRIPTION
                 "tIPsecTsListRmtEntryMaxAddrType supports only the
                  InetAddressType values 'unknown (0)', 'ipv4 (1)', and 'ipv6
                  (2)'."

        VARIATION   tIPsecTsListRmtEntryMinAddrType
            SYNTAX  InetAddressType {
                       unknown              (0),
                       ipv4                 (1),
                       ipv6                 (2)
                    -- ipv4z                (3)
                    -- ipv6z                (4)
                    -- dns                  (16)
                    }
            DESCRIPTION
                 "tIPsecTsListRmtEntryMinAddrType supports only the
                  InetAddressType values 'unknown (0)', 'ipv4 (1)', and 'ipv6
                  (2)'."

        VARIATION   tIPsecTsListRmtEntryRowStatus
            SYNTAX  RowStatus {
                       active               (1),
                    -- notInService         (2)
                    -- notReady             (3)
                       createAndGo          (4),
                    -- createAndWait        (5)
                       destroy              (6)
                    }
            DESCRIPTION
                 "tIPsecTsListRmtEntryRowStatus supports only 'active (1)',
                  'createAndGo (4)', and 'destroy (6)'."

        VARIATION   tIPsecTsListRowStatus
            SYNTAX  RowStatus {
                       active               (1),
                    -- notInService         (2)
                    -- notReady             (3)
                       createAndGo          (4),
                    -- createAndWait        (5)
                       destroy              (6)
                    }
            DESCRIPTION
                 "tIPsecTsListRowStatus supports only 'active (1)', 'createAndGo
                  (4)', and 'destroy (6)'."

        VARIATION   tmnxIPsecGWDhcpV6LinkAddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6LinkAddrType supports only the
                  InetAddressType values 'unknown (0)' and 'ipv6 (2)'."

        VARIATION   tmnxIPsecGWDhcpV6Srvr1AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr1AddrType supports only the
                  InetAddressType values 'unknown (0)' and 'ipv6 (2)'."

        VARIATION   tmnxIPsecGWDhcpV6Srvr2AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr2AddrType supports only the
                  InetAddressType values 'unknown (0)' and 'ipv6 (2)'."

        VARIATION   tmnxIPsecGWDhcpV6Srvr3AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr3AddrType supports only the
                  InetAddressType values 'unknown (0)' and 'ipv6 (2)'."

        VARIATION   tmnxIPsecGWDhcpV6Srvr4AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr4AddrType supports only the
                  InetAddressType values 'unknown (0)' and 'ipv6 (2)'."

        VARIATION   tmnxIPsecGWDhcpV6Srvr5AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr5AddrType supports only the
                  InetAddressType values 'unknown (0)' and 'ipv6 (2)'."

        VARIATION   tmnxIPsecGWDhcpV6Srvr6AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr6AddrType supports only the
                  InetAddressType values 'unknown (0)' and 'ipv6 (2)'."

        VARIATION   tmnxIPsecGWDhcpV6Srvr7AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr7AddrType supports only the
                  InetAddressType values 'unknown (0)' and 'ipv6 (2)'."

        VARIATION   tmnxIPsecGWDhcpV6Srvr8AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr8AddrType supports only the
                  InetAddressType values 'unknown (0)' and 'ipv6 (2)'."

        VARIATION   tmnxIPsecPlcyParamsV6LclAddrType
            SYNTAX  InetAddressType {
                       unknown              (0),
                    -- ipv4                 (1)
                       ipv6                 (2)
                    -- ipv4z                (3)
                    -- ipv6z                (4)
                    -- dns                  (16)
                    }
            DESCRIPTION
                 "tmnxIPsecPlcyParamsV6LclAddrType supports only the
                  InetAddressType values 'unknown (0)' and 'ipv6 (2)'."

        VARIATION   tmnxIPsecPlcyParamsV6RemAddrType
            SYNTAX  InetAddressType {
                       unknown              (0),
                    -- ipv4                 (1)
                       ipv6                 (2)
                    -- ipv4z                (3)
                    -- ipv6z                (4)
                    -- dns                  (16)
                    }
            DESCRIPTION
                 "tmnxIPsecPlcyParamsV6RemAddrType supports only the
                  InetAddressType values 'unknown (0)' and 'ipv6 (2)'."

        VARIATION   tmnxIPsecPolicyParamsLclAPrefLen
            SYNTAX  Unsigned32 (0..32)
            DESCRIPTION
                 "tmnxIPsecPolicyParamsLclAPrefLen supports values between 0 and
                  32 and setting to any other value results in an
                  'inconsistentValue' error."

        VARIATION   tmnxIPsecPolicyParamsLclAddr
            SYNTAX  InetAddress (SIZE (0|4))
            DESCRIPTION
                 "tmnxIPsecPolicyParamsLclAddr supports only InetAddressType
                  values 'unknown (0)' and 'ipv4 (1)'."

        VARIATION   tmnxIPsecPolicyParamsLclAddrType
            SYNTAX  InetAddressType {
                       unknown              (0),
                       ipv4                 (1)
                    -- ipv6                 (2)
                    -- ipv4z                (3)
                    -- ipv6z                (4)
                    -- dns                  (16)
                    }
            DESCRIPTION
                 "tmnxIPsecPolicyParamsLclAddrType supports only the
                  InetAddressType values 'unknown (0)' and 'ipv4 (1)'."

        VARIATION   tmnxIPsecPolicyParamsRemAPrefLen
            SYNTAX  Unsigned32 (0..32)
            DESCRIPTION
                 "tmnxIPsecPolicyParamsRemAPrefLen supports values between 0 and
                  32 and setting to any other value results in an
                  'inconsistentValue' error."

        VARIATION   tmnxIPsecPolicyParamsRemAddr
            SYNTAX  InetAddress (SIZE (0|4))
            DESCRIPTION
                 "tmnxIPsecPolicyParamsRemAddr supports only InetAddressType
                  values 'unknown (0)' and 'ipv4 (1)'."

        VARIATION   tmnxIPsecPolicyParamsRemAddrType
            SYNTAX  InetAddressType {
                       unknown              (0),
                       ipv4                 (1)
                    -- ipv6                 (2)
                    -- ipv4z                (3)
                    -- ipv6z                (4)
                    -- dns                  (16)
                    }
            DESCRIPTION
                 "tmnxIPsecPolicyParamsRemAddrType supports only the
                  InetAddressType values 'unknown (0)' and 'ipv4 (1)'."

        VARIATION   tmnxIPsecPolicyParamsRowStatus
            SYNTAX  RowStatus {
                       active               (1),
                    -- notInService         (2)
                    -- notReady             (3)
                       createAndGo          (4),
                    -- createAndWait        (5)
                       destroy              (6)
                    }
            DESCRIPTION
                 "tmnxIPsecPolicyParamsRowStatus supports only 'active (1)',
                  'createAndGo (4)', and 'destroy (6)'."

        VARIATION   tmnxIPsecPolicyRowStatus
            SYNTAX  RowStatus {
                       active               (1),
                    -- notInService         (2)
                    -- notReady             (3)
                       createAndGo          (4),
                    -- createAndWait        (5)
                       destroy              (6)
                    }
            DESCRIPTION
                 "tmnxIPsecPolicyRowStatus supports only 'active (1)',
                  'createAndGo (4)', and 'destroy (6)'."

        VARIATION   tmnxIPsecTransformRowStatus
            SYNTAX  RowStatus {
                       active               (1),
                    -- notInService         (2)
                    -- notReady             (3)
                       createAndGo          (4),
                    -- createAndWait        (5)
                       destroy              (6)
                    }
            DESCRIPTION
                 "tmnxIPsecTransformRowStatus supports only 'active (1)',
                  'createAndGo (4)', and 'destroy (6)'."

        VARIATION   tmnxIPsecTunnelAdminState
            SYNTAX  INTEGER {
                    -- noop                 (1)
                       inService            (2),
                       outOfService         (3)
                    }
            DESCRIPTION
                 "tmnxIPsecTunnelAdminState supports only the values 'inService
                  (2)' and 'outOfService (3)'."

        VARIATION   tmnxIPsecTunnelRowStatus
            SYNTAX  RowStatus {
                       active               (1),
                    -- notInService         (2)
                    -- notReady             (3)
                       createAndGo          (4),
                    -- createAndWait        (5)
                       destroy              (6)
                    }
            DESCRIPTION
                 "tmnxIPsecTunnelRowStatus supports only 'active (1)',
                  'createAndGo (4)', and 'destroy (6)'."

        VARIATION   tmnxIkePolicyAuthAlgorithm
            SYNTAX  INTEGER {
                       md5                  (2),
                       sha1                 (3)
                    }
            DESCRIPTION
                 "tmnxIkePolicyAuthAlgorithm supports only the values 'md5 (1)'
                  and 'sha1 (3)'."

        VARIATION   tmnxIkePolicyAuthMethod
            SYNTAX  INTEGER {
                       psk                  (1),
                       plainPskXAuth        (4)
                    }
            DESCRIPTION
                 "tmnxIkePolicyAuthMethod supports only 'psk (1)' and
                  'plainPskXAuth (4)'."

        VARIATION   tmnxIkePolicyEncrAlgorithm
            SYNTAX  INTEGER {
                       des                  (2),
                       des3                 (3),
                       aes128               (4),
                       aes192               (5),
                       aes256               (6)
                    }
            DESCRIPTION
                 "tmnxIkePolicyEncrAlgorithm supports only the values 'des (2)',
                  'des3 (3)', 'aes128 (4)', 'aes192 (5)' and 'aes256 (6)'."

        VARIATION   tmnxIkePolicyRowStatus
            SYNTAX  RowStatus {
                       active               (1),
                    -- notInService         (2)
                    -- notReady             (3)
                       createAndGo          (4),
                    -- createAndWait        (5)
                       destroy              (6)
                    }
            DESCRIPTION
                 "tmnxIkePolicyRowStatus supports only 'active (1)',
                  'createAndGo (4)', and 'destroy (6)'."

    ::= { tmnx7750AgentV14v0  56 }

--
-- 7950 IP_SEC CAPABILITIES
--
tmnx7950IpSecV14v0                AGENT-CAPABILITIES
    PRODUCT-RELEASE "Nokia SROS"
    STATUS          current
    DESCRIPTION
         "Implementation of IPsec tunneling, encryption and other related
          features capabilities for Nokia 7950 systems release 14.0."

    SUPPORTS        TIMETRA-IPSEC-MIB
        INCLUDES {
           tIPSecTrustAnchorProfNotifGroup,
           tIPSecTunnelEncapNotifGroup,
           tIPsecClientDatabaseV14v0Group,
           tIPsecIkev2CertAuthChainGroup,
           tIPsecIkev2CertAuthGroup,
           tIPsecIkev2RaTunNotifGroup,
           tIPsecIkev2RaTunNotifyObjsGroup,
           tIPsecRUSATrafficSelGroup,
           tIPsecRUTnlDhcpLeaseStatV14v0Grp,
           tIPsecTnlTempGroup,
           tIPsecTrafficSelectorV14v0Group,
           tIPsecTsReductionGroup,
           tIkev2SendUnSolCfgAttr12v0Group,
           tmnxIPSecGWNotifV13v0Group,
           tmnxIPSecTunnelNotifV11v0Group,
           tmnxIPsecCertGroup,
           tmnxIPsecEncapNotifyObjsGroup,
           tmnxIPsecGWDhcpGroup,
           tmnxIPsecGWDhcpV6Group,
           tmnxIPsecGWLAAIpPool2V14v0Group,
           tmnxIPsecGWLclAddrGroup,
           tmnxIPsecGWPrivIp2V13v0Group,
           tmnxIPsecGWV12v0Group,
           tmnxIPsecIkeGroup,
           tmnxIPsecIkePolicyV14v0Group,
           tmnxIPsecIkev2IdiGroup,
           tmnxIPsecIkev2RatGroup,
           tmnxIPsecMdaDpGroup,
           tmnxIPsecMdaDpStatsV10v0Group,
           tmnxIPsecMdaDpStatsV14v0Group,
           tmnxIPsecMdaDpStatsV6v1Group,
           tmnxIPsecNotifGroup,
           tmnxIPsecNotifyObjsGroup,
           tmnxIPsecRUSAStatsV12v0Group,
           tmnxIPsecRUTnlInUseCfgsV14v0Grp,
           tmnxIPsecRadInterimUpdGroup,
           tmnxIPsecSAStatsV12v0Group,
           tmnxIPsecTnlBfdGroup,
           tmnxIPsecTnlDstv12v0Group,
           tmnxIPsecTnlOperChgGroup,
           tmnxIPsecV10v0Group,
           tmnxIPsecV11v0Group,
           tmnxIPsecV12v0Group,
           tmnxIPsecV6v0Group,
           tmnxIkePolicyAutoEapGroup,
           tmnxIkePolicyAutoEapRadiusGroup,
           tmnxIkePolicyLockoutV14v0Group,
           tmnxIkePolicyV2FragV14v0Group,
           tmnxSecurityNotificationV13v0Grp
        }

        VARIATION   tIPsecClientDBClientIdPeerPfxTyp
            SYNTAX  InetAddressType {
                       unknown              (0),
                       ipv4                 (1),
                       ipv6                 (2)
                    -- ipv4z                (3)
                    -- ipv6z                (4)
                    -- dns                  (16)
                    }
            DESCRIPTION
                 "tIPsecClientDBClientIdPeerPfxTyp supports only the
                  InetAddressType values 'unknown (0)', 'ipv4 (1)', and 'ipv6
                  (2)'."

        VARIATION   tIPsecClientDBClientRowStatus
            SYNTAX  RowStatus {
                       active               (1),
                    -- notInService         (2)
                    -- notReady             (3)
                       createAndGo          (4),
                    -- createAndWait        (5)
                       destroy              (6)
                    }
            DESCRIPTION
                 "tIPsecClientDBClientRowStatus supports only 'active (1)',
                  'createAndGo (4)', and 'destroy (6)'."

        VARIATION   tIPsecClientDatabaseRowStatus
            SYNTAX  RowStatus {
                       active               (1),
                    -- notInService         (2)
                    -- notReady             (3)
                       createAndGo          (4),
                    -- createAndWait        (5)
                       destroy              (6)
                    }
            DESCRIPTION
                 "tIPsecClientDatabaseRowStatus supports only 'active (1)',
                  'createAndGo (4)', and 'destroy (6)'."

        VARIATION   tIPsecRUTnlPrivateIpAddr2Type
            SYNTAX  InetAddressType {
                       unknown              (0),
                       ipv4                 (1),
                       ipv6                 (2)
                    -- ipv4z                (3)
                    -- ipv6z                (4)
                    -- dns                  (16)
                    }
            DESCRIPTION
                 "tIPsecRUTnlPrivateIpAddr2Type supports only the
                  InetAddressType values 'unknown (0)', 'ipv4 (1)', and 'ipv6
                  (2)'."

        VARIATION   tIPsecTnlTempReverseRoute
            SYNTAX  INTEGER {
                       none                 (0),
                    -- reverseRoute         (1)
                       useSecurityPolicy    (2)
                    }
            DESCRIPTION
                 "tIPsecTnlTempReverseRoute supports only 'none(0)' and
                  'useSecurityPolicy (2)'."

        VARIATION   tIPsecTsListRmtEntryMaxAddrType
            SYNTAX  InetAddressType {
                       unknown              (0),
                       ipv4                 (1),
                       ipv6                 (2)
                    -- ipv4z                (3)
                    -- ipv6z                (4)
                    -- dns                  (16)
                    }
            DESCRIPTION
                 "tIPsecTsListRmtEntryMaxAddrType supports only the
                  InetAddressType values 'unknown (0)', 'ipv4 (1)', and 'ipv6
                  (2)'."

        VARIATION   tIPsecTsListRmtEntryMinAddrType
            SYNTAX  InetAddressType {
                       unknown              (0),
                       ipv4                 (1),
                       ipv6                 (2)
                    -- ipv4z                (3)
                    -- ipv6z                (4)
                    -- dns                  (16)
                    }
            DESCRIPTION
                 "tIPsecTsListRmtEntryMinAddrType supports only the
                  InetAddressType values 'unknown (0)', 'ipv4 (1)', and 'ipv6
                  (2)'."

        VARIATION   tIPsecTsListRmtEntryRowStatus
            SYNTAX  RowStatus {
                       active               (1),
                    -- notInService         (2)
                    -- notReady             (3)
                       createAndGo          (4),
                    -- createAndWait        (5)
                       destroy              (6)
                    }
            DESCRIPTION
                 "tIPsecTsListRmtEntryRowStatus supports only 'active (1)',
                  'createAndGo (4)', and 'destroy (6)'."

        VARIATION   tIPsecTsListRowStatus
            SYNTAX  RowStatus {
                       active               (1),
                    -- notInService         (2)
                    -- notReady             (3)
                       createAndGo          (4),
                    -- createAndWait        (5)
                       destroy              (6)
                    }
            DESCRIPTION
                 "tIPsecTsListRowStatus supports only 'active (1)', 'createAndGo
                  (4)', and 'destroy (6)'."

        VARIATION   tmnxIPsecGWDhcpV6LinkAddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6LinkAddrType supports only the
                  InetAddressType values 'unknown (0)' and 'ipv6 (2)'."

        VARIATION   tmnxIPsecGWDhcpV6Srvr1AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr1AddrType supports only the
                  InetAddressType values 'unknown (0)' and 'ipv6 (2)'."

        VARIATION   tmnxIPsecGWDhcpV6Srvr2AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr2AddrType supports only the
                  InetAddressType values 'unknown (0)' and 'ipv6 (2)'."

        VARIATION   tmnxIPsecGWDhcpV6Srvr3AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr3AddrType supports only the
                  InetAddressType values 'unknown (0)' and 'ipv6 (2)'."

        VARIATION   tmnxIPsecGWDhcpV6Srvr4AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr4AddrType supports only the
                  InetAddressType values 'unknown (0)' and 'ipv6 (2)'."

        VARIATION   tmnxIPsecGWDhcpV6Srvr5AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr5AddrType supports only the
                  InetAddressType values 'unknown (0)' and 'ipv6 (2)'."

        VARIATION   tmnxIPsecGWDhcpV6Srvr6AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr6AddrType supports only the
                  InetAddressType values 'unknown (0)' and 'ipv6 (2)'."

        VARIATION   tmnxIPsecGWDhcpV6Srvr7AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr7AddrType supports only the
                  InetAddressType values 'unknown (0)' and 'ipv6 (2)'."

        VARIATION   tmnxIPsecGWDhcpV6Srvr8AddrType
            SYNTAX  InetAddressType {
                       unknown              (0),
                    -- ipv4                 (1)
                       ipv6                 (2)
                    -- ipv4z                (3)
                    -- ipv6z                (4)
                    -- dns                  (16)
                    }
            DESCRIPTION
                 "tmnxIPsecGWDhcpV6Srvr8AddrType supports only the
                  InetAddressType values 'unknown (0)' and 'ipv6 (2)'."

        VARIATION   tmnxIPsecPlcyParamsV6LclAddrType
            SYNTAX  InetAddressType {
                       unknown              (0),
                    -- ipv4                 (1)
                       ipv6                 (2)
                    -- ipv4z                (3)
                    -- ipv6z                (4)
                    -- dns                  (16)
                    }
            DESCRIPTION
                 "tmnxIPsecPlcyParamsV6LclAddrType supports only the
                  InetAddressType values 'unknown (0)' and 'ipv6 (2)'."

        VARIATION   tmnxIPsecPlcyParamsV6RemAddrType
            SYNTAX  InetAddressType {
                       unknown              (0),
                    -- ipv4                 (1)
                       ipv6                 (2)
                    -- ipv4z                (3)
                    -- ipv6z                (4)
                    -- dns                  (16)
                    }
            DESCRIPTION
                 "tmnxIPsecPlcyParamsV6RemAddrType supports only the
                  InetAddressType values 'unknown (0)' and 'ipv6 (2)'."

        VARIATION   tmnxIPsecPolicyParamsLclAPrefLen
            SYNTAX  Unsigned32 (0..32)
            DESCRIPTION
                 "tmnxIPsecPolicyParamsLclAPrefLen supports values between 0 and
                  32 and setting to any other value results in an
                  'inconsistentValue' error."

        VARIATION   tmnxIPsecPolicyParamsLclAddr
            SYNTAX  InetAddress (SIZE (0|4))
            DESCRIPTION
                 "tmnxIPsecPolicyParamsLclAddr supports only InetAddressType
                  values 'unknown (0)' and 'ipv4 (1)'."

        VARIATION   tmnxIPsecPolicyParamsLclAddrType
            SYNTAX  InetAddressType {
                       unknown              (0),
                       ipv4                 (1)
                    -- ipv6                 (2)
                    -- ipv4z                (3)
                    -- ipv6z                (4)
                    -- dns                  (16)
                    }
            DESCRIPTION
                 "tmnxIPsecPolicyParamsLclAddrType supports only the
                  InetAddressType values 'unknown (0)' and 'ipv4 (1)'."

        VARIATION   tmnxIPsecPolicyParamsRemAPrefLen
            SYNTAX  Unsigned32 (0..32)
            DESCRIPTION
                 "tmnxIPsecPolicyParamsRemAPrefLen supports values between 0 and
                  32 and setting to any other value results in an
                  'inconsistentValue' error."

        VARIATION   tmnxIPsecPolicyParamsRemAddr
            SYNTAX  InetAddress (SIZE (0|4))
            DESCRIPTION
                 "tmnxIPsecPolicyParamsRemAddr supports only InetAddressType
                  values 'unknown (0)' and 'ipv4 (1)'."

        VARIATION   tmnxIPsecPolicyParamsRemAddrType
            SYNTAX  InetAddressType {
                       unknown              (0),
                       ipv4                 (1)
                    -- ipv6                 (2)
                    -- ipv4z                (3)
                    -- ipv6z                (4)
                    -- dns                  (16)
                    }
            DESCRIPTION
                 "tmnxIPsecPolicyParamsRemAddrType supports only the
                  InetAddressType values 'unknown (0)' and 'ipv4 (1)'."

        VARIATION   tmnxIPsecPolicyParamsRowStatus
            SYNTAX  RowStatus {
                       active               (1),
                    -- notInService         (2)
                    -- notReady             (3)
                       createAndGo          (4),
                    -- createAndWait        (5)
                       destroy              (6)
                    }
            DESCRIPTION
                 "tmnxIPsecPolicyParamsRowStatus supports only 'active (1)',
                  'createAndGo (4)', and 'destroy (6)'."

        VARIATION   tmnxIPsecPolicyRowStatus
            SYNTAX  RowStatus {
                       active               (1),
                    -- notInService         (2)
                    -- notReady             (3)
                       createAndGo          (4),
                    -- createAndWait        (5)
                       destroy              (6)
                    }
            DESCRIPTION
                 "tmnxIPsecPolicyRowStatus supports only 'active (1)',
                  'createAndGo (4)', and 'destroy (6)'."

        VARIATION   tmnxIPsecTransformRowStatus
            SYNTAX  RowStatus {
                       active               (1),
                    -- notInService         (2)
                    -- notReady             (3)
                       createAndGo          (4),
                    -- createAndWait        (5)
                       destroy              (6)
                    }
            DESCRIPTION
                 "tmnxIPsecTransformRowStatus supports only 'active (1)',
                  'createAndGo (4)', and 'destroy (6)'."

        VARIATION   tmnxIPsecTunnelAdminState
            SYNTAX  INTEGER {
                    -- noop                 (1)
                       inService            (2),
                       outOfService         (3)
                    }
            DESCRIPTION
                 "tmnxIPsecTunnelAdminState supports only the values 'inService
                  (2)' and 'outOfService (3)'."

        VARIATION   tmnxIPsecTunnelRowStatus
            SYNTAX  RowStatus {
                       active               (1),
                    -- notInService         (2)
                    -- notReady             (3)
                       createAndGo          (4),
                    -- createAndWait        (5)
                       destroy              (6)
                    }
            DESCRIPTION
                 "tmnxIPsecTunnelRowStatus supports only 'active (1)',
                  'createAndGo (4)', and 'destroy (6)'."

        VARIATION   tmnxIkePolicyAuthAlgorithm
            SYNTAX  INTEGER {
                       md5                  (2),
                       sha1                 (3)
                    }
            DESCRIPTION
                 "tmnxIkePolicyAuthAlgorithm supports only the values 'md5 (1)'
                  and 'sha1 (3)'."

        VARIATION   tmnxIkePolicyAuthMethod
            SYNTAX  INTEGER {
                       psk                  (1),
                       plainPskXAuth        (4)
                    }
            DESCRIPTION
                 "tmnxIkePolicyAuthMethod supports only 'psk (1)' and
                  'plainPskXAuth (4)'."

        VARIATION   tmnxIkePolicyEncrAlgorithm
            SYNTAX  INTEGER {
                       des                  (2),
                       des3                 (3),
                       aes128               (4),
                       aes192               (5),
                       aes256               (6)
                    }
            DESCRIPTION
                 "tmnxIkePolicyEncrAlgorithm supports only the values 'des (2)',
                  'des3 (3)', 'aes128 (4)', 'aes192 (5)' and 'aes256 (6)'."

        VARIATION   tmnxIkePolicyRowStatus
            SYNTAX  RowStatus {
                       active               (1),
                    -- notInService         (2)
                    -- notReady             (3)
                       createAndGo          (4),
                    -- createAndWait        (5)
                       destroy              (6)
                    }
            DESCRIPTION
                 "tmnxIkePolicyRowStatus supports only 'active (1)',
                  'createAndGo (4)', and 'destroy (6)'."

    ::= { tmnx7950AgentV14v0  56 }

--
-- SROS IPsec_Static CAPABILITIES
--
tmnxSROSIpsecStaticV14v0          AGENT-CAPABILITIES
    PRODUCT-RELEASE "Nokia SROS"
    STATUS          current
    DESCRIPTION
         "Implementation of IPsec Static SA tunneling, encryption and other
          related features capabilities for Nokia SROS systems release 14.0."

    SUPPORTS        TIMETRA-IPSEC-STATIC-SA-MIB
        INCLUDES {
           tmnxIPsecStaticSAGroup
        }

    ::= { tmnxSROSAgentV14v0  74 }

--
-- SROS ISIS CAPABILITIES
--
tmnxSROSIsisV14v0                 AGENT-CAPABILITIES
    PRODUCT-RELEASE "Nokia SROS"
    STATUS          current
    DESCRIPTION
         "Implementation of ISIS protocol capabilities for Nokia SROS systems
          release 14.0."

    SUPPORTS        ISIS-MIB
        INCLUDES {
           isisCircuitGroup,
           isisISAdjGroup,
-- EXCLUDE isisISIPRADestGroup
-- EXCLUDE isisISPDUCounterGroup,
-- EXCLUDE isisRATableGroup
           isisSystemGroup
        }

        VARIATION   isisCircEntry
            CREATION-REQUIRES {
                       vRtrIsisIfRowStatus
                    }
            DESCRIPTION
                 "Row entries in the isisCircTable are created by setting
                  TIMETRA-ISIS-MIB::vRtrIsisIfRowStatus."

        VARIATION   isisCircExistState
            SYNTAX  INTEGER {
                       active               (1)
                    }
            ACCESS  read-only
            DESCRIPTION
                 "isisCircExistState, the RowStatus object, is implemented as
                  read-only."

        VARIATION   isisCircExtDomain
            ACCESS  read-only
            DESCRIPTION
                 "isisCircExtDomain is implemented as read-only on Nokia SROS in
                  release 14.0."

        VARIATION   isisCircIfIndex
            ACCESS  read-only
            DESCRIPTION
                 "isisCircIfIndex is implemented as read-only on Nokia SROS in
                  release 14.0."

        VARIATION   isisCircIfSubIndex
            ACCESS  read-only
            DESCRIPTION
                 "isisCircIfSubIndex is implemented as read-only on Nokia SROS
                  in release 14.0."

        VARIATION   isisCircLevelCSNPInterval
            ACCESS  read-only
            DESCRIPTION
                 "isisCircLevelCSNPInterval is implemented as read-only on Nokia
                  SROS in release 14.0."

        VARIATION   isisCircLevelDRHelloTimer
            ACCESS  read-only
            DESCRIPTION
                 "isisCircLevelDRHelloTimer is implemented as read-only on Nokia
                  SROS in release 14.0."

        VARIATION   isisCircLevelDefaultMetric
            SYNTAX  DefaultMetric (0..63)
            ACCESS  read-only
            DESCRIPTION
                 "isisCircLevelDefaultMetric is implemented as read-only.
                  isisCircLevelDefaultMetric can have a value of 0 for loopback
                  and system interfaces."

        VARIATION   isisCircLevelHelloMultiplier
            DEFVAL  { 3  }
            DESCRIPTION
                 "The default hello multiplier value is 3 instead of 10 since
                  the value of 10 results in a long holding time."

        VARIATION   isisCircLevelHelloTimer
            ACCESS  read-only
            DESCRIPTION
                 "isisCircLevelHelloTimer is implemented as read-only on Nokia
                  SROS in release 14.0."

        VARIATION   isisCircLevelISPriority
            ACCESS  read-only
            DESCRIPTION
                 "isisCircLevelISPriority is implemented as read-only on Nokia
                  SROS in release 14.0."

        VARIATION   isisCircLevelLSPThrottle
            ACCESS  read-only
            DESCRIPTION
                 "isisCircLevelLSPThrottle is implemented as read-only on Nokia
                  SROS in release 14.0."

        VARIATION   isisCircLevelMinLSPRetransInt
            ACCESS  read-only
            DESCRIPTION
                 "isisCircLevelMinLSPRetransInt is implemented as read-only on
                  Nokia SROS in release 14.0."

        VARIATION   isisCircLevelPartSNPInterval
            ACCESS  read-only
            DESCRIPTION
                 "isisCircLevelPartSNPInterval is implemented as read-only on
                  Nokia SROS in release 14.0."

        VARIATION   isisCircMCAddr
            ACCESS  read-only
            DESCRIPTION
                 "isisCircMCAddr is implemented as read-only on Nokia SROS in
                  release 14.0."

        VARIATION   isisCircSmallHellos
            ACCESS  read-only
            DESCRIPTION
                 "isisCircSmallHellos is implemented as read-only on Nokia SROS
                  in release 14.0."

        VARIATION   isisISAdjProtSuppProtocol
            SYNTAX  INTEGER {
                       iso8473(129),
                       spb(193),
                       ip(204),
                       ipV6(205)
                    }
            ACCESS  read-only
            DESCRIPTION
                 "The value 193 is the NLPID assigned for SPB (or IEEE 802.1aq)
                  as per RFC6328/RFC6329."

        VARIATION   isisManAreaAddrExistState
            SYNTAX  RowStatus {
                       active               (1),
                    -- notInService         (2)
                    -- notReady             (3)
                       createAndGo          (4),
                    -- createAndWait        (5)
                       destroy              (6)
                    }
            DESCRIPTION
                 "isisManAreaAddrExistState supports only 'active (1)',
                  'createAndGo (4)', and 'destroy (6)'."

        VARIATION   isisSummAddrAdminState
            ACCESS  not-implemented
            DESCRIPTION
                 "isisSummAddrAdminState is not implemented. This object is no
                  longer supported in the 6.0 release."

        VARIATION   isisSummAddrDefaultMetric
            ACCESS  not-implemented
            DESCRIPTION
                 "isisSummAddrDefaultMetric is not implemented. This object is
                  no longer supported in the 6.0 release."

        VARIATION   isisSummAddrExistState
            ACCESS  not-implemented
            DESCRIPTION
                 "isisSummAddrExistState is not implemented. This object is no
                  longer supported in the 6.0 release."

        VARIATION   isisSummAddrPrefixLen
            ACCESS  not-implemented
            DESCRIPTION
                 "isisSummAddrPrefixLen is not implemented. This object is no
                  longer supported in the 6.0 release.

                  It has been replaced by TIMETRA-ISIS-MIB::vRtrIsisSummMask."

        VARIATION   isisSummAddress
            ACCESS  not-implemented
            DESCRIPTION
                 "isisSummAddress is not implemented. This object is no longer
                  supported in the 6.0 release.

                  It has been replaced by
                  TIMETRA-ISIS-MIB::vRtrIsisSummPrefix."

        VARIATION   isisSummAddressType
            ACCESS  not-implemented
            DESCRIPTION
                 "isisSummAddressType is not implemented. This object is no
                  longer supported in the 6.0 release.

                  It has been replaced by
                  TIMETRA-ISIS-MIB::vRtrIsisSummPrefix."

        VARIATION   isisSysExistState
            SYNTAX  RowStatus {
                       active               (1),
                    -- notInService         (2)
                    -- notReady             (3)
                       createAndGo          (4),
                    -- createAndWait        (5)
                       destroy              (6)
                    }
            DESCRIPTION
                 "isisSysExistState supports only 'active (1)', 'createAndGo
                  (4)', and 'destroy (6)'."

        VARIATION   isisSysID
            ACCESS  read-only
            DESCRIPTION
                 "isisSysID is implemented as read-only on Nokia SROS in release
                  14.0."

        VARIATION   isisSysL2toL1Leaking
            ACCESS  read-only
            DESCRIPTION
                 "isisSysL2toL1Leaking is implemented as read-only on Nokia SROS
                  in release 14.0."

        VARIATION   isisSysLSPIgnoreErrors
            ACCESS  read-only
            DESCRIPTION
                 "isisSysLSPIgnoreErrors is implemented as read-only on Nokia
                  SROS in release 14.0."

        VARIATION   isisSysLogAdjacencyChanges
            ACCESS  read-only
            DESCRIPTION
                 "isisSysLogAdjacencyChanges is implemented as read-only on
                  Nokia SROS in release 14.0."

        VARIATION   isisSysMaxAreaAddresses
            ACCESS  read-only
            DESCRIPTION
                 "isisSysMaxAreaAddresses is implemented as read-only on Nokia
                  SROS in release 14.0."

        VARIATION   isisSysMaxPathSplits
            ACCESS  read-only
            DESCRIPTION
                 "isisSysMaxPathSplits is implemented as read-only on Nokia SROS
                  in release 14.0."

        VARIATION   isisSysMinL1LSPGenInt
            ACCESS  read-only
            DESCRIPTION
                 "isisSysMinL1LSPGenInt is implemented as read-only on Nokia
                  SROS in release 14.0."

        VARIATION   isisSysMinL2LSPGenInt
            ACCESS  read-only
            DESCRIPTION
                 "isisSysMinL2LSPGenInt is implemented as read-only on Nokia
                  SROS in release 14.0."

        VARIATION   isisSysOrigL1LSPBuffSize
            ACCESS  not-implemented
            DESCRIPTION
                 "isisSysOrigL1LSPBuffSize is not implemented. This object is no
                  longer supported in the 6.0 release.

                  It has been replaced by
                  TIMETRA-ISIS-MIB::vRtrIsisSysOrigL1LSPBuffSize."

        VARIATION   isisSysOrigL2LSPBuffSize
            ACCESS  not-implemented
            DESCRIPTION
                 "isisSysOrigL2LSPBuffSize is not implemented. This object is no
                  longer supported in the 6.0 release.

                  It has been replaced by
                  TIMETRA-ISIS-MIB::vRtrIsisSysOrigL2LSPBuffSize."

        VARIATION   isisSysPollESHelloRate
            ACCESS  read-only
            DESCRIPTION
                 "isisSysPollESHelloRate is implemented as read-only on Nokia
                  SROS in release 14.0."

        VARIATION   isisSysProtSuppExistState
            ACCESS  read-only
            DESCRIPTION
                 "isisSysProtSuppExistState is implemented as read-only on Nokia
                  SROS in release 14.0."

        VARIATION   isisSysWaitTime
            SYNTAX  Integer32 (60..1800)
            DESCRIPTION
                 "The supported waiting time is limited to values between 60 and
                  1800. This object has been extended by
                  TIMETRA-ISIS-MIB::tmnxIsisOverloadTimeout. When
                  tmnxIsisOverloadTimeout is set to 0, the isisSysWaitTime will
                  be set to it's default value."

    SUPPORTS        TIMETRA-ISIS-MIB
        INCLUDES {
           vRtrIsisLgV12v0Group,
           vRtrIsisNotifyObjsV10v0Group,
           vRtrIsisNotifyV10v0Group,
           vRtrSpbEctFidGroup
        }

        VARIATION   vRtrIsisLgRowStatus
            SYNTAX  RowStatus {
                       active               (1),
                    -- notInService         (2)
                    -- notReady             (3)
                       createAndGo          (4),
                    -- createAndWait        (5)
                       destroy              (6)
                    }
            DESCRIPTION
                 "vRtrIsisLgRowStatus supports only 'active (1)', 'createAndGo
                  (4)', and 'destroy (6)'."

    SUPPORTS        TIMETRA-ISIS-NG-MIB
        INCLUDES {
           tmnxIsisAdjGroup,
           tmnxIsisGroup,
           tmnxIsisIfGroup,
           tmnxIsisLFAV12v0Group,
           tmnxIsisNotifyGroup,
           tmnxIsisNotifyV13v0Group,
           tmnxIsisNotifyV14v0Group,
           tmnxIsisV13v0Group,
           tmnxIsisV14v0Group
        }

        VARIATION   tmnxIsisIfRowStatus
            SYNTAX  RowStatus {
                       active               (1),
                    -- notInService         (2)
                    -- notReady             (3)
                       createAndGo          (4),
                    -- createAndWait        (5)
                       destroy              (6)
                    }
            DESCRIPTION
                 "tmnxIsisIfRowStatus supports only 'active (1)', 'createAndGo
                  (4)', and 'destroy (6)'."

        VARIATION   tmnxIsisSRMSSidMapPrefixType
            SYNTAX  InetAddressType {
                    -- unknown              (0)
                       ipv4                 (1)
                    -- ipv6                 (2)
                    -- ipv4z                (3)
                    -- ipv6z                (4)
                    -- dns                  (16)
                    }
            DESCRIPTION
                 "tmnxIsisSRMSSidMapPrefixType supports only the InetAddressType
                  value 'ipv4 (1)'."

        VARIATION   tmnxIsisSRMSSidMapRowStatus
            SYNTAX  RowStatus {
                       active               (1),
                    -- notInService         (2)
                    -- notReady             (3)
                       createAndGo          (4),
                    -- createAndWait        (5)
                       destroy              (6)
                    }
            DESCRIPTION
                 "tmnxIsisSRMSSidMapRowStatus supports only 'active (1)',
                  'createAndGo (4)', and 'destroy (6)'."

        VARIATION   tmnxIsisSRMapServAdminState
            SYNTAX  INTEGER {
                    -- noop                 (1)
                       inService            (2),
                       outOfService         (3)
                    }
            DESCRIPTION
                 "tmnxIsisSRMapServAdminState supports only the values
                  'inService (2)' and 'outOfService (3)'."

        VARIATION   tmnxIsisSummRowStatus
            SYNTAX  RowStatus {
                       active               (1),
                    -- notInService         (2)
                    -- notReady             (3)
                       createAndGo          (4),
                    -- createAndWait        (5)
                       destroy              (6)
                    }
            DESCRIPTION
                 "tmnxIsisSummRowStatus supports only 'active (1)', 'createAndGo
                  (4)', and 'destroy (6)'."

    ::= { tmnxSROSAgentV14v0  21 }

--
-- 7750 L2TP CAPABILITIES
--
tmnx7750L2tpV14v0                 AGENT-CAPABILITIES
    PRODUCT-RELEASE "Nokia SROS"
    STATUS          current
    DESCRIPTION
         "Implementation of the L2TP (Layer Two Tunneling Protocol) feature for
          Nokia 7750 systems release 14.0."

    SUPPORTS        TIMETRA-L2TP-MIB
        INCLUDES {
           tmnxL2tpAccountingGroup,
           tmnxL2tpAccountingV12v0Group,
           tmnxL2tpAccountingV13v0Group,
           tmnxL2tpCfgV14v0Group,
           tmnxL2tpCfgV8v0Group,
           tmnxL2tpDontFragmentBitLacGroup,
-- EXCLUDE tmnxL2tpFilterProfileV9v0Group
           tmnxL2tpLnsIfV9v0Group,
           tmnxL2tpLnsIsaGroup,
           tmnxL2tpLnsIsaStatGroup,
           tmnxL2tpLnsIsaStatV12v0Group,
           tmnxL2tpLnsIsaV10v0Group,
           tmnxL2tpLnsSeV9v0Group,
           tmnxL2tpLnsTgGroup,
           tmnxL2tpLnsTgV11v0Group,
           tmnxL2tpLnsTgV9v0Group,
           tmnxL2tpLnsTuGroup,
           tmnxL2tpLnsTuV11v0Group,
           tmnxL2tpLnsTuV9v0Group,
           tmnxL2tpMlpppGroup,
           tmnxL2tpMultiChassisGroup,
           tmnxL2tpNotifyGroup,
           tmnxL2tpNotifyObjsGroup,
           tmnxL2tpNotifyObjsV9v0Group,
           tmnxL2tpNotifyV10v0Group,
           tmnxL2tpNotifyV11v0Group,
           tmnxL2tpNotifyV9v0Group,
           tmnxL2tpPeerOpGroup,
           tmnxL2tpPeerStatV8v0Group,
           tmnxL2tpSeOpGroup,
           tmnxL2tpSeStatGroup,
           tmnxL2tpSeStatV14v0Group,
           tmnxL2tpStatV11v0Group,
           tmnxL2tpTgCfgGroup,
           tmnxL2tpTgOpGroup,
           tmnxL2tpTgStatGroup,
           tmnxL2tpTgStatV14v0Group,
           tmnxL2tpTgV10v0Group,
           tmnxL2tpTgV14v0Group,
           tmnxL2tpTuCfgGroup,
           tmnxL2tpTuOpGroup,
           tmnxL2tpTuStatGroup,
           tmnxL2tpTuStatV11v0Group,
           tmnxL2tpTuStatV14v0Group,
           tmnxL2tpTuV10v0Group,
           tmnxL2tpV11v0Group,
           tmnxL2tpV3SeStatV14v0Group,
           tmnxL2tpV3TgV14v0Group,
           tmnxL2tpV3V14v0Group
        }

        VARIATION   tmnxL2tpAdminState
            SYNTAX  INTEGER {
                    -- noop                 (1)
                       inService            (2),
                       outOfService         (3)
                    }
            DESCRIPTION
                 "tmnxL2tpAdminState supports only the values 'inService (2)'
                  and 'outOfService (3)'."

        VARIATION   tmnxL2tpApRowStatus
            SYNTAX  RowStatus {
                       active               (1),
                    -- notInService         (2)
                    -- notReady             (3)
                       createAndGo          (4),
                    -- createAndWait        (5)
                       destroy              (6)
                    }
            DESCRIPTION
                 "tmnxL2tpApRowStatus supports only 'active (1)', 'createAndGo
                  (4)', and 'destroy (6)'."

        VARIATION   tmnxL2tpApServAddr
            SYNTAX  InetAddress (SIZE(4))
            DESCRIPTION
                 "Only IPv4 addresses are allowed."

        VARIATION   tmnxL2tpApServAddrType
            SYNTAX  InetAddressType {
                    -- unknown              (0)
                       ipv4                 (1)
                    -- ipv6                 (2)
                    -- ipv4z                (3)
                    -- ipv6z                (4)
                    -- dns                  (16)
                    }
            DESCRIPTION
                 "tmnxL2tpApServAddrType supports only the InetAddressType value
                  'ipv4 (1)'."

        VARIATION   tmnxL2tpApServRowStatus
            SYNTAX  RowStatus {
                       active               (1),
                    -- notInService         (2)
                    -- notReady             (3)
                       createAndGo          (4),
                    -- createAndWait        (5)
                       destroy              (6)
                    }
            DESCRIPTION
                 "tmnxL2tpApServRowStatus supports only 'active (1)',
                  'createAndGo (4)', and 'destroy (6)'."

        VARIATION   tmnxL2tpApServerSrcAddr
            SYNTAX  InetAddress (SIZE(0|4))
            DESCRIPTION
                 "tmnxL2tpApServerSrcAddr only supports the values ''H and IPv4
                  addresses."

        VARIATION   tmnxL2tpApServerSrcAddrType
            SYNTAX  InetAddressType {
                       unknown              (0),
                       ipv4                 (1)
                    -- ipv6                 (2)
                    -- ipv4z                (3)
                    -- ipv6z                (4)
                    -- dns                  (16)
                    }
            DESCRIPTION
                 "tmnxL2tpApServerSrcAddrType supports only the InetAddressType
                  values 'unknown (0)' and 'ipv4 (1)'."

        VARIATION   tmnxL2tpIsaGrpAdminState
            SYNTAX  INTEGER {
                    -- noop                 (1)
                       inService            (2),
                       outOfService         (3)
                    }
            DESCRIPTION
                 "tmnxL2tpIsaGrpAdminState supports only the values 'inService
                  (2)' and 'outOfService (3)'."

        VARIATION   tmnxL2tpIsaGrpRowStatus
            SYNTAX  RowStatus {
                       active               (1),
                    -- notInService         (2)
                    -- notReady             (3)
                       createAndGo          (4),
                    -- createAndWait        (5)
                       destroy              (6)
                    }
            DESCRIPTION
                 "tmnxL2tpIsaGrpRowStatus supports only 'active (1)',
                  'createAndGo (4)', and 'destroy (6)'."

        VARIATION   tmnxL2tpIsaMdaRowStatus
            SYNTAX  RowStatus {
                       active               (1),
                    -- notInService         (2)
                    -- notReady             (3)
                       createAndGo          (4),
                    -- createAndWait        (5)
                       destroy              (6)
                    }
            DESCRIPTION
                 "tmnxL2tpIsaMdaRowStatus supports only 'active (1)',
                  'createAndGo (4)', and 'destroy (6)'."

        VARIATION   tmnxL2tpLnsIfDefFilterProfile
            ACCESS  not-implemented
            DESCRIPTION
                 "tmnxL2tpLnsIfDefFilterProfile is not implemented on Nokia 7750
                  in release 14.0."

        VARIATION   tmnxL2tpLnsIfDefSubIdent
            SYNTAX  INTEGER {
                    -- useSapId             (1)
                       useString            (2),
                       useAutoId            (3)
                    }
            DESCRIPTION
                 "tmnxL2tpLnsIfDefSubIdent only supports the value 'useString
                  (2)' and 'useAutoId (3)'."

        VARIATION   tmnxL2tpRowStatus
            SYNTAX  RowStatus {
                       active               (1),
                    -- notInService         (2)
                    -- notReady             (3)
                       createAndGo          (4),
                    -- createAndWait        (5)
                       destroy              (6)
                    }
            DESCRIPTION
                 "tmnxL2tpRowStatus supports only 'active (1)', 'createAndGo
                  (4)', and 'destroy (6)'."

        VARIATION   tmnxL2tpTgCfgAddr
            SYNTAX  InetAddress (SIZE(0|4))
            DESCRIPTION
                 "tmnxL2tpTgCfgAddr only supports the values ''H and IPv4
                  addresses."

        VARIATION   tmnxL2tpTgCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTgCfgAddrType supports only the InetAddressType values
                  'unknown (0)' and 'ipv4 (1)'."

        VARIATION   tmnxL2tpTgCfgAdminState
            SYNTAX  INTEGER {
                    -- noop                 (1)
                       inService            (2),
                       outOfService         (3)
                    }
            DESCRIPTION
                 "tmnxL2tpTgCfgAdminState supports only the values 'inService
                  (2)' and 'outOfService (3)'."

        VARIATION   tmnxL2tpTgCfgRowStatus
            SYNTAX  RowStatus {
                       active               (1),
                    -- notInService         (2)
                    -- notReady             (3)
                       createAndGo          (4),
                    -- createAndWait        (5)
                       destroy              (6)
                    }
            DESCRIPTION
                 "tmnxL2tpTgCfgRowStatus supports only 'active (1)',
                  'createAndGo (4)', and 'destroy (6)'."

        VARIATION   tmnxL2tpTgMlpppAdminState
            SYNTAX  INTEGER {
                    -- noop                 (1)
                       inService            (2),
                       outOfService         (3)
                    }
            DESCRIPTION
                 "tmnxL2tpTgMlpppAdminState supports only the values 'inService
                  (2)' and 'outOfService (3)'."

        VARIATION   tmnxL2tpTuCfgAddr
            SYNTAX  InetAddress (SIZE(0|4))
            DESCRIPTION
                 "tmnxL2tpTuCfgAddr only supports the values ''H and IPv4
                  addresses.

                  In case of a LAC tunnel, the only allowed value for this
                  object is ''H; the value used instead is the value of the
                  object vRiaInetAddress of the entry corresponding to the
                  system interface."

        VARIATION   tmnxL2tpTuCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgAddrType supports only the InetAddressType values
                  'unknown (0)' and 'ipv4 (1)'.

                  In case of a LAC tunnel, the only allowed value for this
                  object is 'unknown (0)'; the value used instead is the actual
                  value of the object vRiaInetAddressType of the entry
                  corresponding to the system interface."

        VARIATION   tmnxL2tpTuCfgAdminState
            SYNTAX  INTEGER {
                    -- noop                 (1)
                       inService            (2),
                       outOfService         (3)
                    }
            DESCRIPTION
                 "tmnxL2tpTuCfgAdminState supports only the values 'inService
                  (2)' and 'outOfService (3)'."

        VARIATION   tmnxL2tpTuCfgPeerAddr
            SYNTAX  InetAddress (SIZE(0|4))
            DESCRIPTION
                 "tmnxL2tpTuCfgPeerAddr only supports the values ''H and IPv4
                  addresses."

        VARIATION   tmnxL2tpTuCfgPeerAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgPeerAddrType supports only the InetAddressType
                  values 'unknown (0)' and 'ipv4 (1)'."

        VARIATION   tmnxL2tpTuCfgRowStatus
            SYNTAX  RowStatus {
                       active               (1),
                    -- notInService         (2)
                    -- notReady             (3)
                       createAndGo          (4),
                    -- createAndWait        (5)
                       destroy              (6)
                    }
            DESCRIPTION
                 "tmnxL2tpTuCfgRowStatus supports only 'active (1)',
                  'createAndGo (4)', and 'destroy (6)'."

        VARIATION   tmnxL2tpTuCfgSessionLimit
            SYNTAX  TmnxL2tpSessionLimit (1..65535)
            DESCRIPTION
                 "The number of sessions allowed for a tunnel is currently
                  limited to 65535.

                  The reason is that currently only L2TP version 2 is
                  supported, and version 2 uses a 16 bit number to identify a
                  session."

        VARIATION   tmnxL2tpV3TgPwCapList
            SYNTAX  BITS {
                       ethernet             (0)
                    -- ethernetVlan         (1)
                    }
            DESCRIPTION
                 "The only bit that can be modified in the tmnxL2tpV3TgPwCapList
                  object is 'ethernet (0)'."

    ::= { tmnx7750AgentV14v0  68 }

--
-- 7750c12 L2TP CAPABILITIES
--
tmnx7750c12L2tpV14v0              AGENT-CAPABILITIES
    PRODUCT-RELEASE "Nokia SROS"
    STATUS          current
    DESCRIPTION
         "Implementation of the L2TP (Layer Two Tunneling Protocol) feature for
          Nokia 7750 c12 systems release 14.0."

    SUPPORTS        TIMETRA-L2TP-MIB
        INCLUDES {
           tmnxL2tpAccountingGroup,
           tmnxL2tpAccountingV12v0Group,
           tmnxL2tpAccountingV13v0Group,
           tmnxL2tpCfgV14v0Group,
           tmnxL2tpCfgV8v0Group,
           tmnxL2tpDontFragmentBitLacGroup,
-- EXCLUDE tmnxL2tpFilterProfileV9v0Group
-- EXCLUDE tmnxL2tpLnsIfV9v0Group
-- EXCLUDE tmnxL2tpLnsIsaGroup
-- EXCLUDE tmnxL2tpLnsIsaStatGroup
-- EXCLUDE tmnxL2tpLnsIsaStatV12v0Group
           tmnxL2tpLnsIsaV10v0Group,
           tmnxL2tpLnsSeV9v0Group,
           tmnxL2tpLnsTgGroup,
           tmnxL2tpLnsTgV11v0Group,
           tmnxL2tpLnsTgV9v0Group,
           tmnxL2tpLnsTuGroup,
           tmnxL2tpLnsTuV11v0Group,
           tmnxL2tpLnsTuV9v0Group,
           tmnxL2tpMlpppGroup,
           tmnxL2tpMultiChassisGroup,
           tmnxL2tpNotifyGroup,
           tmnxL2tpNotifyObjsGroup,
           tmnxL2tpNotifyObjsV9v0Group,
           tmnxL2tpNotifyV10v0Group,
           tmnxL2tpNotifyV11v0Group,
           tmnxL2tpNotifyV9v0Group,
           tmnxL2tpPeerOpGroup,
           tmnxL2tpPeerStatV8v0Group,
           tmnxL2tpSeOpGroup,
           tmnxL2tpSeStatGroup,
           tmnxL2tpSeStatV14v0Group,
           tmnxL2tpStatV11v0Group,
           tmnxL2tpTgCfgGroup,
           tmnxL2tpTgOpGroup,
           tmnxL2tpTgStatGroup,
           tmnxL2tpTgStatV14v0Group,
           tmnxL2tpTgV10v0Group,
           tmnxL2tpTgV14v0Group,
           tmnxL2tpTuCfgGroup,
           tmnxL2tpTuOpGroup,
           tmnxL2tpTuStatGroup,
           tmnxL2tpTuStatV11v0Group,
           tmnxL2tpTuStatV14v0Group,
           tmnxL2tpTuV10v0Group,
           tmnxL2tpV11v0Group,
           tmnxL2tpV3SeStatV14v0Group,
           tmnxL2tpV3TgV14v0Group,
           tmnxL2tpV3V14v0Group
        }

        VARIATION   tmnxL2tpAdminState
            SYNTAX  INTEGER {
                    -- noop                 (1)
                       inService            (2),
                       outOfService         (3)
                    }
            DESCRIPTION
                 "tmnxL2tpAdminState supports only the values 'inService (2)'
                  and 'outOfService (3)'."

        VARIATION   tmnxL2tpApRowStatus
            SYNTAX  RowStatus {
                       active               (1),
                    -- notInService         (2)
                    -- notReady             (3)
                       createAndGo          (4),
                    -- createAndWait        (5)
                       destroy              (6)
                    }
            DESCRIPTION
                 "tmnxL2tpApRowStatus supports only 'active (1)', 'createAndGo
                  (4)', and 'destroy (6)'."

        VARIATION   tmnxL2tpApServAddr
            SYNTAX  InetAddress (SIZE(4))
            DESCRIPTION
                 "Only IPv4 addresses are allowed."

        VARIATION   tmnxL2tpApServAddrType
            SYNTAX  InetAddressType {
                    -- unknown              (0)
                       ipv4                 (1)
                    -- ipv6                 (2)
                    -- ipv4z                (3)
                    -- ipv6z                (4)
                    -- dns                  (16)
                    }
            DESCRIPTION
                 "tmnxL2tpApServAddrType supports only the InetAddressType value
                  'ipv4 (1)'."

        VARIATION   tmnxL2tpApServRowStatus
            SYNTAX  RowStatus {
                       active               (1),
                    -- notInService         (2)
                    -- notReady             (3)
                       createAndGo          (4),
                    -- createAndWait        (5)
                       destroy              (6)
                    }
            DESCRIPTION
                 "tmnxL2tpApServRowStatus supports only 'active (1)',
                  'createAndGo (4)', and 'destroy (6)'."

        VARIATION   tmnxL2tpApServerSrcAddr
            SYNTAX  InetAddress (SIZE(0|4))
            DESCRIPTION
                 "tmnxL2tpApServerSrcAddr only supports the values ''H and IPv4
                  addresses."

        VARIATION   tmnxL2tpApServerSrcAddrType
            SYNTAX  InetAddressType {
                       unknown              (0),
                       ipv4                 (1)
                    -- ipv6                 (2)
                    -- ipv4z                (3)
                    -- ipv6z                (4)
                    -- dns                  (16)
                    }
            DESCRIPTION
                 "tmnxL2tpApServerSrcAddrType supports only the InetAddressType
                  values 'unknown (0)' and 'ipv4 (1)'."

        VARIATION   tmnxL2tpLnsIfDefFilterProfile
            ACCESS  not-implemented
            DESCRIPTION
                 "tmnxL2tpLnsIfDefFilterProfile is not implemented on Nokia 7750
                  c12 in release 14.0."

        VARIATION   tmnxL2tpLnsIfDefSubIdent
            SYNTAX  INTEGER {
                    -- useSapId             (1)
                       useString            (2),
                       useAutoId            (3)
                    }
            DESCRIPTION
                 "tmnxL2tpLnsIfDefSubIdent only supports the value 'useString
                  (2)' and 'useAutoId (3)'."

        VARIATION   tmnxL2tpRowStatus
            SYNTAX  RowStatus {
                       active               (1),
                    -- notInService         (2)
                    -- notReady             (3)
                       createAndGo          (4),
                    -- createAndWait        (5)
                       destroy              (6)
                    }
            DESCRIPTION
                 "tmnxL2tpRowStatus supports only 'active (1)', 'createAndGo
                  (4)', and 'destroy (6)'."

        VARIATION   tmnxL2tpTgCfgAddr
            SYNTAX  InetAddress (SIZE(0|4))
            DESCRIPTION
                 "tmnxL2tpTgCfgAddr only supports the values ''H and IPv4
                  addresses."

        VARIATION   tmnxL2tpTgCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTgCfgAddrType supports only the InetAddressType values
                  'unknown (0)' and 'ipv4 (1)'."

        VARIATION   tmnxL2tpTgCfgAdminState
            SYNTAX  INTEGER {
                    -- noop                 (1)
                       inService            (2),
                       outOfService         (3)
                    }
            DESCRIPTION
                 "tmnxL2tpTgCfgAdminState supports only the values 'inService
                  (2)' and 'outOfService (3)'."

        VARIATION   tmnxL2tpTgCfgRowStatus
            SYNTAX  RowStatus {
                       active               (1),
                    -- notInService         (2)
                    -- notReady             (3)
                       createAndGo          (4),
                    -- createAndWait        (5)
                       destroy              (6)
                    }
            DESCRIPTION
                 "tmnxL2tpTgCfgRowStatus supports only 'active (1)',
                  'createAndGo (4)', and 'destroy (6)'."

        VARIATION   tmnxL2tpTgMlpppAdminState
            SYNTAX  INTEGER {
                    -- noop                 (1)
                       inService            (2),
                       outOfService         (3)
                    }
            DESCRIPTION
                 "tmnxL2tpTgMlpppAdminState supports only the values 'inService
                  (2)' and 'outOfService (3)'."

        VARIATION   tmnxL2tpTuCfgAddr
            SYNTAX  InetAddress (SIZE(0|4))
            DESCRIPTION
                 "tmnxL2tpTuCfgAddr only supports the values ''H and IPv4
                  addresses.

                  In case of a LAC tunnel, the only allowed value for this
                  object is ''H; the value used instead is the value of the
                  object vRiaInetAddress of the entry corresponding to the
                  system interface."

        VARIATION   tmnxL2tpTuCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgAddrType supports only the InetAddressType values
                  'unknown (0)' and 'ipv4 (1)'.

                  In case of a LAC tunnel, the only allowed value for this
                  object is 'unknown (0)'; the value used instead is the actual
                  value of the object vRiaInetAddressType of the entry
                  corresponding to the system interface."

        VARIATION   tmnxL2tpTuCfgAdminState
            SYNTAX  INTEGER {
                    -- noop                 (1)
                       inService            (2),
                       outOfService         (3)
                    }
            DESCRIPTION
                 "tmnxL2tpTuCfgAdminState supports only the values 'inService
                  (2)' and 'outOfService (3)'."

        VARIATION   tmnxL2tpTuCfgPeerAddr
            SYNTAX  InetAddress (SIZE(0|4))
            DESCRIPTION
                 "tmnxL2tpTuCfgPeerAddr only supports the values ''H and IPv4
                  addresses."

        VARIATION   tmnxL2tpTuCfgPeerAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgPeerAddrType supports only the InetAddressType
                  values 'unknown (0)' and 'ipv4 (1)'."

        VARIATION   tmnxL2tpTuCfgRowStatus
            SYNTAX  RowStatus {
                       active               (1),
                    -- notInService         (2)
                    -- notReady             (3)
                       createAndGo          (4),
                    -- createAndWait        (5)
                       destroy              (6)
                    }
            DESCRIPTION
                 "tmnxL2tpTuCfgRowStatus supports only 'active (1)',
                  'createAndGo (4)', and 'destroy (6)'."

        VARIATION   tmnxL2tpTuCfgSessionLimit
            SYNTAX  TmnxL2tpSessionLimit (1..65535)
            DESCRIPTION
                 "The number of sessions allowed for a tunnel is currently
                  limited to 65535.

                  The reason is that currently only L2TP version 2 is
                  supported, and version 2 uses a 16 bit number to identify a
                  session."

        VARIATION   tmnxL2tpV3TgPwCapList
            SYNTAX  BITS {
                       ethernet             (0)
                    -- ethernetVlan         (1)
                    }
            DESCRIPTION
                 "The only bit that can be modified in the tmnxL2tpV3TgPwCapList
                  object is 'ethernet (0)'."

    ::= { tmnx7750c12AgentV14v0  68 }

--
-- 7750c4 L2TP CAPABILITIES
--
tmnx7750c4L2tpV14v0               AGENT-CAPABILITIES
    PRODUCT-RELEASE "Nokia SROS"
    STATUS          current
    DESCRIPTION
         "Implementation of the L2TP (Layer Two Tunneling Protocol) feature for
          Nokia 7750 c4 systems release 14.0."

    SUPPORTS        TIMETRA-L2TP-MIB
        INCLUDES {
           tmnxL2tpAccountingGroup,
           tmnxL2tpAccountingV12v0Group,
           tmnxL2tpAccountingV13v0Group,
           tmnxL2tpCfgV14v0Group,
           tmnxL2tpCfgV8v0Group,
           tmnxL2tpDontFragmentBitLacGroup,
-- EXCLUDE tmnxL2tpFilterProfileV9v0Group
-- EXCLUDE tmnxL2tpLnsIfV9v0Group
-- EXCLUDE tmnxL2tpLnsIsaGroup
-- EXCLUDE tmnxL2tpLnsIsaStatGroup
-- EXCLUDE tmnxL2tpLnsIsaStatV12v0Group
           tmnxL2tpLnsIsaV10v0Group,
           tmnxL2tpLnsSeV9v0Group,
           tmnxL2tpLnsTgGroup,
           tmnxL2tpLnsTgV11v0Group,
           tmnxL2tpLnsTgV9v0Group,
           tmnxL2tpLnsTuGroup,
           tmnxL2tpLnsTuV11v0Group,
           tmnxL2tpLnsTuV9v0Group,
           tmnxL2tpMlpppGroup,
           tmnxL2tpMultiChassisGroup,
           tmnxL2tpNotifyGroup,
           tmnxL2tpNotifyObjsGroup,
           tmnxL2tpNotifyObjsV9v0Group,
           tmnxL2tpNotifyV10v0Group,
           tmnxL2tpNotifyV11v0Group,
           tmnxL2tpNotifyV9v0Group,
           tmnxL2tpPeerOpGroup,
           tmnxL2tpPeerStatV8v0Group,
           tmnxL2tpSeOpGroup,
           tmnxL2tpSeStatGroup,
           tmnxL2tpSeStatV14v0Group,
           tmnxL2tpStatV11v0Group,
           tmnxL2tpTgCfgGroup,
           tmnxL2tpTgOpGroup,
           tmnxL2tpTgStatGroup,
           tmnxL2tpTgStatV14v0Group,
           tmnxL2tpTgV10v0Group,
           tmnxL2tpTgV14v0Group,
           tmnxL2tpTuCfgGroup,
           tmnxL2tpTuOpGroup,
           tmnxL2tpTuStatGroup,
           tmnxL2tpTuStatV11v0Group,
           tmnxL2tpTuStatV14v0Group,
           tmnxL2tpTuV10v0Group,
           tmnxL2tpV11v0Group,
           tmnxL2tpV3SeStatV14v0Group,
           tmnxL2tpV3TgV14v0Group,
           tmnxL2tpV3V14v0Group
        }

        VARIATION   tmnxL2tpAdminState
            SYNTAX  INTEGER {
                    -- noop                 (1)
                       inService            (2),
                       outOfService         (3)
                    }
            DESCRIPTION
                 "tmnxL2tpAdminState supports only the values 'inService (2)'
                  and 'outOfService (3)'."

        VARIATION   tmnxL2tpApRowStatus
            SYNTAX  RowStatus {
                       active               (1),
                    -- notInService         (2)
                    -- notReady             (3)
                       createAndGo          (4),
                    -- createAndWait        (5)
                       destroy              (6)
                    }
            DESCRIPTION
                 "tmnxL2tpApRowStatus supports only 'active (1)', 'createAndGo
                  (4)', and 'destroy (6)'."

        VARIATION   tmnxL2tpApServAddr
            SYNTAX  InetAddress (SIZE(4))
            DESCRIPTION
                 "Only IPv4 addresses are allowed."

        VARIATION   tmnxL2tpApServAddrType
            SYNTAX  InetAddressType {
                    -- unknown              (0)
                       ipv4                 (1)
                    -- ipv6                 (2)
                    -- ipv4z                (3)
                    -- ipv6z                (4)
                    -- dns                  (16)
                    }
            DESCRIPTION
                 "tmnxL2tpApServAddrType supports only the InetAddressType value
                  'ipv4 (1)'."

        VARIATION   tmnxL2tpApServRowStatus
            SYNTAX  RowStatus {
                       active               (1),
                    -- notInService         (2)
                    -- notReady             (3)
                       createAndGo          (4),
                    -- createAndWait        (5)
                       destroy              (6)
                    }
            DESCRIPTION
                 "tmnxL2tpApServRowStatus supports only 'active (1)',
                  'createAndGo (4)', and 'destroy (6)'."

        VARIATION   tmnxL2tpApServerSrcAddr
            SYNTAX  InetAddress (SIZE(0|4))
            DESCRIPTION
                 "tmnxL2tpApServerSrcAddr only supports the values ''H and IPv4
                  addresses."

        VARIATION   tmnxL2tpApServerSrcAddrType
            SYNTAX  InetAddressType {
                       unknown              (0),
                       ipv4                 (1)
                    -- ipv6                 (2)
                    -- ipv4z                (3)
                    -- ipv6z                (4)
                    -- dns                  (16)
                    }
            DESCRIPTION
                 "tmnxL2tpApServerSrcAddrType supports only the InetAddressType
                  values 'unknown (0)' and 'ipv4 (1)'."

        VARIATION   tmnxL2tpLnsIfDefFilterProfile
            ACCESS  not-implemented
            DESCRIPTION
                 "tmnxL2tpLnsIfDefFilterProfile is not implemented on Nokia 7750
                  c4 in release 14.0."

        VARIATION   tmnxL2tpLnsIfDefSubIdent
            SYNTAX  INTEGER {
                    -- useSapId             (1)
                       useString            (2),
                       useAutoId            (3)
                    }
            DESCRIPTION
                 "tmnxL2tpLnsIfDefSubIdent only supports the value 'useString
                  (2)' and 'useAutoId (3)'."

        VARIATION   tmnxL2tpRowStatus
            SYNTAX  RowStatus {
                       active               (1),
                    -- notInService         (2)
                    -- notReady             (3)
                       createAndGo          (4),
                    -- createAndWait        (5)
                       destroy              (6)
                    }
            DESCRIPTION
                 "tmnxL2tpRowStatus supports only 'active (1)', 'createAndGo
                  (4)', and 'destroy (6)'."

        VARIATION   tmnxL2tpTgCfgAddr
            SYNTAX  InetAddress (SIZE(0|4))
            DESCRIPTION
                 "tmnxL2tpTgCfgAddr only supports the values ''H and IPv4
                  addresses."

        VARIATION   tmnxL2tpTgCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTgCfgAddrType supports only the InetAddressType values
                  'unknown (0)' and 'ipv4 (1)'."

        VARIATION   tmnxL2tpTgCfgAdminState
            SYNTAX  INTEGER {
                    -- noop                 (1)
                       inService            (2),
                       outOfService         (3)
                    }
            DESCRIPTION
                 "tmnxL2tpTgCfgAdminState supports only the values 'inService
                  (2)' and 'outOfService (3)'."

        VARIATION   tmnxL2tpTgCfgRowStatus
            SYNTAX  RowStatus {
                       active               (1),
                    -- notInService         (2)
                    -- notReady             (3)
                       createAndGo          (4),
                    -- createAndWait        (5)
                       destroy              (6)
                    }
            DESCRIPTION
                 "tmnxL2tpTgCfgRowStatus supports only 'active (1)',
                  'createAndGo (4)', and 'destroy (6)'."

        VARIATION   tmnxL2tpTgMlpppAdminState
            SYNTAX  INTEGER {
                    -- noop                 (1)
                       inService            (2),
                       outOfService         (3)
                    }
            DESCRIPTION
                 "tmnxL2tpTgMlpppAdminState supports only the values 'inService
                  (2)' and 'outOfService (3)'."

        VARIATION   tmnxL2tpTuCfgAddr
            SYNTAX  InetAddress (SIZE(0|4))
            DESCRIPTION
                 "tmnxL2tpTuCfgAddr only supports the values ''H and IPv4
                  addresses.

                  In case of a LAC tunnel, the only allowed value for this
                  object is ''H; the value used instead is the value of the
                  object vRiaInetAddress of the entry corresponding to the
                  system interface."

        VARIATION   tmnxL2tpTuCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgAddrType supports only the InetAddressType values
                  'unknown (0)' and 'ipv4 (1)'.

                  In case of a LAC tunnel, the only allowed value for this
                  object is 'unknown (0)'; the value used instead is the actual
                  value of the object vRiaInetAddressType of the entry
                  corresponding to the system interface."

        VARIATION   tmnxL2tpTuCfgAdminState
            SYNTAX  INTEGER {
                    -- noop                 (1)
                       inService            (2),
                       outOfService         (3)
                    }
            DESCRIPTION
                 "tmnxL2tpTuCfgAdminState supports only the values 'inService
                  (2)' and 'outOfService (3)'."

        VARIATION   tmnxL2tpTuCfgPeerAddr
            SYNTAX  InetAddress (SIZE(0|4))
            DESCRIPTION
                 "tmnxL2tpTuCfgPeerAddr only supports the values ''H and IPv4
                  addresses."

        VARIATION   tmnxL2tpTuCfgPeerAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgPeerAddrType supports only the InetAddressType
                  values 'unknown (0)' and 'ipv4 (1)'."

        VARIATION   tmnxL2tpTuCfgRowStatus
            SYNTAX  RowStatus {
                       active               (1),
                    -- notInService         (2)
                    -- notReady             (3)
                       createAndGo          (4),
                    -- createAndWait        (5)
                       destroy              (6)
                    }
            DESCRIPTION
                 "tmnxL2tpTuCfgRowStatus supports only 'active (1)',
                  'createAndGo (4)', and 'destroy (6)'."

        VARIATION   tmnxL2tpTuCfgSessionLimit
            SYNTAX  TmnxL2tpSessionLimit (1..65535)
            DESCRIPTION
                 "The number of sessions allowed for a tunnel is currently
                  limited to 65535.

                  The reason is that currently only L2TP version 2 is
                  supported, and version 2 uses a 16 bit number to identify a
                  session."

        VARIATION   tmnxL2tpV3TgPwCapList
            SYNTAX  BITS {
                       ethernet             (0)
                    -- ethernetVlan         (1)
                    }
            DESCRIPTION
                 "The only bit that can be modified in the tmnxL2tpV3TgPwCapList
                  object is 'ethernet (0)'."

    ::= { tmnx7750c4AgentV14v0  68 }

--
-- 7450 L2TP CAPABILITIES
--
tmnx7450L2tpV14v0                 AGENT-CAPABILITIES
    PRODUCT-RELEASE "Nokia SROS"
    STATUS          current
    DESCRIPTION
         "Implementation of the L2TP (Layer Two Tunneling Protocol) feature for
          Nokia 7450 systems release 14.0."

    SUPPORTS        TIMETRA-L2TP-MIB
        INCLUDES {
           tmnxL2tpAccountingGroup,
           tmnxL2tpAccountingV12v0Group,
           tmnxL2tpAccountingV13v0Group,
           tmnxL2tpCfgV14v0Group,
           tmnxL2tpCfgV8v0Group,
           tmnxL2tpDontFragmentBitLacGroup,
-- EXCLUDE tmnxL2tpFilterProfileV9v0Group
           tmnxL2tpLnsIfV9v0Group,
           tmnxL2tpLnsIsaGroup,
           tmnxL2tpLnsIsaStatGroup,
           tmnxL2tpLnsIsaStatV12v0Group,
           tmnxL2tpLnsIsaV10v0Group,
           tmnxL2tpLnsSeV9v0Group,
           tmnxL2tpLnsTgGroup,
           tmnxL2tpLnsTgV11v0Group,
           tmnxL2tpLnsTgV9v0Group,
           tmnxL2tpLnsTuGroup,
           tmnxL2tpLnsTuV11v0Group,
           tmnxL2tpLnsTuV9v0Group,
           tmnxL2tpMlpppGroup,
           tmnxL2tpMultiChassisGroup,
           tmnxL2tpNotifyGroup,
           tmnxL2tpNotifyObjsGroup,
           tmnxL2tpNotifyObjsV9v0Group,
           tmnxL2tpNotifyV10v0Group,
           tmnxL2tpNotifyV11v0Group,
           tmnxL2tpNotifyV9v0Group,
           tmnxL2tpPeerOpGroup,
           tmnxL2tpPeerStatV8v0Group,
           tmnxL2tpSeOpGroup,
           tmnxL2tpSeStatGroup,
           tmnxL2tpSeStatV14v0Group,
           tmnxL2tpStatV11v0Group,
           tmnxL2tpTgCfgGroup,
           tmnxL2tpTgOpGroup,
           tmnxL2tpTgStatGroup,
           tmnxL2tpTgStatV14v0Group,
           tmnxL2tpTgV10v0Group,
           tmnxL2tpTgV14v0Group,
           tmnxL2tpTuCfgGroup,
           tmnxL2tpTuOpGroup,
           tmnxL2tpTuStatGroup,
           tmnxL2tpTuStatV11v0Group,
           tmnxL2tpTuStatV14v0Group,
           tmnxL2tpTuV10v0Group,
           tmnxL2tpV11v0Group,
           tmnxL2tpV3SeStatV14v0Group,
           tmnxL2tpV3TgV14v0Group,
           tmnxL2tpV3V14v0Group
        }

        VARIATION   tmnxL2tpAdminState
            SYNTAX  INTEGER {
                    -- noop                 (1)
                       inService            (2),
                       outOfService         (3)
                    }
            DESCRIPTION
                 "tmnxL2tpAdminState supports only the values 'inService (2)'
                  and 'outOfService (3)'."

        VARIATION   tmnxL2tpApRowStatus
            SYNTAX  RowStatus {
                       active               (1),
                    -- notInService         (2)
                    -- notReady             (3)
                       createAndGo          (4),
                    -- createAndWait        (5)
                       destroy              (6)
                    }
            DESCRIPTION
                 "tmnxL2tpApRowStatus supports only 'active (1)', 'createAndGo
                  (4)', and 'destroy (6)'."

        VARIATION   tmnxL2tpApServAddr
            SYNTAX  InetAddress (SIZE(4))
            DESCRIPTION
                 "Only IPv4 addresses are allowed."

        VARIATION   tmnxL2tpApServAddrType
            SYNTAX  InetAddressType {
                    -- unknown              (0)
                       ipv4                 (1)
                    -- ipv6                 (2)
                    -- ipv4z                (3)
                    -- ipv6z                (4)
                    -- dns                  (16)
                    }
            DESCRIPTION
                 "tmnxL2tpApServAddrType supports only the InetAddressType value
                  'ipv4 (1)'."

        VARIATION   tmnxL2tpApServRowStatus
            SYNTAX  RowStatus {
                       active               (1),
                    -- notInService         (2)
                    -- notReady             (3)
                       createAndGo          (4),
                    -- createAndWait        (5)
                       destroy              (6)
                    }
            DESCRIPTION
                 "tmnxL2tpApServRowStatus supports only 'active (1)',
                  'createAndGo (4)', and 'destroy (6)'."

        VARIATION   tmnxL2tpApServerSrcAddr
            SYNTAX  InetAddress (SIZE(0|4))
            DESCRIPTION
                 "tmnxL2tpApServerSrcAddr only supports the values ''H and IPv4
                  addresses."

        VARIATION   tmnxL2tpApServerSrcAddrType
            SYNTAX  InetAddressType {
                       unknown              (0),
                       ipv4                 (1)
                    -- ipv6                 (2)
                    -- ipv4z                (3)
                    -- ipv6z                (4)
                    -- dns                  (16)
                    }
            DESCRIPTION
                 "tmnxL2tpApServerSrcAddrType supports only the InetAddressType
                  values 'unknown (0)' and 'ipv4 (1)'."

        VARIATION   tmnxL2tpIsaGrpAdminState
            SYNTAX  INTEGER {
                    -- noop                 (1)
                       inService            (2),
                       outOfService         (3)
                    }
            DESCRIPTION
                 "tmnxL2tpIsaGrpAdminState supports only the values 'inService
                  (2)' and 'outOfService (3)'."

        VARIATION   tmnxL2tpIsaGrpRowStatus
            SYNTAX  RowStatus {
                       active               (1),
                    -- notInService         (2)
                    -- notReady             (3)
                       createAndGo          (4),
                    -- createAndWait        (5)
                       destroy              (6)
                    }
            DESCRIPTION
                 "tmnxL2tpIsaGrpRowStatus supports only 'active (1)',
                  'createAndGo (4)', and 'destroy (6)'."

        VARIATION   tmnxL2tpIsaMdaRowStatus
            SYNTAX  RowStatus {
                       active               (1),
                    -- notInService         (2)
                    -- notReady             (3)
                       createAndGo          (4),
                    -- createAndWait        (5)
                       destroy              (6)
                    }
            DESCRIPTION
                 "tmnxL2tpIsaMdaRowStatus supports only 'active (1)',
                  'createAndGo (4)', and 'destroy (6)'."

        VARIATION   tmnxL2tpLnsIfDefFilterProfile
            ACCESS  not-implemented
            DESCRIPTION
                 "tmnxL2tpLnsIfDefFilterProfile is not implemented on Nokia 7450
                  in release 14.0."

        VARIATION   tmnxL2tpLnsIfDefSubIdent
            SYNTAX  INTEGER {
                    -- useSapId             (1)
                       useString            (2),
                       useAutoId            (3)
                    }
            DESCRIPTION
                 "tmnxL2tpLnsIfDefSubIdent only supports the value 'useString
                  (2)' and 'useAutoId (3)'."

        VARIATION   tmnxL2tpRowStatus
            SYNTAX  RowStatus {
                       active               (1),
                    -- notInService         (2)
                    -- notReady             (3)
                       createAndGo          (4),
                    -- createAndWait        (5)
                       destroy              (6)
                    }
            DESCRIPTION
                 "tmnxL2tpRowStatus supports only 'active (1)', 'createAndGo
                  (4)', and 'destroy (6)'."

        VARIATION   tmnxL2tpTgCfgAddr
            SYNTAX  InetAddress (SIZE(0|4))
            DESCRIPTION
                 "tmnxL2tpTgCfgAddr only supports the values ''H and IPv4
                  addresses."

        VARIATION   tmnxL2tpTgCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTgCfgAddrType supports only the InetAddressType values
                  'unknown (0)' and 'ipv4 (1)'."

        VARIATION   tmnxL2tpTgCfgAdminState
            SYNTAX  INTEGER {
                    -- noop                 (1)
                       inService            (2),
                       outOfService         (3)
                    }
            DESCRIPTION
                 "tmnxL2tpTgCfgAdminState supports only the values 'inService
                  (2)' and 'outOfService (3)'."

        VARIATION   tmnxL2tpTgCfgRowStatus
            SYNTAX  RowStatus {
                       active               (1),
                    -- notInService         (2)
                    -- notReady             (3)
                       createAndGo          (4),
                    -- createAndWait        (5)
                       destroy              (6)
                    }
            DESCRIPTION
                 "tmnxL2tpTgCfgRowStatus supports only 'active (1)',
                  'createAndGo (4)', and 'destroy (6)'."

        VARIATION   tmnxL2tpTgMlpppAdminState
            SYNTAX  INTEGER {
                    -- noop                 (1)
                       inService            (2),
                       outOfService         (3)
                    }
            DESCRIPTION
                 "tmnxL2tpTgMlpppAdminState supports only the values 'inService
                  (2)' and 'outOfService (3)'."

        VARIATION   tmnxL2tpTuCfgAddr
            SYNTAX  InetAddress (SIZE(0|4))
            DESCRIPTION
                 "tmnxL2tpTuCfgAddr only supports the values ''H and IPv4
                  addresses.

                  In case of a LAC tunnel, the only allowed value for this
                  object is ''H; the value used instead is the value of the
                  object vRiaInetAddress of the entry corresponding to the
                  system interface."

        VARIATION   tmnxL2tpTuCfgAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgAddrType supports only the InetAddressType values
                  'unknown (0)' and 'ipv4 (1)'.

                  In case of a LAC tunnel, the only allowed value for this
                  object is 'unknown (0)'; the value used instead is the actual
                  value of the object vRiaInetAddressType of the entry
                  corresponding to the system interface."

        VARIATION   tmnxL2tpTuCfgAdminState
            SYNTAX  INTEGER {
                    -- noop                 (1)
                       inService            (2),
                       outOfService         (3)
                    }
            DESCRIPTION
                 "tmnxL2tpTuCfgAdminState supports only the values 'inService
                  (2)' and 'outOfService (3)'."

        VARIATION   tmnxL2tpTuCfgPeerAddr
            SYNTAX  InetAddress (SIZE(0|4))
            DESCRIPTION
                 "tmnxL2tpTuCfgPeerAddr only supports the values ''H and IPv4
                  addresses."

        VARIATION   tmnxL2tpTuCfgPeerAddrType
            SYNTAX  InetAddressType {
                       unknown              (0),
                       ipv4                 (1)
                    -- ipv6                 (2)
                    -- ipv4z                (3)
                    -- ipv6z                (4)
                    -- dns                  (16)
                    }
            DESCRIPTION
                 "tmnxL2tpTuCfgPeerAddrType supports only the InetAddressType
                  values 'unknown (0)' and 'ipv4 (1)'."

        VARIATION   tmnxL2tpTuCfgRowStatus
            SYNTAX  RowStatus {
                       active               (1),
                    -- notInService         (2)
                    -- notReady             (3)
                       createAndGo          (4),
                    -- createAndWait        (5)
                       destroy              (6)
                    }
            DESCRIPTION
                 "tmnxL2tpTuCfgRowStatus supports only 'active (1)',
                  'createAndGo (4)', and 'destroy (6)'."

        VARIATION   tmnxL2tpTuCfgSessionLimit
            SYNTAX  TmnxL2tpSessionLimit (1..65535)
            DESCRIPTION
                 "The number of sessions allowed for a tunnel is currently
                  limited to 65535.

                  The reason is that currently only L2TP version 2 is
                  supported, and version 2 uses a 16 bit number to identify a
                  session."

        VARIATION   tmnxL2tpV3TgPwCapList
            SYNTAX  BITS {
                       ethernet             (0)
                    -- ethernetVlan         (1)
                    }
            DESCRIPTION
                 "The only bit that can be modified in the tmnxL2tpV3TgPwCapList
                  object is 'ethernet (0)'."

    ::= { tmnx7450AgentV14v0  68 }

--
-- SROS LAG CAPABILITIES
--
tmnxSROSLagV14v0                  AGENT-CAPABILITIES
    PRODUCT-RELEASE "Nokia SROS"
    STATUS          current
    DESCRIPTION
         "Implementation of Link Aggregation, LAG, capabilities for Nokia SROS
          systems release 14.0."

    SUPPORTS        IEEE8023-LAG-MIB
        INCLUDES {
           dot3adAggGroup,
-- EXCLUDE dot3adAggPortDebugGroup
           dot3adAggPortGroup,
-- EXCLUDE dot3adAggPortListGroup,
-- EXCLUDE dot3adAggPortStatsGroup,
           dot3adTablesLastChangedGroup
        }

        VARIATION   dot3adAggActorAdminKey
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia SROS in release 14.0."

        VARIATION   dot3adAggCollectorMaxDelay
            ACCESS  read-only
            DESCRIPTION
                 "dot3adAggCollectorMaxDelay is implemented as read-only on
                  Nokia SROS in release 14.0."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia SROS in release 14.0."

        VARIATION   dot3adAggPortActorAdminState
            ACCESS  read-only
            DESCRIPTION
                 "dot3adAggPortActorAdminState is implemented as read-only on
                  Nokia SROS in release 14.0."

        VARIATION   dot3adAggPortActorOperKey
            ACCESS  read-only
            DESCRIPTION
                 "dot3adAggPortActorOperKey is implemented as read-only on Nokia
                  SROS in release 14.0."

        VARIATION   dot3adAggPortActorSystemPriority
            ACCESS  read-only
            DESCRIPTION
                 "dot3adAggPortActorSystemPriority is implemented as read-only
                  on Nokia SROS in release 14.0."

        VARIATION   dot3adAggPortPartnerAdminKey
            ACCESS  read-only
            DESCRIPTION
                 "dot3adAggPortPartnerAdminKey is implemented as read-only on
                  Nokia SROS in release 14.0."

        VARIATION   dot3adAggPortPartnerAdminPort
            ACCESS  read-only
            DESCRIPTION
                 "dot3adAggPortPartnerAdminPort is implemented as read-only on
                  Nokia SROS in release 14.0."

        VARIATION   dot3adAggPortPartnerAdminPortPriority
            ACCESS  read-only
            DESCRIPTION
                 "dot3adAggPortPartnerAdminPortPriority is implemented as
                  read-only on Nokia SROS in release 14.0."

        VARIATION   dot3adAggPortPartnerAdminState
            ACCESS  read-only
            DESCRIPTION
                 "dot3adAggPortPartnerAdminState is implemented as read-only on
                  Nokia SROS in release 14.0."

        VARIATION   dot3adAggPortPartnerAdminSystemID
            ACCESS  read-only
            DESCRIPTION
                 "dot3adAggPortPartnerAdminSystemID is implemented as read-only
                  on Nokia SROS in release 14.0."

        VARIATION   dot3adAggPortPartnerAdminSystemPriority
            ACCESS  read-only
            DESCRIPTION
                 "dot3adAggPortPartnerAdminSystemPriority is implemented as
                  read-only on Nokia SROS in release 14.0."

        VARIATION   dot3adTablesLastChanged
            ACCESS  not-implemented
            DESCRIPTION
                 "dot3adTablesLastChanged is not implemented on Nokia SROS in
                  release 14.0."

    SUPPORTS        TIMETRA-LAG-MIB
        INCLUDES {
           tmnxLagAccessV14v0Group,
           tmnxLagBfdGroup,
           tmnxLagBfdNotifGroup,
           tmnxLagHsmdaV6v0Group,
           tmnxLagIndependentMuxGroup,
           tmnxLagInstanceV7v0Group,
           tmnxLagInstanceV9v0Group,
           tmnxLagMixed10g100gV12v0Group,
           tmnxLagPerFpSapV12v0Group,
           tmnxLagPerLinkHashV12v0Group,
           tmnxLagSelectionHoldV12v0Group,
           tmnxLagV10v0NotifGroup,
           tmnxLagV11v0Group,
           tmnxLagV13v0Group,
           tmnxLagV6v0NotifGroup,
           tmnxLagV8v0Group
        }

        VARIATION   tLagAccessAdaptQos
            DESCRIPTION
                 "The default value for tLagAccessAdaptQos varies based on the
                  MDA type. For an HS-MDA, the default value is 'link (1)'."

        VARIATION   tLagRowStatus
            SYNTAX  RowStatus {
                       active               (1),
                    -- notInService         (2)
                    -- notReady             (3)
                       createAndGo          (4),
                    -- createAndWait        (5)
                       destroy              (6)
                    }
            DESCRIPTION
                 "tLagRowStatus supports only 'active (1)', 'createAndGo (4)',
                  and 'destroy (6)'."

    ::= { tmnxSROSAgentV14v0  22 }

--
-- 7750SR-1 LAG CAPABILITIES
--
tmnx7750SR1LagV14v0               AGENT-CAPABILITIES
    PRODUCT-RELEASE "Nokia SROS"
    STATUS          current
    DESCRIPTION
         "Implementation of Link Aggregation, LAG, capabilities for Nokia 7750
          SR-1 systems release 14.0."

    SUPPORTS        IEEE8023-LAG-MIB
        INCLUDES {
           dot3adAggGroup,
-- EXCLUDE dot3adAggPortDebugGroup
           dot3adAggPortGroup,
-- EXCLUDE dot3adAggPortListGroup,
-- EXCLUDE dot3adAggPortStatsGroup,
           dot3adTablesLastChangedGroup
        }

        VARIATION   dot3adAggActorAdminKey
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia 7750 SR-1 in release 14.0."

        VARIATION   dot3adAggCollectorMaxDelay
            ACCESS  read-only
            DESCRIPTION
                 "dot3adAggCollectorMaxDelay is implemented as read-only on
                  Nokia 7750 SR-1 in release 14.0."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia 7750 SR-1 in release 14.0."

        VARIATION   dot3adAggPortActorAdminState
            ACCESS  read-only
            DESCRIPTION
                 "dot3adAggPortActorAdminState is implemented as read-only on
                  Nokia 7750 SR-1 in release 14.0."

        VARIATION   dot3adAggPortActorOperKey
            ACCESS  read-only
            DESCRIPTION
                 "dot3adAggPortActorOperKey is implemented as read-only on Nokia
                  7750 SR-1 in release 14.0."

        VARIATION   dot3adAggPortActorSystemPriority
            ACCESS  read-only
            DESCRIPTION
                 "dot3adAggPortActorSystemPriority is implemented as read-only
                  on Nokia 7750 SR-1 in release 14.0."

        VARIATION   dot3adAggPortPartnerAdminKey
            ACCESS  read-only
            DESCRIPTION
                 "dot3adAggPortPartnerAdminKey is implemented as read-only on
                  Nokia 7750 SR-1 in release 14.0."

        VARIATION   dot3adAggPortPartnerAdminPort
            ACCESS  read-only
            DESCRIPTION
                 "dot3adAggPortPartnerAdminPort is implemented as read-only on
                  Nokia 7750 SR-1 in release 14.0."

        VARIATION   dot3adAggPortPartnerAdminPortPriority
            ACCESS  read-only
            DESCRIPTION
                 "dot3adAggPortPartnerAdminPortPriority is implemented as
                  read-only on Nokia 7750 SR-1 in release 14.0."

        VARIATION   dot3adAggPortPartnerAdminState
            ACCESS  read-only
            DESCRIPTION
                 "dot3adAggPortPartnerAdminState is implemented as read-only on
                  Nokia 7750 SR-1 in release 14.0."

        VARIATION   dot3adAggPortPartnerAdminSystemID
            ACCESS  read-only
            DESCRIPTION
                 "dot3adAggPortPartnerAdminSystemID is implemented as read-only
                  on Nokia 7750 SR-1 in release 14.0."

        VARIATION   dot3adAggPortPartnerAdminSystemPriority
            ACCESS  read-only
            DESCRIPTION
                 "dot3adAggPortPartnerAdminSystemPriority is implemented as
                  read-only on Nokia 7750 SR-1 in release 14.0."

        VARIATION   dot3adTablesLastChanged
            ACCESS  not-implemented
            DESCRIPTION
                 "dot3adTablesLastChanged is not implemented on Nokia 7750 SR-1
                  in release 14.0."

    SUPPORTS        TIMETRA-LAG-MIB
        INCLUDES {
           tmnxLagAccessV14v0Group,
-- EXCLUDE tmnxLagBfdGroup
-- EXCLUDE tmnxLagBfdNotifGroup
           tmnxLagHsmdaV6v0Group,
           tmnxLagIndependentMuxGroup,
           tmnxLagInstanceV7v0Group,
           tmnxLagInstanceV9v0Group,
           tmnxLagMixed10g100gV12v0Group,
           tmnxLagPerFpSapV12v0Group,
           tmnxLagPerLinkHashV12v0Group,
           tmnxLagSelectionHoldV12v0Group,
           tmnxLagV10v0NotifGroup,
           tmnxLagV11v0Group,
           tmnxLagV13v0Group,
           tmnxLagV6v0NotifGroup,
           tmnxLagV8v0Group
        }

        VARIATION   tLagAccessAdaptQos
            DESCRIPTION
                 "The default value for tLagAccessAdaptQos varies based on the
                  MDA type. For an HS-MDA, the default value is 'link (1)'."

        VARIATION   tLagRowStatus
            SYNTAX  RowStatus {
                       active               (1),
                    -- notInService         (2)
                    -- notReady             (3)
                       createAndGo          (4),
                    -- createAndWait        (5)
                       destroy              (6)
                    }
            DESCRIPTION
                 "tLagRowStatus supports only 'active (1)', 'createAndGo (4)',
                  and 'destroy (6)'."

    ::= { tmnx7750SR1AgentV14v0  22 }

--
-- 7750c12 LAG CAPABILITIES
--
tmnx7750c12LagV14v0               AGENT-CAPABILITIES
    PRODUCT-RELEASE "Nokia SROS"
    STATUS          current
    DESCRIPTION
         "Implementation of Link Aggregation, LAG, capabilities for Nokia 7750
          c12 systems release 14.0."

    SUPPORTS        IEEE8023-LAG-MIB
        INCLUDES {
           dot3adAggGroup,
-- EXCLUDE dot3adAggPortDebugGroup
           dot3adAggPortGroup,
-- EXCLUDE dot3adAggPortListGroup,
-- EXCLUDE dot3adAggPortStatsGroup,
           dot3adTablesLastChangedGroup
        }

        VARIATION   dot3adAggActorAdminKey
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia 7750 c12 in release 14.0."

        VARIATION   dot3adAggCollectorMaxDelay
            ACCESS  read-only
            DESCRIPTION
                 "dot3adAggCollectorMaxDelay is implemented as read-only on
                  Nokia 7750 c12 in release 14.0."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia 7750 c12 in release 14.0."

        VARIATION   dot3adAggPortActorAdminState
            ACCESS  read-only
            DESCRIPTION
                 "dot3adAggPortActorAdminState is implemented as read-only on
                  Nokia 7750 c12 in release 14.0."

        VARIATION   dot3adAggPortActorOperKey
            ACCESS  read-only
            DESCRIPTION
                 "dot3adAggPortActorOperKey is implemented as read-only on Nokia
                  7750 c12 in release 14.0."

        VARIATION   dot3adAggPortActorSystemPriority
            ACCESS  read-only
            DESCRIPTION
                 "dot3adAggPortActorSystemPriority is implemented as read-only
                  on Nokia 7750 c12 in release 14.0."

        VARIATION   dot3adAggPortPartnerAdminKey
            ACCESS  read-only
            DESCRIPTION
                 "dot3adAggPortPartnerAdminKey is implemented as read-only on
                  Nokia 7750 c12 in release 14.0."

        VARIATION   dot3adAggPortPartnerAdminPort
            ACCESS  read-only
            DESCRIPTION
                 "dot3adAggPortPartnerAdminPort is implemented as read-only on
                  Nokia 7750 c12 in release 14.0."

        VARIATION   dot3adAggPortPartnerAdminPortPriority
            ACCESS  read-only
            DESCRIPTION
                 "dot3adAggPortPartnerAdminPortPriority is implemented as
                  read-only on Nokia 7750 c12 in release 14.0."

        VARIATION   dot3adAggPortPartnerAdminState
            ACCESS  read-only
            DESCRIPTION
                 "dot3adAggPortPartnerAdminState is implemented as read-only on
                  Nokia 7750 c12 in release 14.0."

        VARIATION   dot3adAggPortPartnerAdminSystemID
            ACCESS  read-only
            DESCRIPTION
                 "dot3adAggPortPartnerAdminSystemID is implemented as read-only
                  on Nokia 7750 c12 in release 14.0."

        VARIATION   dot3adAggPortPartnerAdminSystemPriority
            ACCESS  read-only
            DESCRIPTION
                 "dot3adAggPortPartnerAdminSystemPriority is implemented as
                  read-only on Nokia 7750 c12 in release 14.0."

        VARIATION   dot3adTablesLastChanged
            ACCESS  not-implemented
            DESCRIPTION
                 "dot3adTablesLastChanged is not implemented on Nokia 7750 c12
                  in release 14.0."

    SUPPORTS        TIMETRA-LAG-MIB
        INCLUDES {
           tmnxLagAccessV14v0Group,
           tmnxLagBfdGroup,
           tmnxLagBfdNotifGroup,
-- EXCLUDE tmnxLagHsmdaV6v0Group
           tmnxLagIndependentMuxGroup,
           tmnxLagInstanceV7v0Group,
           tmnxLagInstanceV9v0Group,
           tmnxLagMixed10g100gV12v0Group,
           tmnxLagPerFpSapV12v0Group,
           tmnxLagPerLinkHashV12v0Group,
           tmnxLagSelectionHoldV12v0Group,
           tmnxLagV10v0NotifGroup,
           tmnxLagV11v0Group,
           tmnxLagV13v0Group,
           tmnxLagV6v0NotifGroup,
           tmnxLagV8v0Group
        }

        VARIATION   tLagAccessAdaptQos
            DESCRIPTION
                 "The default value for tLagAccessAdaptQos varies based on the
                  MDA type. For an HS-MDA, the default value is 'link (1)'."

        VARIATION   tLagPortType
            SYNTAX  INTEGER {
                       standard             (1),
                    -- hsmda                (2)
                       hsmdaV2              (3)
                    }
            DESCRIPTION
                 "tLagPortType value of 'hsmda (2)' is not supported."

        VARIATION   tLagRowStatus
            SYNTAX  RowStatus {
                       active               (1),
                    -- notInService         (2)
                    -- notReady             (3)
                       createAndGo          (4),
                    -- createAndWait        (5)
                       destroy              (6)
                    }
            DESCRIPTION
                 "tLagRowStatus supports only 'active (1)', 'createAndGo (4)',
                  and 'destroy (6)'."

    ::= { tmnx7750c12AgentV14v0  22 }

--
-- 7750c4 LAG CAPABILITIES
--
tmnx7750c4LagV14v0                AGENT-CAPABILITIES
    PRODUCT-RELEASE "Nokia SROS"
    STATUS          current
    DESCRIPTION
         "Implementation of Link Aggregation, LAG, capabilities for Nokia 7750
          c4 systems release 14.0."

    SUPPORTS        IEEE8023-LAG-MIB
        INCLUDES {
           dot3adAggGroup,
-- EXCLUDE dot3adAggPortDebugGroup
           dot3adAggPortGroup,
-- EXCLUDE dot3adAggPortListGroup,
-- EXCLUDE dot3adAggPortStatsGroup,
           dot3adTablesLastChangedGroup
        }

        VARIATION   dot3adAggActorAdminKey
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia 7750 c4 in release 14.0."

        VARIATION   dot3adAggCollectorMaxDelay
            ACCESS  read-only
            DESCRIPTION
                 "dot3adAggCollectorMaxDelay is implemented as read-only on
                  Nokia 7750 c4 in release 14.0."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia 7750 c4 in release 14.0."

        VARIATION   dot3adAggPortActorAdminState
            ACCESS  read-only
            DESCRIPTION
                 "dot3adAggPortActorAdminState is implemented as read-only on
                  Nokia 7750 c4 in release 14.0."

        VARIATION   dot3adAggPortActorOperKey
            ACCESS  read-only
            DESCRIPTION
                 "dot3adAggPortActorOperKey is implemented as read-only on Nokia
                  7750 c4 in release 14.0."

        VARIATION   dot3adAggPortActorSystemPriority
            ACCESS  read-only
            DESCRIPTION
                 "dot3adAggPortActorSystemPriority is implemented as read-only
                  on Nokia 7750 c4 in release 14.0."

        VARIATION   dot3adAggPortPartnerAdminKey
            ACCESS  read-only
            DESCRIPTION
                 "dot3adAggPortPartnerAdminKey is implemented as read-only on
                  Nokia 7750 c4 in release 14.0."

        VARIATION   dot3adAggPortPartnerAdminPort
            ACCESS  read-only
            DESCRIPTION
                 "dot3adAggPortPartnerAdminPort is implemented as read-only on
                  Nokia 7750 c4 in release 14.0."

        VARIATION   dot3adAggPortPartnerAdminPortPriority
            ACCESS  read-only
            DESCRIPTION
                 "dot3adAggPortPartnerAdminPortPriority is implemented as
                  read-only on Nokia 7750 c4 in release 14.0."

        VARIATION   dot3adAggPortPartnerAdminState
            ACCESS  read-only
            DESCRIPTION
                 "dot3adAggPortPartnerAdminState is implemented as read-only on
                  Nokia 7750 c4 in release 14.0."

        VARIATION   dot3adAggPortPartnerAdminSystemID
            ACCESS  read-only
            DESCRIPTION
                 "dot3adAggPortPartnerAdminSystemID is implemented as read-only
                  on Nokia 7750 c4 in release 14.0."

        VARIATION   dot3adAggPortPartnerAdminSystemPriority
            ACCESS  read-only
            DESCRIPTION
                 "dot3adAggPortPartnerAdminSystemPriority is implemented as
                  read-only on Nokia 7750 c4 in release 14.0."

        VARIATION   dot3adTablesLastChanged
            ACCESS  not-implemented
            DESCRIPTION
                 "dot3adTablesLastChanged is not implemented on Nokia 7750 c4 in
                  release 14.0."

    SUPPORTS        TIMETRA-LAG-MIB
        INCLUDES {
           tmnxLagAccessV14v0Group,
           tmnxLagBfdGroup,
           tmnxLagBfdNotifGroup,
-- EXCLUDE tmnxLagHsmdaV6v0Group
           tmnxLagIndependentMuxGroup,
           tmnxLagInstanceV7v0Group,
           tmnxLagInstanceV9v0Group,
           tmnxLagMixed10g100gV12v0Group,
           tmnxLagPerFpSapV12v0Group,
           tmnxLagPerLinkHashV12v0Group,
           tmnxLagSelectionHoldV12v0Group,
           tmnxLagV10v0NotifGroup,
           tmnxLagV11v0Group,
           tmnxLagV13v0Group,
           tmnxLagV6v0NotifGroup,
           tmnxLagV8v0Group
        }

        VARIATION   tLagAccessAdaptQos
            DESCRIPTION
                 "The default value for tLagAccessAdaptQos varies based on the
                  MDA type. For an HS-MDA, the default value is 'link (1)'."

        VARIATION   tLagPortType
            SYNTAX  INTEGER {
                       standard             (1),
                    -- hsmda                (2)
                       hsmdaV2              (3)
                    }
            DESCRIPTION
                 "tLagPortType value of 'hsmda (2)' is not supported."

        VARIATION   tLagRowStatus
            SYNTAX  RowStatus {
                       active               (1),
                    -- notInService         (2)
                    -- notReady             (3)
                       createAndGo          (4),
                    -- createAndWait        (5)
                       destroy              (6)
                    }
            DESCRIPTION
                 "tLagRowStatus supports only 'active (1)', 'createAndGo (4)',
                  and 'destroy (6)'."

    ::= { tmnx7750c4AgentV14v0  22 }

--
-- 7450ESS-1 LAG CAPABILITIES
--
tmnx7450ESS1LagV14v0              AGENT-CAPABILITIES
    PRODUCT-RELEASE "Nokia SROS"
    STATUS          current
    DESCRIPTION
         "Implementation of Link Aggregation, LAG, capabilities for Nokia 7450
          ESS-1 systems release 14.0."

    SUPPORTS        IEEE8023-LAG-MIB
        INCLUDES {
           dot3adAggGroup,
-- EXCLUDE dot3adAggPortDebugGroup
           dot3adAggPortGroup,
-- EXCLUDE dot3adAggPortListGroup,
-- EXCLUDE dot3adAggPortStatsGroup,
           dot3adTablesLastChangedGroup
        }

        VARIATION   dot3adAggActorAdminKey
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia 7450 ESS-1 in release 14.0."

        VARIATION   dot3adAggCollectorMaxDelay
            ACCESS  read-only
            DESCRIPTION
                 "dot3adAggCollectorMaxDelay is implemented as read-only on
                  Nokia 7450 ESS-1 in release 14.0."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia 7450 ESS-1 in release 14.0."

        VARIATION   dot3adAggPortActorAdminState
            ACCESS  read-only
            DESCRIPTION
                 "dot3adAggPortActorAdminState is implemented as read-only on
                  Nokia 7450 ESS-1 in release 14.0."

        VARIATION   dot3adAggPortActorOperKey
            ACCESS  read-only
            DESCRIPTION
                 "dot3adAggPortActorOperKey is implemented as read-only on Nokia
                  7450 ESS-1 in release 14.0."

        VARIATION   dot3adAggPortActorSystemPriority
            ACCESS  read-only
            DESCRIPTION
                 "dot3adAggPortActorSystemPriority is implemented as read-only
                  on Nokia 7450 ESS-1 in release 14.0."

        VARIATION   dot3adAggPortPartnerAdminKey
            ACCESS  read-only
            DESCRIPTION
                 "dot3adAggPortPartnerAdminKey is implemented as read-only on
                  Nokia 7450 ESS-1 in release 14.0."

        VARIATION   dot3adAggPortPartnerAdminPort
            ACCESS  read-only
            DESCRIPTION
                 "dot3adAggPortPartnerAdminPort is implemented as read-only on
                  Nokia 7450 ESS-1 in release 14.0."

        VARIATION   dot3adAggPortPartnerAdminPortPriority
            ACCESS  read-only
            DESCRIPTION
                 "dot3adAggPortPartnerAdminPortPriority is implemented as
                  read-only on Nokia 7450 ESS-1 in release 14.0."

        VARIATION   dot3adAggPortPartnerAdminState
            ACCESS  read-only
            DESCRIPTION
                 "dot3adAggPortPartnerAdminState is implemented as read-only on
                  Nokia 7450 ESS-1 in release 14.0."

        VARIATION   dot3adAggPortPartnerAdminSystemID
            ACCESS  read-only
            DESCRIPTION
                 "dot3adAggPortPartnerAdminSystemID is implemented as read-only
                  on Nokia 7450 ESS-1 in release 14.0."

        VARIATION   dot3adAggPortPartnerAdminSystemPriority
            ACCESS  read-only
            DESCRIPTION
                 "dot3adAggPortPartnerAdminSystemPriority is implemented as
                  read-only on Nokia 7450 ESS-1 in release 14.0."

        VARIATION   dot3adTablesLastChanged
            ACCESS  not-implemented
            DESCRIPTION
                 "dot3adTablesLastChanged is not implemented on Nokia 7450 ESS-1
                  in release 14.0."

    SUPPORTS        TIMETRA-LAG-MIB
        INCLUDES {
           tmnxLagAccessV14v0Group,
-- EXCLUDE tmnxLagBfdGroup
-- EXCLUDE tmnxLagBfdNotifGroup
           tmnxLagHsmdaV6v0Group,
           tmnxLagIndependentMuxGroup,
           tmnxLagInstanceV7v0Group,
           tmnxLagInstanceV9v0Group,
           tmnxLagMixed10g100gV12v0Group,
           tmnxLagPerFpSapV12v0Group,
           tmnxLagPerLinkHashV12v0Group,
           tmnxLagSelectionHoldV12v0Group,
           tmnxLagV10v0NotifGroup,
           tmnxLagV11v0Group,
           tmnxLagV13v0Group,
           tmnxLagV6v0NotifGroup,
           tmnxLagV8v0Group
        }

        VARIATION   tLagAccessAdaptQos
            DESCRIPTION
                 "The default value for tLagAccessAdaptQos varies based on the
                  MDA type. For an HS-MDA, the default value is 'link (1)'."

        VARIATION   tLagRowStatus
            SYNTAX  RowStatus {
                       active               (1),
                    -- notInService         (2)
                    -- notReady             (3)
                       createAndGo          (4),
                    -- createAndWait        (5)
                       destroy              (6)
                    }
            DESCRIPTION
                 "tLagRowStatus supports only 'active (1)', 'createAndGo (4)',
                  and 'destroy (6)'."

    ::= { tmnx7450ESS1AgentV14v0  22 }

--
-- 7710 LAG CAPABILITIES
--
tmnx7710LagV14v0                  AGENT-CAPABILITIES
    PRODUCT-RELEASE "Nokia SROS"
    STATUS          current
    DESCRIPTION
         "Implementation of Link Aggregation, LAG, capabilities for Nokia 7710
          systems release 14.0."

    SUPPORTS        IEEE8023-LAG-MIB
        INCLUDES {
           dot3adAggGroup,
-- EXCLUDE dot3adAggPortDebugGroup
           dot3adAggPortGroup,
-- EXCLUDE dot3adAggPortListGroup,
-- EXCLUDE dot3adAggPortStatsGroup,
           dot3adTablesLastChangedGroup
        }

        VARIATION   dot3adAggActorAdminKey
            DESCRIPTION
                 "The value of dot3adAggActorAdminKey cannot be changed after
                  the row entry has been created. A set to the same value
                  succeeds."

        VARIATION   dot3adAggActorSystemPriority
            ACCESS  read-only
            DESCRIPTION
                 "dot3adAggActorSystemPriority is implemented as read-only on
                  Nokia 7710 in release 14.0."

        VARIATION   dot3adAggCollectorMaxDelay
            ACCESS  read-only
            DESCRIPTION
                 "dot3adAggCollectorMaxDelay is implemented as read-only on
                  Nokia 7710 in release 14.0."

        VARIATION   dot3adAggEntry
            CREATION-REQUIRES {
                       tLagRowStatus
                    }
            DESCRIPTION
                 "An entry in the dot3adAggTable is created when an entry is
                  created in the tLagConfigTable in TIMETRA-LAG-MIB."

        VARIATION   dot3adAggPortActorAdminKey
            ACCESS  read-only
            DESCRIPTION
                 "dot3adAggPortActorAdminKey is implemented as read-only on
                  Nokia 7710 in release 14.0."

        VARIATION   dot3adAggPortActorAdminState
            ACCESS  read-only
            DESCRIPTION
                 "dot3adAggPortActorAdminState is implemented as read-only on
                  Nokia 7710 in release 14.0."

        VARIATION   dot3adAggPortActorOperKey
            ACCESS  read-only
            DESCRIPTION
                 "dot3adAggPortActorOperKey is implemented as read-only on Nokia
                  7710 in release 14.0."

        VARIATION   dot3adAggPortActorSystemPriority
            ACCESS  read-only
            DESCRIPTION
                 "dot3adAggPortActorSystemPriority is implemented as read-only
                  on Nokia 7710 in release 14.0."

        VARIATION   dot3adAggPortPartnerAdminKey
            ACCESS  read-only
            DESCRIPTION
                 "dot3adAggPortPartnerAdminKey is implemented as read-only on
                  Nokia 7710 in release 14.0."

        VARIATION   dot3adAggPortPartnerAdminPort
            ACCESS  read-only
            DESCRIPTION
                 "dot3adAggPortPartnerAdminPort is implemented as read-only on
                  Nokia 7710 in release 14.0."

        VARIATION   dot3adAggPortPartnerAdminPortPriority
            ACCESS  read-only
            DESCRIPTION
                 "dot3adAggPortPartnerAdminPortPriority is implemented as
                  read-only on Nokia 7710 in release 14.0."

        VARIATION   dot3adAggPortPartnerAdminState
            ACCESS  read-only
            DESCRIPTION
                 "dot3adAggPortPartnerAdminState is implemented as read-only on
                  Nokia 7710 in release 14.0."

        VARIATION   dot3adAggPortPartnerAdminSystemID
            ACCESS  read-only
            DESCRIPTION
                 "dot3adAggPortPartnerAdminSystemID is implemented as read-only
                  on Nokia 7710 in release 14.0."

        VARIATION   dot3adAggPortPartnerAdminSystemPriority
            ACCESS  read-only
            DESCRIPTION
                 "dot3adAggPortPartnerAdminSystemPriority is implemented as
                  read-only on Nokia 7710 in release 14.0."

        VARIATION   dot3adTablesLastChanged
            ACCESS  not-implemented
            DESCRIPTION
                 "dot3adTablesLastChanged is not implemented on Nokia 7710 in
                  release 14.0."

    SUPPORTS        TIMETRA-LAG-MIB
        INCLUDES {
           tmnxLagAccessV14v0Group,
-- EXCLUDE tmnxLagBfdGroup
-- EXCLUDE tmnxLagBfdNotifGroup
-- EXCLUDE tmnxLagHsmdaV6v0Group
           tmnxLagIndependentMuxGroup,
           tmnxLagInstanceV7v0Group,
           tmnxLagInstanceV9v0Group,
           tmnxLagMixed10g100gV12v0Group,
           tmnxLagPerFpSapV12v0Group,
           tmnxLagPerLinkHashV12v0Group,
           tmnxLagSelectionHoldV12v0Group,
           tmnxLagV10v0NotifGroup,
           tmnxLagV11v0Group,
           tmnxLagV13v0Group,
           tmnxLagV6v0NotifGroup,
           tmnxLagV8v0Group
        }

        VARIATION   tLagAccessAdaptQos
            DESCRIPTION
                 "The default value for tLagAccessAdaptQos varies based on the
                  MDA type. For an HS-MDA, the default value is 'link (1)'."

        VARIATION   tLagPortType
            SYNTAX  INTEGER {
                       standard             (1),
                    -- hsmda                (2)
                       hsmdaV2              (3)
                    }
            DESCRIPTION
                 "tLagPortType value of 'hsmda (2)' is not supported."

        VARIATION   tLagRowStatus
            SYNTAX  RowStatus {
                       active               (1),
                    -- notInService         (2)
                    -- notReady             (3)
                       createAndGo          (4),
                    -- createAndWait        (5)
                       destroy              (6)
                    }
            DESCRIPTION
                 "tLagRowStatus supports only 'active (1)', 'createAndGo (4)',
                  and 'destroy (6)'."

    ::= { tmnx7710AgentV14v0  22 }

--
-- SROS LDAP CAPABILITIES
--
tmnxSROSLdapV14v0                 AGENT-CAPABILITIES
    PRODUCT-RELEASE "Nokia SROS"
    STATUS          current
    DESCRIPTION
         "Implementation of LDAP capabilities for Nokia SROS systems release
          14.0."

    SUPPORTS        TIMETRA-LDAP-MIB
        INCLUDES {
           tmnxLdapInitialGroup,
           tmnxLdapNotifyGroup
        }

        VARIATION   tmnxLdapServerInetAddressType
            SYNTAX  InetAddressType {
                       unknown              (0),
                       ipv4                 (1),
                       ipv6                 (2)
                    -- ipv4z                (3)
                    -- ipv6z                (4)
                    -- dns                  (16)
                    }
            DESCRIPTION
                 "tmnxLdapServerInetAddressType supports only the
                  InetAddressType values 'unknown (0)', 'ipv4 (1)', and 'ipv6
                  (2)'."

        VARIATION   tmnxLdapServerRowStatus
            SYNTAX  RowStatus {
                       active               (1),
                    -- notInService         (2)
                    -- notReady             (3)
                       createAndGo          (4),
                    -- createAndWait        (5)
                       destroy              (6)
                    }
            DESCRIPTION
                 "tmnxLdapServerRowStatus supports only 'active (1)',
                  'createAndGo (4)', and 'destroy (6)'."

    ::= { tmnxSROSAgentV14v0  97 }

--
-- SROS LDP CAPABILITIES
--
tmnxSROSLdpV14v0                  AGENT-CAPABILITIES
    PRODUCT-RELEASE "Nokia SROS"
    STATUS          current
    DESCRIPTION
         "Implementation of LDP capabilities for Nokia SROS systems release
          14.0."

    SUPPORTS        MPLS-LDP-MIB
        INCLUDES {
-- EXCLUDE mplsLdpAtmGroup
-- EXCLUDE mplsLdpFrameRelayGroup
           mplsLdpGeneralGroup,
-- EXCLUDE mplsLdpGenericGroup
-- EXCLUDE mplsLdpMappingGroup
           mplsLdpNotificationsGroup
        }

        VARIATION   mplsFecIndexNext
            ACCESS  not-implemented
            DESCRIPTION
                 "mplsFecIndexNext is not implemented on Nokia SROS in release
                  14.0."

        VARIATION   mplsFecTable
            ACCESS  not-implemented
            DESCRIPTION
                 "mplsFecTable is not implemented on Nokia SROS in release
                  14.0."

        VARIATION   mplsLdpAttemptedSessions
            ACCESS  not-implemented
            DESCRIPTION
                 "The mplsLdpAttemptedSessions is not supported. It is
                  implemented through vRtrLdpStatsAttemptedSessions in
                  TIMETRA-LDP-MIB."

        VARIATION   mplsLdpBadLdpIdentifierErrors
            ACCESS  not-implemented
            DESCRIPTION
                 "The mplsLdpBadLdpIdentifierErrors is not supported. It is
                  implemented through vRtrLdpStatsBadLdpIdentifierErrors in
                  TIMETRA-LDP-MIB."

        VARIATION   mplsLdpBadMessageLengthErrors
            ACCESS  not-implemented
            DESCRIPTION
                 "The mplsLdpBadMessageLengthErrors is not supported. It is
                  implemented through vRtrLdpStatsBadMessageLengthErrors in
                  TIMETRA-LDP-MIB."

        VARIATION   mplsLdpBadPduLengthErrors
            ACCESS  not-implemented
            DESCRIPTION
                 "The mplsLdpBadPduLengthErrors is not supported. It is
                  implemented through vRtrLdpStatsBadPduLengthErrors in
                  TIMETRA-LDP-MIB."

        VARIATION   mplsLdpBadTlvLengthErrors
            ACCESS  not-implemented
            DESCRIPTION
                 "The mplsLdpBadTlvLengthErrors is not supported. It is
                  implemented through vRtrLdpStatsBadTlvLengthErrors in
                  TIMETRA-LDP-MIB."

        VARIATION   mplsLdpEntityAdminStatus
            ACCESS  read-only
            DESCRIPTION
                 "mplsLdpEntityAdminStatus is implemented as read-only on Nokia
                  SROS in release 14.0.

                  The mplsLdpEntityTable is implemented as read-only."

        VARIATION   mplsLdpEntityEntry
            CREATION-REQUIRES {
                       vRtrLdpStatus
                    }
            DESCRIPTION
                 "Row entries cannot be created by SNMP SET requests.

                  Row entries in the mplsLdpEntityTable are created by setting
                  TIMETRA-VRTR-MIB::vRtrLdpStatus to 'create'."

        VARIATION   mplsLdpEntityFailedInitSessionThreshold
            ACCESS  read-only
            DESCRIPTION
                 "mplsLdpEntityFailedInitSessionThreshold is implemented as
                  read-only on Nokia SROS in release 14.0.

                  The mplsLdpEntityTable is implemented as read-only."

        VARIATION   mplsLdpEntityFailedInitSessionTrapEnable
            ACCESS  read-only
            DESCRIPTION
                 "mplsLdpEntityFailedInitSessionTrapEnable is implemented as
                  read-only on Nokia SROS in release 14.0.

                  The mplsLdpEntityTable is implemented as read-only."

        VARIATION   mplsLdpEntityHelloHoldTimer
            ACCESS  read-only
            DESCRIPTION
                 "mplsLdpEntityHelloHoldTimer is implemented as read-only on
                  Nokia SROS in release 14.0.

                  The mplsLdpEntityTable is implemented as read-only."

        VARIATION   mplsLdpEntityHopCountLimit
            ACCESS  read-only
            DESCRIPTION
                 "mplsLdpEntityHopCountLimit is implemented as read-only on
                  Nokia SROS in release 14.0.

                  The mplsLdpEntityTable is implemented as read-only."

        VARIATION   mplsLdpEntityIndexNext
            ACCESS  not-implemented
            DESCRIPTION
                 "The mplsLdpEntityTable is implemented as read-only. Row
                  entries cannot be created by SNMP SET requests. LDP Entities
                  are created in TIMETRA-LDP-MIB."

        VARIATION   mplsLdpEntityKeepAliveHoldTimer
            ACCESS  read-only
            DESCRIPTION
                 "mplsLdpEntityKeepAliveHoldTimer is implemented as read-only on
                  Nokia SROS in release 14.0.

                  The mplsLdpEntityTable is implemented as read-only."

        VARIATION   mplsLdpEntityLabelDistributionMethod
            ACCESS  read-only
            DESCRIPTION
                 "mplsLdpEntityLabelDistributionMethod is implemented as
                  read-only on Nokia SROS in release 14.0.

                  The mplsLdpEntityTable is implemented as read-only."

        VARIATION   mplsLdpEntityLabelRetentionMode
            ACCESS  read-only
            DESCRIPTION
                 "mplsLdpEntityLabelRetentionMode is implemented as read-only on
                  Nokia SROS in release 14.0.

                  The mplsLdpEntityTable is implemented as read-only."

        VARIATION   mplsLdpEntityMaxPduLength
            ACCESS  read-only
            DESCRIPTION
                 "mplsLdpEntityMaxPduLength is implemented as read-only on Nokia
                  SROS in release 14.0.

                  The mplsLdpEntityTable is implemented as read-only."

        VARIATION   mplsLdpEntityOptionalParameters
            ACCESS  read-only
            DESCRIPTION
                 "mplsLdpEntityOptionalParameters is implemented as read-only on
                  Nokia SROS in release 14.0.

                  The mplsLdpEntityTable is implemented as read-only."

        VARIATION   mplsLdpEntityPVLimitMismatchTrapEnable
            ACCESS  read-only
            DESCRIPTION
                 "mplsLdpEntityPVLimitMismatchTrapEnable is implemented as
                  read-only on Nokia SROS in release 14.0.

                  The mplsLdpEntityTable is implemented as read-only."

        VARIATION   mplsLdpEntityPathVectorLimit
            ACCESS  read-only
            DESCRIPTION
                 "mplsLdpEntityPathVectorLimit is implemented as read-only on
                  Nokia SROS in release 14.0.

                  The mplsLdpEntityTable is implemented as read-only."

        VARIATION   mplsLdpEntityProtocolVersion
            ACCESS  read-only
            DESCRIPTION
                 "mplsLdpEntityProtocolVersion is implemented as read-only on
                  Nokia SROS in release 14.0.

                  The mplsLdpEntityTable is implemented as read-only."

        VARIATION   mplsLdpEntityRowStatus
            ACCESS  read-only
            DESCRIPTION
                 "The mplsLdpEntityTable is implemented as read-only. Row
                  entries cannot be created by SNMP SET requests. LDP Entities
                  are created in TIMETRA-LDP-MIB and this table when
                  TIMETRA-VRTR-MIB::vRtrLdpStatus is set to 'create'."

        VARIATION   mplsLdpEntityStorageType
            ACCESS  read-only
            DESCRIPTION
                 "mplsLdpEntityStorageType is implemented as read-only on Nokia
                  SROS in release 14.0.

                  The mplsLdpEntityTable is implemented as read-only."

        VARIATION   mplsLdpEntityTargetedPeer
            ACCESS  read-only
            DESCRIPTION
                 "mplsLdpEntityTargetedPeer is implemented as read-only on Nokia
                  SROS in release 14.0.

                  The mplsLdpEntityTable is implemented as read-only."

        VARIATION   mplsLdpEntityTargetedPeerAddr
            ACCESS  read-only
            DESCRIPTION
                 "mplsLdpEntityTargetedPeerAddr is implemented as read-only on
                  Nokia SROS in release 14.0.

                  The mplsLdpEntityTable is implemented as read-only."

        VARIATION   mplsLdpEntityTargetedPeerAddrType
            ACCESS  read-only
            DESCRIPTION
                 "mplsLdpEntityTargetedPeerAddrType is implemented as read-only
                  on Nokia SROS in release 14.0.

                  The mplsLdpEntityTable is implemented as read-only."

        VARIATION   mplsLdpEntityWellKnownTcpDiscoveryPort
            ACCESS  read-only
            DESCRIPTION
                 "mplsLdpEntityWellKnownTcpDiscoveryPort is implemented as
                  read-only on Nokia SROS in release 14.0.

                  The mplsLdpEntityTable is implemented as read-only."

        VARIATION   mplsLdpEntityWellKnownUdpDiscoveryPort
            ACCESS  read-only
            DESCRIPTION
                 "mplsLdpEntityWellKnownUdpDiscoveryPort is implemented as
                  read-only on Nokia SROS in release 14.0.

                  The mplsLdpEntityTable is implemented as read-only."

        VARIATION   mplsLdpFailedInitSessionThresholdExceeded
            ACCESS  not-implemented
            DESCRIPTION
                 "mplsLdpFailedInitSessionThresholdExceeded notification is not
                  implemented."

        VARIATION   mplsLdpKeepAliveTimerExpiredErrors
            ACCESS  not-implemented
            DESCRIPTION
                 "The mplsLdpKeepAliveTimerExpiredErrors is not supported. It is
                  implemented through vRtrLdpStatsKeepAliveExpiredErrors in
                  TIMETRA-LDP-MIB."

        VARIATION   mplsLdpMalformedTlvValueErrors
            ACCESS  not-implemented
            DESCRIPTION
                 "The mplsLdpMalformedTlvValueErrors is not supported. It is
                  implemented through vRtrLdpStatsMalformedTlvValueErrors in
                  TIMETRA-LDP-MIB."

        VARIATION   mplsLdpPathVectorLimitMismatch
            ACCESS  not-implemented
            DESCRIPTION
                 "mplsLdpPathVectorLimitMismatch notification is not
                  implemented."

        VARIATION   mplsLdpSessionDown
            ACCESS  not-implemented
            DESCRIPTION
                 "mplsLdpSessionDown notification is not implemented."

        VARIATION   mplsLdpSessionPeerAddressTable
            ACCESS  not-implemented
            DESCRIPTION
                 "mplsLdpSessionPeerAddressTable is not implemented on Nokia
                  SROS in release 14.0."

        VARIATION   mplsLdpSessionRejectedAdvertisementErrors
            ACCESS  not-implemented
            DESCRIPTION
                 "The mplsLdpSessionRejectedAdvertisementErrors is not
                  supported. It is implemented through
                  vRtrLdpStatsSessRejAdvErrors in TIMETRA-LDP-MIB."

        VARIATION   mplsLdpSessionRejectedLabelRangeErrors
            ACCESS  not-implemented
            DESCRIPTION
                 "The mplsLdpSessionRejectedLabelRangeErrors is not supported.
                  It is implemented through vRtrLdpStatsSessRejLabelRangeErrors
                  in TIMETRA-LDP-MIB."

        VARIATION   mplsLdpSessionRejectedMaxPduErrors
            ACCESS  not-implemented
            DESCRIPTION
                 "The mplsLdpSessionRejectedMaxPduErrors is not supported. It is
                  implemented through vRtrLdpStatsSessRejMaxPduErrors in
                  TIMETRA-LDP-MIB."

        VARIATION   mplsLdpSessionRejectedNoHelloErrors
            ACCESS  not-implemented
            DESCRIPTION
                 "The mplsLdpSessionRejectedNoHelloErrors is not supported. It
                  is implemented through vRtrLdpStatsSessRejNoHelloErrors in
                  TIMETRA-LDP-MIB."

        VARIATION   mplsLdpSessionStatsTable
            ACCESS  not-implemented
            DESCRIPTION
                 "mplsLdpSessionStatsTable is not implemented on Nokia SROS in
                  release 14.0."

        VARIATION   mplsLdpSessionUp
            ACCESS  not-implemented
            DESCRIPTION
                 "mplsLdpSessionUp notification is not implemented."

        VARIATION   mplsLdpSessionUpDownTrapEnable
            ACCESS  not-implemented
            DESCRIPTION
                 "The generation of MPLS LDP traps is controlled by the
                  tmnxEventTable in TIMETRA-LOG-MIB."

        VARIATION   mplsLdpShutdownNotifReceived
            ACCESS  not-implemented
            DESCRIPTION
                 "The mplsLdpShutdownNotifReceived is not supported. It is
                  implemented through vRtrLdpStatsShutdownNotifRecv in
                  TIMETRA-LDP-MIB."

        VARIATION   mplsLdpShutdownNotifSent
            ACCESS  not-implemented
            DESCRIPTION
                 "The mplsLdpShutdownNotifSent is not supported. It is
                  implemented through vRtrLdpStatsShutdownNotifSent in
                  TIMETRA-LDP-MIB."

    SUPPORTS        TIMETRA-LDP-MIB
        INCLUDES {
           tmnxLdpNotificationV13v0Group,
           tmnxLdpNotifyObjsV13v0Group,
           tmnxLdpObsoletedNotifyObjGroup,
           tmnxLdpObsoletedNtfnV13v0Group,
           tmnxLdpObsoletedV13V0Group,
           tmnxLdpStatsV7v0Group,
           tmnxLdpTLDPAutoCreateV13v0Group
        }

        VARIATION   vRtrLdpEgrStatFecPfxRowStatus
            DESCRIPTION
                 "vRtrLdpEgrStatFecPfxRowStatus supports only 'ipv4' indices. If
                  an attempt is made to create a row entry with the
                  vRtrLdpEgrStatFecPfxAddrType index set to a value other than
                  'ipv4', a 'noCreation' error will be returned."

        VARIATION   vRtrLdpGenBackoffTime
            ACCESS  read-only
            DESCRIPTION
                 "vRtrLdpGenBackoffTime is implemented as read-only on Nokia
                  SROS in release 14.0."

        VARIATION   vRtrLdpGenDeaggregateFec
            ACCESS  read-only
            DESCRIPTION
                 "vRtrLdpGenDeaggregateFec is implemented as read-only on Nokia
                  SROS in release 14.0."

        VARIATION   vRtrLdpGenHopLimit
            ACCESS  read-only
            DESCRIPTION
                 "vRtrLdpGenHopLimit is implemented as read-only on Nokia SROS
                  in release 14.0."

        VARIATION   vRtrLdpGenLoopDetectCapable
            ACCESS  read-only
            DESCRIPTION
                 "vRtrLdpGenLoopDetectCapable is implemented as read-only on
                  Nokia SROS in release 14.0."

        VARIATION   vRtrLdpGenMaxBackoffTime
            ACCESS  read-only
            DESCRIPTION
                 "vRtrLdpGenMaxBackoffTime is implemented as read-only on Nokia
                  SROS in release 14.0."

        VARIATION   vRtrLdpGenPathVectorLimit
            ACCESS  read-only
            DESCRIPTION
                 "vRtrLdpGenPathVectorLimit is implemented as read-only on Nokia
                  SROS in release 14.0."

        VARIATION   vRtrLdpGenPropagatePolicy
            ACCESS  read-only
            DESCRIPTION
                 "vRtrLdpGenPropagatePolicy is implemented as read-only on Nokia
                  SROS in release 14.0."

        VARIATION   vRtrLdpGenRoutePreference
            ACCESS  read-only
            DESCRIPTION
                 "vRtrLdpGenRoutePreference is implemented as read-only on Nokia
                  SROS in release 14.0."

        VARIATION   vRtrLdpGenTargPassiveMode
            ACCESS  read-only
            DESCRIPTION
                 "vRtrLdpGenTargPassiveMode is implemented as read-only on Nokia
                  SROS in release 14.0."

        VARIATION   vRtrLdpGenTrustList
            ACCESS  not-implemented
            DESCRIPTION
                 "vRtrLdpGenTrustList is not implemented. This object was made
                  obsolete in the 5.0-R3 release."

        VARIATION   vRtrLdpIfBackoffTime
            ACCESS  read-only
            DESCRIPTION
                 "vRtrLdpIfBackoffTime is implemented as read-only on Nokia SROS
                  in release 14.0."

        VARIATION   vRtrLdpIfMaxBackoffTime
            ACCESS  read-only
            DESCRIPTION
                 "vRtrLdpIfMaxBackoffTime is implemented as read-only on Nokia
                  SROS in release 14.0."

        VARIATION   vRtrLdpIfPassiveMode
            ACCESS  read-only
            DESCRIPTION
                 "vRtrLdpIfPassiveMode is implemented as read-only on Nokia SROS
                  in release 14.0."

        VARIATION   vRtrLdpIfTableSpinlock
            ACCESS  not-implemented
            DESCRIPTION
                 "vRtrLdpIfTableSpinlock is not implemented on Nokia SROS in
                  release 14.0."

        VARIATION   vRtrLdpPeerTTLLogId
            ACCESS  not-implemented
            DESCRIPTION
                 "vRtrLdpPeerTTLLogId is not implemented on Nokia SROS in
                  release 14.0."

    ::= { tmnxSROSAgentV14v0  23 }

--
-- SROS LDP2 CAPABILITIES
--
tmnxSROSLdp2V14v0                 AGENT-CAPABILITIES
    PRODUCT-RELEASE "Nokia SROS"
    STATUS          current
    DESCRIPTION
         "Implementation of LDP capabilities for Nokia SROS systems release
          14.0."

    SUPPORTS        TIMETRA-LDP-NG-MIB
        INCLUDES {
           tmnxLdpNgAddrActiveFecV13v0Group,
           tmnxLdpNgAddrFecV12v0Group,
           tmnxLdpNgAdjV12v0Group,
           tmnxLdpNgAggrPreMatchV12v0Group,
           tmnxLdpNgCapabilityV12v0Group,
           tmnxLdpNgCepTdmFecV12v0Group,
           tmnxLdpNgFec129V12v0Group,
           tmnxLdpNgFecLimPerPeerV13v0Group,
           tmnxLdpNgGeneralEliV14v0Group,
           tmnxLdpNgGeneralFrrV14v0Group,
           tmnxLdpNgGeneralV12v0Group,
           tmnxLdpNgGeneralV13v0Group,
           tmnxLdpNgHelloAdjV13v0Group,
           tmnxLdpNgIfParamsV12v0Group,
           tmnxLdpNgIfV12v0Group,
           tmnxLdpNgIfV14v0Group,
           tmnxLdpNgInetIfV12v0Group,
           tmnxLdpNgInetIfV13v0Group,
           tmnxLdpNgLegacyInteropGrp,
           tmnxLdpNgNotificationGroup,
           tmnxLdpNgNotifyObjs,
           tmnxLdpNgP2MPFecV12v0Group,
           tmnxLdpNgPeerParamsV12v0Group,
           tmnxLdpNgPolicyV12v0Group,
           tmnxLdpNgRecvFecCapV13v0Group,
           tmnxLdpNgServFecV12v0Group,
           tmnxLdpNgSessParamPeerV13v0Group,
           tmnxLdpNgSessV14v0Group,
           tmnxLdpNgSessionStatsV12v0Group,
           tmnxLdpNgSessionV12v0Group,
           tmnxLdpNgStaticFecV12v0Group,
           tmnxLdpNgStatsV12v0Group,
           tmnxLdpNgTargPeerV12v0Group,
           tmnxLdpNgTargPeerV13v0Group,
           tmnxLdpNgTargPeerV14v0Group,
           tmnxLdpNgTargetedPeerV12v0Group,
           tmnxLdpNgTcpSessParamsV12v0Group,
           tmnxLdpNgTcpSessParamsV13v0Group
        }

    ::= { tmnxSROSAgentV14v0  88 }

--
-- SROS LLDP CAPABILITIES
--
tmnxSROSLldpV14v0                 AGENT-CAPABILITIES
    PRODUCT-RELEASE "Nokia SROS"
    STATUS          current
    DESCRIPTION
         "Implementation of LLDP capabilities for Nokia SROS systems release
          14.0."

    SUPPORTS        LLDP-MIB
        INCLUDES {
-- EXCLUDE lldpConfigGroup,
           lldpConfigRxGroup,
           lldpConfigTxGroup,
           lldpLocSysGroup,
           lldpNotificationsGroup,
-- EXCLUDE lldpRemSysGroup,
           lldpStatsRxGroup
-- EXCLUDE lldpStatsTxGroup,
        }

        VARIATION   lldpConfigManAddrPortsTxEnable
            ACCESS  not-implemented
            DESCRIPTION
                 "lldpConfigManAddrPortsTxEnable has been replaced with
                  TIMETRA-LLDP-MIB::tmnxLldpPortCfgManAddrTxEnabled."

        VARIATION   lldpLocPortDesc
            ACCESS  not-implemented
            DESCRIPTION
                 "lldpLocPortDesc has been replaced with
                  TIMETRA-LLDP-MIB::tmnxLldpLocPortDesc."

        VARIATION   lldpLocPortId
            ACCESS  not-implemented
            DESCRIPTION
                 "lldpLocPortId has been replaced with
                  TIMETRA-LLDP-MIB::tmnxLldpLocPortId."

        VARIATION   lldpLocPortIdSubtype
            ACCESS  not-implemented
            DESCRIPTION
                 "lldpLocPortIdSubtype has been replaced with
                  TIMETRA-LLDP-MIB::tmnxLldpLocPortIdSubtype."

        VARIATION   lldpPortConfigNotificationEnable
            ACCESS  not-implemented
            DESCRIPTION
                 "lldpPortConfigNotificationEnable has been replaced with
                  TIMETRA-LLDP-MIB::tmnxLldpPortCfgNotifyEnable."

        VARIATION   lldpPortConfigTLVsTxEnable
            ACCESS  not-implemented
            DESCRIPTION
                 "lldpPortConfigTLVsTxEnable has been replaced with
                  TIMETRA-LLDP-MIB::tmnxLldpPortCfgTLVsTxEnable."

        VARIATION   lldpRemSysCapEnabled
            SYNTAX  BITS {
                       other(0),
                       repeater(1),
                       bridge(2),
                       wlanAccessPoint(3),
                       router(4),
                       telephone(5),
                       docsisCableDevice(6),
                       stationOnly(7),
                       cVlan(8),
                       sVlan(9),
                       tpmr(10)
                    }
            DESCRIPTION
                 "lldpRemSysCapSupported and lldpRemSysCapEnabled have added the
                  following values: - C-VLAN Component of a VLAN Bridge IEEE Std
                  802.1Q, 'cVlan(8)' - S-VLAN Component of a VLAN Bridge IEEE
                  Std 802.1Q, 'sVlan(9)' - Two-port MAC Relay (TPMR) IEEE Std
                  802.1Q, 'tpmr(10)'"

        VARIATION   lldpRemSysCapSupported
            SYNTAX  BITS {
                       other(0),
                       repeater(1),
                       bridge(2),
                       wlanAccessPoint(3),
                       router(4),
                       telephone(5),
                       docsisCableDevice(6),
                       stationOnly(7),
                       cVlan(8),
                       sVlan(9),
                       tpmr(10)
                    }
            DESCRIPTION
                 "lldpRemSysCapSupported and lldpRemSysCapEnabled have added the
                  following values: - C-VLAN Component of a VLAN Bridge IEEE Std
                  802.1Q, 'cVlan(8)' - S-VLAN Component of a VLAN Bridge IEEE
                  Std 802.1Q, 'sVlan(9)' - Two-port MAC Relay (TPMR) IEEE Std
                  802.1Q, 'tpmr(10)'"

        VARIATION   lldpStatsRxPortAgeoutsTotal
            ACCESS  not-implemented
            DESCRIPTION
                 "lldpStatsRxPortAgeoutsTotal has been replaced with
                  TIMETRA-LLDP-MIB::tmnxLldpStatsRxPortAgeouts."

        VARIATION   lldpStatsRxPortFramesDiscardedTotal
            ACCESS  not-implemented
            DESCRIPTION
                 "lldpStatsRxPortFramesDiscardedTotal has been replaced with
                  TIMETRA-LLDP-MIB::tmnxLldpStatsRxPortFrameDiscard."

        VARIATION   lldpStatsRxPortFramesErrors
            ACCESS  not-implemented
            DESCRIPTION
                 "lldpStatsRxPortFramesErrors has been replaced with
                  TIMETRA-LLDP-MIB::tmnxLldpStatsRxPortFrameErrs."

        VARIATION   lldpStatsRxPortFramesTotal
            ACCESS  not-implemented
            DESCRIPTION
                 "lldpStatsRxPortFramesTotal has been replaced with
                  TIMETRA-LLDP-MIB::tmnxLldpStatsRxPortFrames."

        VARIATION   lldpStatsRxPortTLVsDiscardedTotal
            ACCESS  not-implemented
            DESCRIPTION
                 "lldpStatsRxPortTLVsDiscardedTotal has been replaced with
                  TIMETRA-LLDP-MIB::tmnxLldpStatsRxPortTLVDiscard."

        VARIATION   lldpStatsRxPortTLVsUnrecognizedTotal
            ACCESS  not-implemented
            DESCRIPTION
                 "lldpStatsRxPortTLVsUnrecognizedTotal has been replaced with
                  TIMETRA-LLDP-MIB::tmnxLldpStatsRxPortTLVUnknown."

        VARIATION   lldpTxDelay
            ACCESS  not-implemented
            DESCRIPTION
                 "lldpTxDelay is not implemented."

    SUPPORTS        TIMETRA-LLDP-MIB
        INCLUDES {
           tmnxLldpConfigGroup,
           tmnxLldpConfigV11v0Group,
           tmnxLldpConfigV13v0Group,
           tmnxLldpLocSysGroup,
           tmnxLldpRemManAddrGroup,
           tmnxLldpRemSysGroup,
           tmnxLldpStatsRxGroup,
           tmnxLldpStatsTxGroup
        }

        VARIATION   tmnxLldpPortCfgManAddress
            SYNTAX  OCTET STRING (SIZE (0..31))
            DESCRIPTION
                 "The value of this object can be the zero-length string."

        VARIATION   tmnxLldpPortCfgPortIdSubtype
            SYNTAX  LldpPortIdSubtype {
                       interfaceAlias(1),
                    -- portComponent(2)
                    -- macAddress(3)
                    -- networkAddress(4)
                       interfaceName(5),
                    -- agentCircuitId(6)
                       local(7)
                    }
            DESCRIPTION
                 "tmnxLldpPortCfgPortIdSubtype supports only the values
                  'interfaceAlias(1)', 'interfaceName(5)' and 'local(7)'."

        VARIATION   tmnxLldpRemSysCapEnabled
            SYNTAX  BITS {
                       other(0),
                       repeater(1),
                       bridge(2),
                       wlanAccessPoint(3),
                       router(4),
                       telephone(5),
                       docsisCableDevice(6),
                       stationOnly(7),
                       cVlan(8),
                       sVlan(9),
                       tpmr(10)
                    }
            DESCRIPTION
                 "tmnxLldpRemSysCapSupported and tmnxLldpRemSysCapEnabled have
                  added the following values: - C-VLAN Component of a VLAN
                  Bridge IEEE Std 802.1Q, 'cVlan(8)' - S-VLAN Component of a
                  VLAN Bridge IEEE Std 802.1Q, 'sVlan(9)' - Two-port MAC Relay
                  (TPMR) IEEE Std 802.1Q, 'tpmr(10)'"

        VARIATION   tmnxLldpRemSysCapSupported
            SYNTAX  BITS {
                       other(0),
                       repeater(1),
                       bridge(2),
                       wlanAccessPoint(3),
                       router(4),
                       telephone(5),
                       docsisCableDevice(6),
                       stationOnly(7),
                       cVlan(8),
                       sVlan(9),
                       tpmr(10)
                    }
            DESCRIPTION
                 "tmnxLldpRemSysCapSupported and tmnxLldpRemSysCapEnabled have
                  added the following values: - C-VLAN Component of a VLAN
                  Bridge IEEE Std 802.1Q, 'cVlan(8)' - S-VLAN Component of a
                  VLAN Bridge IEEE Std 802.1Q, 'sVlan(9)' - Two-port MAC Relay
                  (TPMR) IEEE Std 802.1Q, 'tpmr(10)'"

    ::= { tmnxSROSAgentV14v0  67 }

--
-- SROS LOCAL_USER_DB CAPABILITIES
--
tmnxSROSLocalUserDbV14v0          AGENT-CAPABILITIES
    PRODUCT-RELEASE "Nokia SROS"
    STATUS          current
    DESCRIPTION
         "Implementation of the Local User Database feature on Nokia SROS
          systems release 14.0."

    SUPPORTS        TIMETRA-LOCAL-USER-DB-MIB
        INCLUDES {
           tmnxLocalUserDbDhcpV11v0Group,
           tmnxLocalUserDbDhcpV12v0Group,
           tmnxLocalUserDbDhcpV8v0Group,
           tmnxLocalUserDbDhcpV9v0Group,
-- EXCLUDE tmnxLocalUserDbFltrProfGroup
           tmnxLocalUserDbHostGroup,
           tmnxLocalUserDbIpoeV14v0Group,
           tmnxLocalUserDbPppoeDfGroup,
           tmnxLocalUserDbPppoeV12v0Group,
           tmnxLocalUserDbPppoeV14v0Group,
           tmnxLocalUserDbPppoeV8v0Group,
           tmnxLocalUserDbPppoeV9v0Group,
           tmnxLocalUserDbRadiusFllbckGroup,
           tmnxLocalUserDbToolsV8v0Group,
           tmnxLocalUserDbV14v0Group,
           tmnxLocalUserDbV7v0Group,
           tmnxLudbDiameterAuthPlcyGroup,
           tmnxLudbNotifV11v0Group,
           tmnxLudbPppAliGroup,
           tmnxLudbPppHostGroup,
           tmnxLudbRadproxGroup,
           tmnxLudbRadproxV12v0Group,
           tmnxLudbRipPlcyV13v0Group,
           tmnxLudbToClntOptGroup,
           tmnxLudbToServerOptGroup
        }

        VARIATION   tmnxLocUsrDbDhcpAddrType
            SYNTAX  InetAddressType {
                       unknown              (0),
                       ipv4                 (1)
                    -- ipv6                 (2)
                    -- ipv4z                (3)
                    -- ipv6z                (4)
                    -- dns                  (16)
                    }
            DESCRIPTION
                 "tmnxLocUsrDbDhcpAddrType supports only the InetAddressType
                  values 'unknown (0)' and 'ipv4 (1)'."

        VARIATION   tmnxLocUsrDbDhcpAddress
            SYNTAX  InetAddress (SIZE (0|4))
            DESCRIPTION
                 "tmnxLocUsrDbDhcpAddress supports only InetAddressType 'unknown
                  (0)' and 'ipv4 (1)'."

        VARIATION   tmnxLocUsrDbDhcpAdminState
            SYNTAX  INTEGER {
                    -- noop                 (1)
                       inService            (2),
                       outOfService         (3)
                    }
            DESCRIPTION
                 "tmnxLocUsrDbDhcpAdminState supports only the values 'inService
                  (2)' and 'outOfService (3)'."

        VARIATION   tmnxLocUsrDbDhcpFltrProfString
            ACCESS  not-implemented
            DESCRIPTION
                 "tmnxLocUsrDbDhcpFltrProfString is not implemented on Nokia
                  SROS in release 14.0."

        VARIATION   tmnxLocUsrDbDhcpIpPrefixAddrType
            SYNTAX  InetAddressType {
                       unknown              (0),
                       ipv4                 (1),
                       ipv6                 (2)
                    -- ipv4z                (3)
                    -- ipv6z                (4)
                    -- dns                  (16)
                    }
            DESCRIPTION
                 "tmnxLocUsrDbDhcpIpPrefixAddrType supports only the
                  InetAddressType values 'unknown (0)', 'ipv4 (1)', and 'ipv6
                  (2)'."

        VARIATION   tmnxLocUsrDbDhcpMaskRowStatus
            SYNTAX  RowStatus {
                       active               (1),
                    -- notInService         (2)
                    -- notReady             (3)
                       createAndGo          (4),
                    -- createAndWait        (5)
                       destroy              (6)
                    }
            DESCRIPTION
                 "tmnxLocUsrDbDhcpMaskRowStatus supports only 'active (1)',
                  'createAndGo (4)', and 'destroy (6)'."

        VARIATION   tmnxLocUsrDbDhcpOptionRowStatus
            SYNTAX  RowStatus {
                       active               (1),
                    -- notInService         (2)
                    -- notReady             (3)
                       createAndGo          (4),
                    -- createAndWait        (5)
                       destroy              (6)
                    }
            DESCRIPTION
                 "tmnxLocUsrDbDhcpOptionRowStatus supports only 'active (1)',
                  'createAndGo (4)', and 'destroy (6)'."

        VARIATION   tmnxLocUsrDbDhcpOptionType
            SYNTAX  INTEGER {
                       ipv4(1),
                       ascii(2),
                       hex(3)
                    -- ipv6(4)
                    -- domain(5)
                    }
            DESCRIPTION
                 "tmnxLocUsrDbDhcpOptionType does not support the values
                  'ipv6(4)' and 'domain(5)'."

        VARIATION   tmnxLocUsrDbPppoeAddrType
            SYNTAX  InetAddressType {
                       unknown              (0),
                       ipv4                 (1)
                    -- ipv6                 (2)
                    -- ipv4z                (3)
                    -- ipv6z                (4)
                    -- dns                  (16)
                    }
            DESCRIPTION
                 "tmnxLocUsrDbPppoeAddrType supports only the InetAddressType
                  values 'unknown (0)' and 'ipv4 (1)'."

        VARIATION   tmnxLocUsrDbPppoeAddress
            SYNTAX  InetAddress (SIZE (0|4))
            DESCRIPTION
                 "tmnxLocUsrDbPppoeAddress supports only InetAddressType
                  'unknown (0)' and 'ipv4 (1)'."

        VARIATION   tmnxLocUsrDbPppoeFltrProfString
            ACCESS  not-implemented
            DESCRIPTION
                 "tmnxLocUsrDbPppoeFltrProfString is not implemented on Nokia
                  SROS in release 14.0."

        VARIATION   tmnxLocUsrDbPppoeMaskRowStatus
            SYNTAX  RowStatus {
                       active               (1),
                    -- notInService         (2)
                    -- notReady             (3)
                       createAndGo          (4),
                    -- createAndWait        (5)
                       destroy              (6)
                    }
            DESCRIPTION
                 "tmnxLocUsrDbPppoeMaskRowStatus supports only 'active (1)',
                  'createAndGo (4)', and 'destroy (6)'."

        VARIATION   tmnxLocUsrDbPppoeOptionRowStatus
            SYNTAX  RowStatus {
                       active               (1),
                    -- notInService         (2)
                    -- notReady             (3)
                       createAndGo          (4),
                    -- createAndWait        (5)
                       destroy              (6)
                    }
            DESCRIPTION
                 "tmnxLocUsrDbPppoeOptionRowStatus supports only 'active (1)',
                  'createAndGo (4)', and 'destroy (6)'."

        VARIATION   tmnxLocUsrDbPppoeOptionType
            SYNTAX  INTEGER {
                       ipv4(1),
                       ascii(2),
                       hex(3)
                    -- ipv6(4)
                    -- domain(5)
                    }
            DESCRIPTION
                 "tmnxLocUsrDbPppoeOptionType does not support the values
                  'ipv6(4)' and 'domain(5)'."

        VARIATION   tmnxLocUsrDbPppoeRowStatus
            SYNTAX  RowStatus {
                       active               (1),
                    -- notInService         (2)
                    -- notReady             (3)
                       createAndGo          (4),
                    -- createAndWait        (5)
                       destroy              (6)
                    }
            DESCRIPTION
                 "tmnxLocUsrDbPppoeRowStatus supports only 'active (1)',
                  'createAndGo (4)', and 'destroy (6)'."

        VARIATION   tmnxLocUsrDbRowStatus
            SYNTAX  RowStatus {
                       active               (1),
                    -- notInService         (2)
                    -- notReady             (3)
                       createAndGo          (4),
                    -- createAndWait        (5)
                       destroy              (6)
                    }
            DESCRIPTION
                 "tmnxLocUsrDbRowStatus supports only 'active (1)', 'createAndGo
                  (4)', and 'destroy (6)'."

        VARIATION   tmnxLudbHostFltrProfString
            ACCESS  not-implemented
            DESCRIPTION
                 "tmnxLudbHostFltrProfString is not implemented on Nokia SROS in
                  release 14.0."

        VARIATION   tmnxLudbHostTable
            ACCESS  not-implemented
            DESCRIPTION
                 "tmnxLudbHostTable is not implemented on Nokia SROS in release
                  14.0."

        VARIATION   tmnxLudbHostTableLastChange
            ACCESS  not-implemented
            DESCRIPTION
                 "tmnxLudbHostTableLastChange is not implemented on Nokia SROS
                  in release 14.0."

        VARIATION   tmnxLudbToClntOptRowStatus
            SYNTAX  RowStatus {
                       active               (1),
                    -- notInService         (2)
                    -- notReady             (3)
                       createAndGo          (4),
                    -- createAndWait        (5)
                       destroy              (6)
                    }
            DESCRIPTION
                 "tmnxLudbToClntOptRowStatus supports only 'active (1)',
                  'createAndGo (4)', and 'destroy (6)'."

    ::= { tmnxSROSAgentV14v0  62 }

--
-- 7710 LOCAL_USER_DB CAPABILITIES
--
tmnx7710LocalUserDbV14v0          AGENT-CAPABILITIES
    PRODUCT-RELEASE "Nokia SROS"
    STATUS          current
    DESCRIPTION
         "Implementation of the Local User Database feature on Nokia 7710
          systems release 14.0."

    SUPPORTS        TIMETRA-LOCAL-USER-DB-MIB
        INCLUDES {
           tmnxLocalUserDbDhcpV11v0Group,
           tmnxLocalUserDbDhcpV12v0Group,
           tmnxLocalUserDbDhcpV8v0Group,
           tmnxLocalUserDbDhcpV9v0Group,
-- EXCLUDE tmnxLocalUserDbFltrProfGroup
           tmnxLocalUserDbHostGroup,
           tmnxLocalUserDbIpoeV14v0Group,
           tmnxLocalUserDbPppoeDfGroup,
           tmnxLocalUserDbPppoeV12v0Group,
           tmnxLocalUserDbPppoeV14v0Group,
           tmnxLocalUserDbPppoeV8v0Group,
           tmnxLocalUserDbPppoeV9v0Group,
           tmnxLocalUserDbRadiusFllbckGroup,
           tmnxLocalUserDbToolsV8v0Group,
           tmnxLocalUserDbV14v0Group,
           tmnxLocalUserDbV7v0Group,
           tmnxLudbDiameterAuthPlcyGroup,
           tmnxLudbNotifV11v0Group,
           tmnxLudbPppAliGroup,
           tmnxLudbPppHostGroup,
           tmnxLudbRadproxGroup,
           tmnxLudbRadproxV12v0Group,
           tmnxLudbRipPlcyV13v0Group,
           tmnxLudbToClntOptGroup,
           tmnxLudbToServerOptGroup
        }

        VARIATION   tmnxLocUsrDbDhcpAddrType
            SYNTAX  InetAddressType {
                       unknown              (0),
                       ipv4                 (1)
                    -- ipv6                 (2)
                    -- ipv4z                (3)
                    -- ipv6z                (4)
                    -- dns                  (16)
                    }
            DESCRIPTION
                 "tmnxLocUsrDbDhcpAddrType supports only the InetAddressType
                  values 'unknown (0)' and 'ipv4 (1)'."

        VARIATION   tmnxLocUsrDbDhcpAddress
            SYNTAX  InetAddress (SIZE (0|4))
            DESCRIPTION
                 "tmnxLocUsrDbDhcpAddress supports only InetAddressType 'unknown
                  (0)' and 'ipv4 (1)'."

        VARIATION   tmnxLocUsrDbDhcpAdminState
            SYNTAX  INTEGER {
                    -- noop                 (1)
                       inService            (2),
                       outOfService         (3)
                    }
            DESCRIPTION
                 "tmnxLocUsrDbDhcpAdminState supports only the values 'inService
                  (2)' and 'outOfService (3)'."

        VARIATION   tmnxLocUsrDbDhcpFltrProfString
            ACCESS  not-implemented
            DESCRIPTION
                 "tmnxLocUsrDbDhcpFltrProfString is not implemented on Nokia
                  7710 in release 14.0."

        VARIATION   tmnxLocUsrDbDhcpIpPrefixAddrType
            SYNTAX  InetAddressType {
                       unknown              (0),
                       ipv4                 (1),
                       ipv6                 (2)
                    -- ipv4z                (3)
                    -- ipv6z                (4)
                    -- dns                  (16)
                    }
            DESCRIPTION
                 "tmnxLocUsrDbDhcpIpPrefixAddrType supports only the
                  InetAddressType values 'unknown (0)', 'ipv4 (1)', and 'ipv6
                  (2)'."

        VARIATION   tmnxLocUsrDbDhcpMaskRowStatus
            SYNTAX  RowStatus {
                       active               (1),
                    -- notInService         (2)
                    -- notReady             (3)
                       createAndGo          (4),
                    -- createAndWait        (5)
                       destroy              (6)
                    }
            DESCRIPTION
                 "tmnxLocUsrDbDhcpMaskRowStatus supports only 'active (1)',
                  'createAndGo (4)', and 'destroy (6)'."

        VARIATION   tmnxLocUsrDbDhcpOptionRowStatus
            SYNTAX  RowStatus {
                       active               (1),
                    -- notInService         (2)
                    -- notReady             (3)
                       createAndGo          (4),
                    -- createAndWait        (5)
                       destroy              (6)
                    }
            DESCRIPTION
                 "tmnxLocUsrDbDhcpOptionRowStatus supports only 'active (1)',
                  'createAndGo (4)', and 'destroy (6)'."

        VARIATION   tmnxLocUsrDbDhcpOptionType
            SYNTAX  INTEGER {
                       ipv4(1),
                       ascii(2),
                       hex(3)
                    -- ipv6(4)
                    -- domain(5)
                    }
            DESCRIPTION
                 "tmnxLocUsrDbDhcpOptionType does not support the values
                  'ipv6(4)' and 'domain(5)'."

        VARIATION   tmnxLocUsrDbPppoeAddrType
            SYNTAX  InetAddressType {
                       unknown              (0),
                       ipv4                 (1)
                    -- ipv6                 (2)
                    -- ipv4z                (3)
                    -- ipv6z                (4)
                    -- dns                  (16)
                    }
            DESCRIPTION
                 "tmnxLocUsrDbPppoeAddrType supports only the InetAddressType
                  values 'unknown (0)' and 'ipv4 (1)'."

        VARIATION   tmnxLocUsrDbPppoeAddress
            SYNTAX  InetAddress (SIZE (0|4))
            DESCRIPTION
                 "tmnxLocUsrDbPppoeAddress supports only InetAddressType
                  'unknown (0)' and 'ipv4 (1)'."

        VARIATION   tmnxLocUsrDbPppoeFltrProfString
            ACCESS  not-implemented
            DESCRIPTION
                 "tmnxLocUsrDbPppoeFltrProfString is not implemented on Nokia
                  7710 in release 14.0."

        VARIATION   tmnxLocUsrDbPppoeL2tpSvcId
            ACCESS  not-implemented
            DESCRIPTION
                 "tmnxLocUsrDbPppoeL2tpSvcId is not implemented on Nokia 7710 in
                  release 14.0."

        VARIATION   tmnxLocUsrDbPppoeL2tpTunnelGroup
            ACCESS  not-implemented
            DESCRIPTION
                 "tmnxLocUsrDbPppoeL2tpTunnelGroup is not implemented on Nokia
                  7710 in release 14.0."

        VARIATION   tmnxLocUsrDbPppoeMaskRowStatus
            SYNTAX  RowStatus {
                       active               (1),
                    -- notInService         (2)
                    -- notReady             (3)
                       createAndGo          (4),
                    -- createAndWait        (5)
                       destroy              (6)
                    }
            DESCRIPTION
                 "tmnxLocUsrDbPppoeMaskRowStatus supports only 'active (1)',
                  'createAndGo (4)', and 'destroy (6)'."

        VARIATION   tmnxLocUsrDbPppoeOptionRowStatus
            SYNTAX  RowStatus {
                       active               (1),
                    -- notInService         (2)
                    -- notReady             (3)
                       createAndGo          (4),
                    -- createAndWait        (5)
                       destroy              (6)
                    }
            DESCRIPTION
                 "tmnxLocUsrDbPppoeOptionRowStatus supports only 'active (1)',
                  'createAndGo (4)', and 'destroy (6)'."

        VARIATION   tmnxLocUsrDbPppoeOptionType
            SYNTAX  INTEGER {
                       ipv4(1),
                       ascii(2),
                       hex(3)
                    -- ipv6(4)
                    -- domain(5)
                    }
            DESCRIPTION
                 "tmnxLocUsrDbPppoeOptionType does not support the values
                  'ipv6(4)' and 'domain(5)'."

        VARIATION   tmnxLocUsrDbPppoeRowStatus
            SYNTAX  RowStatus {
                       active               (1),
                    -- notInService         (2)
                    -- notReady             (3)
                       createAndGo          (4),
                    -- createAndWait        (5)
                       destroy              (6)
                    }
            DESCRIPTION
                 "tmnxLocUsrDbPppoeRowStatus supports only 'active (1)',
                  'createAndGo (4)', and 'destroy (6)'."

        VARIATION   tmnxLocUsrDbRowStatus
            SYNTAX  RowStatus {
                       active               (1),
                    -- notInService         (2)
                    -- notReady             (3)
                       createAndGo          (4),
                    -- createAndWait        (5)
                       destroy              (6)
                    }
            DESCRIPTION
                 "tmnxLocUsrDbRowStatus supports only 'active (1)', 'createAndGo
                  (4)', and 'destroy (6)'."

        VARIATION   tmnxLudbHostFltrProfString
            ACCESS  not-implemented
            DESCRIPTION
                 "tmnxLudbHostFltrProfString is not implemented on Nokia 7710 in
                  release 14.0."

        VARIATION   tmnxLudbHostTable
            ACCESS  not-implemented
            DESCRIPTION
                 "tmnxLudbHostTable is not implemented on Nokia 7710 in release
                  14.0."

        VARIATION   tmnxLudbHostTableLastChange
            ACCESS  not-implemented
            DESCRIPTION
                 "tmnxLudbHostTableLastChange is not implemented on Nokia 7710
                  in release 14.0."

        VARIATION   tmnxLudbToClntOptRowStatus
            SYNTAX  RowStatus {
                       active               (1),
                    -- notInService         (2)
                    -- notReady             (3)
                       createAndGo          (4),
                    -- createAndWait        (5)
                       destroy              (6)
                    }
            DESCRIPTION
                 "tmnxLudbToClntOptRowStatus supports only 'active (1)',
                  'createAndGo (4)', and 'destroy (6)'."

    ::= { tmnx7710AgentV14v0  62 }

--
-- 7950 LOCAL_USER_DB CAPABILITIES
--
tmnx7950LocalUserDbV14v0          AGENT-CAPABILITIES
    PRODUCT-RELEASE "Nokia SROS"
    STATUS          current
    DESCRIPTION
         "Implementation of the Local User Database feature on Nokia 7950
          systems release 14.0."

--    SUPPORTS        TIMETRA-LOCAL-USER-DB-MIB
--        INCLUDES {
--        }

    ::= { tmnx7950AgentV14v0  62 }

--
-- SROS LOG CAPABILITIES
--
tmnxSROSLogV14v0                  AGENT-CAPABILITIES
    PRODUCT-RELEASE "Nokia SROS"
    STATUS          current
    DESCRIPTION
         "Implementation of event logging capabilities for Nokia SROS systems
          release 14.0."

    SUPPORTS        NOTIFICATION-LOG-MIB
        INCLUDES {
           notificationLogConfigGroup,
           notificationLogDateGroup,
           notificationLogLogGroup,
           notificationLogStatsGroup
        }

        VARIATION   nlmConfigGlobalAgeOut
            ACCESS  read-only
            DESCRIPTION
                 "nlmConfigGlobalAgeOut is implemented as read-only on Nokia
                  SROS in release 14.0."

        VARIATION   nlmConfigGlobalEntryLimit
            ACCESS  read-only
            DESCRIPTION
                 "nlmConfigGlobalEntryLimit is implemented as read-only on Nokia
                  SROS in release 14.0."

        VARIATION   nlmConfigLogEntryStatus
            SYNTAX  INTEGER {
                       active               (1)
                    }
            ACCESS  read-only
            DESCRIPTION
                 "nlmConfigLogEntryStatus is implemented as read-only. Row
                  entries cannot be created by SNMP SET requests. Notification
                  logs are created using the TIMETRA-LOG-MIB."

        VARIATION   nlmConfigLogStorageType
            ACCESS  read-only
            DESCRIPTION
                 "nlmConfigLogStorageType is implemented as read-only on Nokia
                  SROS in release 14.0."

    SUPPORTS        TIMETRA-LOG-MIB
        INCLUDES {
           tmnxLogAccountingPolicyCRV7v0Group,
           tmnxLogAccountingPolicyGroup,
           tmnxLogAccountingPolicyV6v1Group,
           tmnxLogApCrV11v0Group,
           tmnxLogApExtGroup,
           tmnxLogApV11v0Group,
           tmnxLogApV9v0Group,
           tmnxLogAppRouteNotifV10v0Group,
           tmnxLogEHSV13v0Group,
           tmnxLogEHSV14v0Group,
           tmnxLogEventDampedV8v0Group,
           tmnxLogEventsV11v0Group,
           tmnxLogEventsV5v0Group,
           tmnxLogExRbkOpGroup,
           tmnxLogFileIdGroup,
           tmnxLogFilterMsgV13v0Group,
           tmnxLogGlobalGroup,
           tmnxLogNotificationV6v0Group,
           tmnxLogNotificationV9v0Group,
           tmnxLogRoutePreferenceV7v0Group,
           tmnxLogSyslogV5v0Group,
           tmnxLogToSessionGroup,
           tmnxLogV5v0Group,
           tmnxSnmpSetErrsGroup,
           tmnxSnmpTrapDestV6v0Group,
           tmnxSnmpTrapV5v0Group
        }

        VARIATION   tmnxEventSeverity
            DESCRIPTION
                 "An attempt to set tmnxEventSeverity to value 'none(0)' will
                  result in a 'wrongValue' error."

        VARIATION   tmnxLogApAdminStatus
            SYNTAX  INTEGER {
                    -- noop                 (1)
                       inService            (2),
                       outOfService         (3)
                    }
            DESCRIPTION
                 "tmnxLogApAdminStatus supports only the values 'inService (2)'
                  and 'outOfService (3)'."

        VARIATION   tmnxLogApCrAACounters
            SYNTAX  INTEGER {
                    -- any                  (0)
                       sfa                  (1),
                       nfa                  (2),
                       sfd                  (3),
                       nfd                  (4),
                       saf                  (5),
                       naf                  (6),
                       spa                  (7),
                       npa                  (8),
                       sba                  (9),
                       nba                  (10),
                       spd                  (11),
                       npd                  (12),
                       sbd                  (13),
                       nbd                  (14),
                       sdf                  (15),
                       mdf                  (16),
                       ldf                  (17),
                       tfd                  (18),
                       tfc                  (19),
                       sbm                  (20),
                       spm                  (21),
                       smt                  (22),
                       nbm                  (23),
                       npm                  (24),
                       nmt                  (25)
                    }
            DESCRIPTION
                 "An attempt to set tmnxLogApCrAACounters to value 'any (0)'
                  will result in a 'wrongValue' error."

        VARIATION   tmnxLogApCrOverrideCntrRowStatus
            SYNTAX  RowStatus {
                       active               (1),
                    -- notInService         (2)
                    -- notReady             (3)
                       createAndGo          (4),
                    -- createAndWait        (5)
                       destroy              (6)
                    }
            DESCRIPTION
                 "tmnxLogApCrOverrideCntrRowStatus supports only 'active (1)',
                  'createAndGo (4)', and 'destroy (6)'."

        VARIATION   tmnxLogApCrQueueRowStatus
            SYNTAX  RowStatus {
                       active               (1),
                    -- notInService         (2)
                    -- notReady             (3)
                       createAndGo          (4),
                    -- createAndWait        (5)
                       destroy              (6)
                    }
            DESCRIPTION
                 "tmnxLogApCrQueueRowStatus supports only 'active (1)',
                  'createAndGo (4)', and 'destroy (6)'."

        VARIATION   tmnxLogApCrSignChangeAACounters
            SYNTAX  INTEGER {
                       any                  (0)
                    -- sfa                  (1)
                    -- nfa                  (2)
                    -- sfd                  (3)
                    -- nfd                  (4)
                    -- saf                  (5)
                    -- naf                  (6)
                    -- spa                  (7)
                    -- npa                  (8)
                    -- sba                  (9)
                    -- nba                  (10)
                    -- spd                  (11)
                    -- npd                  (12)
                    -- sbd                  (13)
                    -- nbd                  (14)
                    -- sdf                  (15)
                    -- mdf                  (16)
                    -- ldf                  (17)
                    -- tfd                  (18)
                    -- tfc                  (19)
                    -- sbm                  (20)
                    -- spm                  (21)
                    -- smt                  (22)
                    -- nbm                  (23)
                    -- npm                  (24)
                    -- nmt                  (25)
                    }
            DESCRIPTION
                 "An attempt to set tmnxLogApCrSignChangeAACounters to a value
                  other than 'any (0)' will result in a 'wrongValue' error."

        VARIATION   tmnxLogApRowStatus
            SYNTAX  RowStatus {
                       active               (1),
                    -- notInService         (2)
                    -- notReady             (3)
                       createAndGo          (4),
                    -- createAndWait        (5)
                       destroy              (6)
                    }
            DESCRIPTION
                 "tmnxLogApRowStatus supports only 'active (1)', 'createAndGo
                  (4)', and 'destroy (6)'."

        VARIATION   tmnxLogFilterParamsApplOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsApplOperator supports only 'off (1)',
                  'equal (2)', and 'notEqual (3)'."

        VARIATION   tmnxLogFilterParamsRouterOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsRouterOperator supports only 'off (1)',
                  'equal (2)', and 'notEqual (3)'."

        VARIATION   tmnxLogFilterParamsSubjectOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsSubjectOperator supports only 'off (1)',
                  'equal (2)', and 'notEqual (3)'."

        VARIATION   tmnxLogIdAdminStatus
            SYNTAX  INTEGER {
                    -- noop                 (1)
                       inService            (2),
                       outOfService         (3)
                    }
            DESCRIPTION
                 "tmnxLogIdAdminStatus supports only the values 'inService (2)'
                  and 'outOfService (3)'."

        VARIATION   tmnxStdName
            SYNTAX  SnmpAdminString (SIZE(1..42))
            DESCRIPTION
                 "The maximum length supported for the base log instance for the
                  name of an snmp notification destination is 28.

                  The maximum length supported for the name of an snmp
                  notification destination for vprn context is 42."

        VARIATION   tmnxStdNotifyCommunity
            SYNTAX  OCTET STRING (SIZE(0..45))
            DESCRIPTION
                 "The maximum length supported for the base log instance for the
                  community name string is 31.

                  The maximum length supported for community name string is 45
                  for vprn context."

        VARIATION   tmnxStdVersion
            SYNTAX  INTEGER {
                       snmpV1               (0),
                       snmpV2c              (1),
                       snmpV3               (3)
                    }
            DESCRIPTION
                 "The only values supported from the SnmpMessageProcessingModel
                  TEXTUAL-CONVENTION are 'snmpV1', 'snmpV2c', and .snmpV3'."

    ::= { tmnxSROSAgentV14v0  24 }

--
-- 7710 LOG CAPABILITIES
--
tmnx7710LogV14v0                  AGENT-CAPABILITIES
    PRODUCT-RELEASE "Nokia SROS"
    STATUS          current
    DESCRIPTION
         "Implementation of event logging capabilities for Nokia 7710 systems
          release 14.0."

    SUPPORTS        NOTIFICATION-LOG-MIB
        INCLUDES {
           notificationLogConfigGroup,
           notificationLogDateGroup,
           notificationLogLogGroup,
           notificationLogStatsGroup
        }

        VARIATION   nlmConfigGlobalAgeOut
            ACCESS  read-only
            DESCRIPTION
                 "nlmConfigGlobalAgeOut is implemented as read-only on Nokia
                  7710 in release 14.0."

        VARIATION   nlmConfigGlobalEntryLimit
            ACCESS  read-only
            DESCRIPTION
                 "nlmConfigGlobalEntryLimit is implemented as read-only on Nokia
                  7710 in release 14.0."

        VARIATION   nlmConfigLogEntryStatus
            SYNTAX  INTEGER {
                       active               (1)
                    }
            ACCESS  read-only
            DESCRIPTION
                 "nlmConfigLogEntryStatus is implemented as read-only. Row
                  entries cannot be created by SNMP SET requests. Notification
                  logs are created using the TIMETRA-LOG-MIB."

        VARIATION   nlmConfigLogStorageType
            ACCESS  read-only
            DESCRIPTION
                 "nlmConfigLogStorageType is implemented as read-only on Nokia
                  7710 in release 14.0."

    SUPPORTS        TIMETRA-LOG-MIB
        INCLUDES {
           tmnxLogAccountingPolicyCRV7v0Group,
           tmnxLogAccountingPolicyGroup,
           tmnxLogAccountingPolicyV6v1Group,
           tmnxLogApCrV11v0Group,
           tmnxLogApExtGroup,
           tmnxLogApV11v0Group,
           tmnxLogApV9v0Group,
           tmnxLogAppRouteNotifV10v0Group,
           tmnxLogEHSV13v0Group,
           tmnxLogEHSV14v0Group,
           tmnxLogEventDampedV8v0Group,
           tmnxLogEventsV11v0Group,
           tmnxLogEventsV5v0Group,
           tmnxLogExRbkOpGroup,
           tmnxLogFileIdGroup,
           tmnxLogFilterMsgV13v0Group,
           tmnxLogGlobalGroup,
           tmnxLogNotificationV6v0Group,
           tmnxLogNotificationV9v0Group,
           tmnxLogRoutePreferenceV7v0Group,
           tmnxLogSyslogV5v0Group,
           tmnxLogToSessionGroup,
           tmnxLogV5v0Group,
           tmnxSnmpSetErrsGroup,
           tmnxSnmpTrapDestV6v0Group,
           tmnxSnmpTrapV5v0Group
        }

        VARIATION   tmnxEventSeverity
            DESCRIPTION
                 "An attempt to set tmnxEventSeverity to value 'none(0)' will
                  result in a 'wrongValue' error."

        VARIATION   tmnxLogApAdminStatus
            SYNTAX  INTEGER {
                    -- noop                 (1)
                       inService            (2),
                       outOfService         (3)
                    }
            DESCRIPTION
                 "tmnxLogApAdminStatus supports only the values 'inService (2)'
                  and 'outOfService (3)'."

        VARIATION   tmnxLogApCrAACounters
            SYNTAX  INTEGER {
                    -- any                  (0)
                       sfa                  (1),
                       nfa                  (2),
                       sfd                  (3),
                       nfd                  (4),
                       saf                  (5),
                       naf                  (6),
                       spa                  (7),
                       npa                  (8),
                       sba                  (9),
                       nba                  (10),
                       spd                  (11),
                       npd                  (12),
                       sbd                  (13),
                       nbd                  (14),
                       sdf                  (15),
                       mdf                  (16),
                       ldf                  (17),
                       tfd                  (18),
                       tfc                  (19),
                       sbm                  (20),
                       spm                  (21),
                       smt                  (22),
                       nbm                  (23),
                       npm                  (24),
                       nmt                  (25)
                    }
            DESCRIPTION
                 "An attempt to set tmnxLogApCrAACounters to value 'any (0)'
                  will result in a 'wrongValue' error."

        VARIATION   tmnxLogApCrOverrideCntrRowStatus
            SYNTAX  RowStatus {
                       active               (1),
                    -- notInService         (2)
                    -- notReady             (3)
                       createAndGo          (4),
                    -- createAndWait        (5)
                       destroy              (6)
                    }
            DESCRIPTION
                 "tmnxLogApCrOverrideCntrRowStatus supports only 'active (1)',
                  'createAndGo (4)', and 'destroy (6)'."

        VARIATION   tmnxLogApCrQueueRowStatus
            SYNTAX  RowStatus {
                       active               (1),
                    -- notInService         (2)
                    -- notReady             (3)
                       createAndGo          (4),
                    -- createAndWait        (5)
                       destroy              (6)
                    }
            DESCRIPTION
                 "tmnxLogApCrQueueRowStatus supports only 'active (1)',
                  'createAndGo (4)', and 'destroy (6)'."

        VARIATION   tmnxLogApCrSignChangeAACounters
            SYNTAX  INTEGER {
                       any                  (0)
                    -- sfa                  (1)
                    -- nfa                  (2)
                    -- sfd                  (3)
                    -- nfd                  (4)
                    -- saf                  (5)
                    -- naf                  (6)
                    -- spa                  (7)
                    -- npa                  (8)
                    -- sba                  (9)
                    -- nba                  (10)
                    -- spd                  (11)
                    -- npd                  (12)
                    -- sbd                  (13)
                    -- nbd                  (14)
                    -- sdf                  (15)
                    -- mdf                  (16)
                    -- ldf                  (17)
                    -- tfd                  (18)
                    -- tfc                  (19)
                    -- sbm                  (20)
                    -- spm                  (21)
                    -- smt                  (22)
                    -- nbm                  (23)
                    -- npm                  (24)
                    -- nmt                  (25)
                    }
            DESCRIPTION
                 "An attempt to set tmnxLogApCrSignChangeAACounters to a value
                  other than 'any (0)' will result in a 'wrongValue' error."

        VARIATION   tmnxLogApPortType
            SYNTAX  INTEGER {
                       none                 (0),
                       access               (1),
                       network              (2),
                       sdp                  (3),
                       subscriber           (4)
                    -- appAssure            (5)
                    }
            DESCRIPTION
                 "The BSX (Application Assurance) port type is not supported on
                  Nokia 7710."

        VARIATION   tmnxLogApRecord
            SYNTAX  INTEGER {
                       none                 (0),
                       svcIngressOctet      (1),
                       svcEgressOctet       (2),
                       svcIngressPkt        (3),
                       svcEgressPkt         (4),
                       netIngressOctet      (5),
                       netEgressOctet       (6),
                       netIngressPkt        (7),
                       netEgressPkt         (8),
                       compactSvcInOctet    (9),
                       combinedSvcIngress   (10),
                       combinedNetInEgOctet (11),
                       combinedSvcInEgOctet (12),
                       completeSvcInEg      (13),
                       combinedSvcSdpInEg   (14),
                       completeSvcSdpInEg   (15),
                       completeSubscrIngrEgr (16),
                    -- bsxProtocol          (17)
                    -- bsxApplication       (18)
                    -- bsxAppGroup          (19)
                    -- bsxSubscriberProtocol (20)
                    -- bsxSubscriberApplication (21)
                    -- bsxSubscriberAppGroup (22)
                       customRecordSubscriber (23),
                       customRecordService  (24),
                       customRecordAa       (25),
                       queueGroupOctets     (26),
                       queueGroupPackets    (27),
                       combinedQueueGroup   (28),
                       combinedMplsLspIngress (29),
                       combinedMplsLspEgress (30),
                       combinedLdpLspEgress (31),
                       saa                  (32),
                       video                (33),
                       kpiSystem            (34),
                       kpiBearerMgmt        (35),
                       kpiBearerTraffic     (36),
                       kpiRefPoint          (37),
                       kpiPathMgmt          (38),
                       kciIom3              (39),
                       kciSystem            (40),
                       kciBearerMgmt        (41),
                       kciPathMgmt          (42),
                       completeKpi          (43),
                       completeKci          (44),
                       kpiBearerGroup       (45),
                       kpiRefPathGroup      (46),
                       kpiKciBearerMgmt     (47),
                       kpiKciPathMgmt       (48),
                       kpiKciSystem         (49),
                       completeKpiKci       (50),
                    -- aaPerformance        (51)
                       completeEthernetPort (52),
                       extendedSvcIngrEgr   (53),
                       completeNetIngrEgr   (54),
                    -- aaPartition          (55)
                       completeOamPm(56),
                       kpiRefPtSecErrorCauseCode(57),
                       kpiBearerTrafficGtpEndpoint(58),
                       kpiIpReas(59),
                       kpiRadiusGroup(60),
                       kpiRefPtFailureCauseCode(61),
                       kpiDhcpGroup(62)
                    }
            DESCRIPTION
                 "The BSX (Application Assurance) record types are not supported
                  on Nokia 7710."

        VARIATION   tmnxLogApRowStatus
            SYNTAX  RowStatus {
                       active               (1),
                    -- notInService         (2)
                    -- notReady             (3)
                       createAndGo          (4),
                    -- createAndWait        (5)
                       destroy              (6)
                    }
            DESCRIPTION
                 "tmnxLogApRowStatus supports only 'active (1)', 'createAndGo
                  (4)', and 'destroy (6)'."

        VARIATION   tmnxLogFilterParamsApplOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsApplOperator supports only 'off (1)',
                  'equal (2)', and 'notEqual (3)'."

        VARIATION   tmnxLogFilterParamsRouterOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsRouterOperator supports only 'off (1)',
                  'equal (2)', and 'notEqual (3)'."

        VARIATION   tmnxLogFilterParamsSubjectOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsSubjectOperator supports only 'off (1)',
                  'equal (2)', and 'notEqual (3)'."

        VARIATION   tmnxLogIdAdminStatus
            SYNTAX  INTEGER {
                    -- noop                 (1)
                       inService            (2),
                       outOfService         (3)
                    }
            DESCRIPTION
                 "tmnxLogIdAdminStatus supports only the values 'inService (2)'
                  and 'outOfService (3)'."

        VARIATION   tmnxStdName
            SYNTAX  SnmpAdminString (SIZE(1..42))
            DESCRIPTION
                 "The maximum length supported for the base log instance for the
                  name of an snmp notification destination is 28.

                  The maximum length supported for the name of an snmp
                  notification destination for vprn context is 42."

        VARIATION   tmnxStdNotifyCommunity
            SYNTAX  OCTET STRING (SIZE(0..45))
            DESCRIPTION
                 "The maximum length supported for the base log instance for the
                  community name string is 31.

                  The maximum length supported for community name string is 45
                  for vprn context."

        VARIATION   tmnxStdVersion
            SYNTAX  INTEGER {
                       snmpV1               (0),
                       snmpV2c              (1),
                       snmpV3               (3)
                    }
            DESCRIPTION
                 "The only values supported from the SnmpMessageProcessingModel
                  TEXTUAL-CONVENTION are 'snmpV1', 'snmpV2c', and .snmpV3'."

    ::= { tmnx7710AgentV14v0  24 }

--
-- 7950 LOG CAPABILITIES
--
tmnx7950LogV14v0                  AGENT-CAPABILITIES
    PRODUCT-RELEASE "Nokia SROS"
    STATUS          current
    DESCRIPTION
         "Implementation of event logging capabilities for Nokia 7950 systems
          release 14.0."

    SUPPORTS        NOTIFICATION-LOG-MIB
        INCLUDES {
           notificationLogConfigGroup,
           notificationLogDateGroup,
           notificationLogLogGroup,
           notificationLogStatsGroup
        }

        VARIATION   nlmConfigGlobalAgeOut
            ACCESS  read-only
            DESCRIPTION
                 "nlmConfigGlobalAgeOut is implemented as read-only on Nokia
                  7950 in release 14.0."

        VARIATION   nlmConfigGlobalEntryLimit
            ACCESS  read-only
            DESCRIPTION
                 "nlmConfigGlobalEntryLimit is implemented as read-only on Nokia
                  7950 in release 14.0."

        VARIATION   nlmConfigLogEntryStatus
            SYNTAX  INTEGER {
                       active               (1)
                    }
            ACCESS  read-only
            DESCRIPTION
                 "nlmConfigLogEntryStatus is implemented as read-only. Row
                  entries cannot be created by SNMP SET requests. Notification
                  logs are created using the TIMETRA-LOG-MIB."

        VARIATION   nlmConfigLogStorageType
            ACCESS  read-only
            DESCRIPTION
                 "nlmConfigLogStorageType is implemented as read-only on Nokia
                  7950 in release 14.0."

    SUPPORTS        TIMETRA-LOG-MIB
        INCLUDES {
           tmnxLogAccountingPolicyCRV7v0Group,
           tmnxLogAccountingPolicyGroup,
           tmnxLogAccountingPolicyV6v1Group,
           tmnxLogApCrV11v0Group,
           tmnxLogApExtGroup,
           tmnxLogApV11v0Group,
           tmnxLogApV9v0Group,
           tmnxLogAppRouteNotifV10v0Group,
           tmnxLogEHSV13v0Group,
           tmnxLogEHSV14v0Group,
           tmnxLogEventDampedV8v0Group,
           tmnxLogEventsV11v0Group,
           tmnxLogEventsV5v0Group,
           tmnxLogExRbkOpGroup,
           tmnxLogFileIdGroup,
           tmnxLogFilterMsgV13v0Group,
           tmnxLogGlobalGroup,
           tmnxLogNotificationV6v0Group,
           tmnxLogNotificationV9v0Group,
           tmnxLogRoutePreferenceV7v0Group,
           tmnxLogSyslogV5v0Group,
           tmnxLogToSessionGroup,
           tmnxLogV5v0Group,
           tmnxSnmpSetErrsGroup,
           tmnxSnmpTrapDestV6v0Group,
           tmnxSnmpTrapV5v0Group
        }

        VARIATION   tmnxEventSeverity
            DESCRIPTION
                 "An attempt to set tmnxEventSeverity to value 'none(0)' will
                  result in a 'wrongValue' error."

        VARIATION   tmnxLogApAdminStatus
            SYNTAX  INTEGER {
                    -- noop                 (1)
                       inService            (2),
                       outOfService         (3)
                    }
            DESCRIPTION
                 "tmnxLogApAdminStatus supports only the values 'inService (2)'
                  and 'outOfService (3)'."

        VARIATION   tmnxLogApCrAACounters
            SYNTAX  INTEGER {
                    -- any                  (0)
                       sfa                  (1),
                       nfa                  (2),
                       sfd                  (3),
                       nfd                  (4),
                       saf                  (5),
                       naf                  (6),
                       spa                  (7),
                       npa                  (8),
                       sba                  (9),
                       nba                  (10),
                       spd                  (11),
                       npd                  (12),
                       sbd                  (13),
                       nbd                  (14),
                       sdf                  (15),
                       mdf                  (16),
                       ldf                  (17),
                       tfd                  (18),
                       tfc                  (19),
                       sbm                  (20),
                       spm                  (21),
                       smt                  (22),
                       nbm                  (23),
                       npm                  (24),
                       nmt                  (25)
                    }
            DESCRIPTION
                 "An attempt to set tmnxLogApCrAACounters to value 'any (0)'
                  will result in a 'wrongValue' error."

        VARIATION   tmnxLogApCrOverrideCntrRowStatus
            SYNTAX  RowStatus {
                       active               (1),
                    -- notInService         (2)
                    -- notReady             (3)
                       createAndGo          (4),
                    -- createAndWait        (5)
                       destroy              (6)
                    }
            DESCRIPTION
                 "tmnxLogApCrOverrideCntrRowStatus supports only 'active (1)',
                  'createAndGo (4)', and 'destroy (6)'."

        VARIATION   tmnxLogApCrQueueRowStatus
            SYNTAX  RowStatus {
                       active               (1),
                    -- notInService         (2)
                    -- notReady             (3)
                       createAndGo          (4),
                    -- createAndWait        (5)
                       destroy              (6)
                    }
            DESCRIPTION
                 "tmnxLogApCrQueueRowStatus supports only 'active (1)',
                  'createAndGo (4)', and 'destroy (6)'."

        VARIATION   tmnxLogApCrSignChangeAACounters
            SYNTAX  INTEGER {
                       any                  (0)
                    -- sfa                  (1)
                    -- nfa                  (2)
                    -- sfd                  (3)
                    -- nfd                  (4)
                    -- saf                  (5)
                    -- naf                  (6)
                    -- spa                  (7)
                    -- npa                  (8)
                    -- sba                  (9)
                    -- nba                  (10)
                    -- spd                  (11)
                    -- npd                  (12)
                    -- sbd                  (13)
                    -- nbd                  (14)
                    -- sdf                  (15)
                    -- mdf                  (16)
                    -- ldf                  (17)
                    -- tfd                  (18)
                    -- tfc                  (19)
                    -- sbm                  (20)
                    -- spm                  (21)
                    -- smt                  (22)
                    -- nbm                  (23)
                    -- npm                  (24)
                    -- nmt                  (25)
                    }
            DESCRIPTION
                 "An attempt to set tmnxLogApCrSignChangeAACounters to a value
                  other than 'any (0)' will result in a 'wrongValue' error."

        VARIATION   tmnxLogApPortType
            SYNTAX  INTEGER {
                       none                 (0),
                       access               (1),
                       network              (2),
                       sdp                  (3),
                       subscriber           (4)
                    -- appAssure            (5)
                    }
            DESCRIPTION
                 "The BSX (Application Assurance) port type is not supported on
                  Nokia 7950."

        VARIATION   tmnxLogApRecord
            SYNTAX  INTEGER {
                       none                 (0),
                       svcIngressOctet      (1),
                       svcEgressOctet       (2),
                       svcIngressPkt        (3),
                       svcEgressPkt         (4),
                       netIngressOctet      (5),
                       netEgressOctet       (6),
                       netIngressPkt        (7),
                       netEgressPkt         (8),
                       compactSvcInOctet    (9),
                       combinedSvcIngress   (10),
                       combinedNetInEgOctet (11),
                       combinedSvcInEgOctet (12),
                       completeSvcInEg      (13),
                       combinedSvcSdpInEg   (14),
                       completeSvcSdpInEg   (15),
                       completeSubscrIngrEgr (16),
                    -- bsxProtocol          (17)
                    -- bsxApplication       (18)
                    -- bsxAppGroup          (19)
                    -- bsxSubscriberProtocol (20)
                    -- bsxSubscriberApplication (21)
                    -- bsxSubscriberAppGroup (22)
                       customRecordSubscriber (23),
                       customRecordService  (24),
                       customRecordAa       (25),
                       queueGroupOctets     (26),
                       queueGroupPackets    (27),
                       combinedQueueGroup   (28),
                       combinedMplsLspIngress (29),
                       combinedMplsLspEgress (30),
                       combinedLdpLspEgress (31),
                       saa                  (32),
                       video                (33),
                       kpiSystem            (34),
                       kpiBearerMgmt        (35),
                       kpiBearerTraffic     (36),
                       kpiRefPoint          (37),
                       kpiPathMgmt          (38),
                       kciIom3              (39),
                       kciSystem            (40),
                       kciBearerMgmt        (41),
                       kciPathMgmt          (42),
                       completeKpi          (43),
                       completeKci          (44),
                       kpiBearerGroup       (45),
                       kpiRefPathGroup      (46),
                       kpiKciBearerMgmt     (47),
                       kpiKciPathMgmt       (48),
                       kpiKciSystem         (49),
                       completeKpiKci       (50),
                    -- aaPerformance        (51)
                       completeEthernetPort (52),
                       extendedSvcIngrEgr   (53),
                       completeNetIngrEgr   (54),
                    -- aaPartition          (55)
                       completeOamPm(56),
                       kpiRefPtSecErrorCauseCode(57),
                       kpiBearerTrafficGtpEndpoint(58),
                       kpiIpReas(59),
                       kpiRadiusGroup(60),
                       kpiRefPtFailureCauseCode(61),
                       kpiDhcpGroup(62)
                    }
            DESCRIPTION
                 "The BSX (Application Assurance) record types are not supported
                  on Nokia 7950."

        VARIATION   tmnxLogApRowStatus
            SYNTAX  RowStatus {
                       active               (1),
                    -- notInService         (2)
                    -- notReady             (3)
                       createAndGo          (4),
                    -- createAndWait        (5)
                       destroy              (6)
                    }
            DESCRIPTION
                 "tmnxLogApRowStatus supports only 'active (1)', 'createAndGo
                  (4)', and 'destroy (6)'."

        VARIATION   tmnxLogFilterParamsApplOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsApplOperator supports only 'off (1)',
                  'equal (2)', and 'notEqual (3)'."

        VARIATION   tmnxLogFilterParamsRouterOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsRouterOperator supports only 'off (1)',
                  'equal (2)', and 'notEqual (3)'."

        VARIATION   tmnxLogFilterParamsSubjectOperator
            SYNTAX  INTEGER {
                       off                  (1),
                       equal                (2),
                       notEqual             (3)
                    -- lessThan             (4)
                    -- lessThanOrEqual      (5)
                    -- greaterThan          (6)
                    -- greaterThanOrEqual   (7)
                    }
            DESCRIPTION
                 "tmnxLogFilterParamsSubjectOperator supports only 'off (1)',
                  'equal (2)', and 'notEqual (3)'."

        VARIATION   tmnxLogIdAdminStatus
            SYNTAX  INTEGER {
                    -- noop                 (1)
                       inService            (2),
                       outOfService         (3)
                    }
            DESCRIPTION
                 "tmnxLogIdAdminStatus supports only the values 'inService (2)'
                  and 'outOfService (3)'."

        VARIATION   tmnxStdName
            SYNTAX  SnmpAdminString (SIZE(1..42))
            DESCRIPTION
                 "The maximum length supported for the base log instance for the
                  name of an snmp notification destination is 28.

                  The maximum length supported for the name of an snmp
                  notification destination for vprn context is 42."

        VARIATION   tmnxStdNotifyCommunity
            SYNTAX  OCTET STRING (SIZE(0..45))
            DESCRIPTION
                 "The maximum length supported for the base log instance for the
                  community name string is 31.

                  The maximum length supported for community name string is 45
                  for vprn context."

        VARIATION   tmnxStdVersion
            SYNTAX  INTEGER {
                       snmpV1               (0),
                       snmpV2c              (1),
                       snmpV3               (3)
                    }
            DESCRIPTION
                 "The only values supported from the SnmpMessageProcessingModel
                  TEXTUAL-CONVENTION are 'snmpV1', 'snmpV2c', and .snmpV3'."

    ::= { tmnx7950AgentV14v0  24 }

--
-- SROS MCAST_PATH_MGMT CAPABILITIES
--
tmnxSROSMcastPathMgmtV14v0        AGENT-CAPABILITIES
    PRODUCT-RELEASE "Nokia SROS"
    STATUS          current
    DESCRIPTION
         "Implementation of support for multicast load balancing and for tunnel
          interfaces related to Point to Multipoint LSPs (P2MP) feature through
          Multicast Path Management feature on Nokia SROS systems release 14.0."

    SUPPORTS        TIMETRA-MCAST-PATH-MGMT-MIB
        INCLUDES {
           tmnxMcPathBdlChlV6v0Group,
           tmnxMcPathBdlV6v0Group,
           tmnxMcPathChlSrcV6v0Group,
           tmnxMcPathGlobalExtV6v1Group,
           tmnxMcPathGlobalGroup,
           tmnxMcPathGlobalV10v0Group,
           tmnxMcPathGlobalV6v1Group,
           tmnxMcPathGlobalV7v0Group,
           tmnxMcPathGlobalV8v0Group,
           tmnxMcPathGlobalV9v0Group,
           tmnxMcPathNotificationGroup,
           tmnxMcPathOperChlV6v0Group,
           tmnxMcPathPlcyV6v0Group,
           tmnxMcPathPlcyV6v1Group,
           tmnxMcPathRprtDestV9v0Group,
           tmnxMcPathSwPlaneGroup,
           tmnxMcPathTunnelIfV7v0Group,
           tmnxMcPathVdoV13v0Group,
           tmnxMcPathVdoV7v0Group,
           tmnxMcPathVdoV9v0Group
        }

        VARIATION   tmnxMcPathBdlChlEndAddr
            SYNTAX  InetAddress (SIZE (4))
            DESCRIPTION
                 "tmnxMcPathBdlChlEndAddr supports only InetAddressType 'ipv4
                  (1)' and 'ipv6 (2)'."

        VARIATION   tmnxMcPathBdlChlEndAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlEndAddrType supports only the InetAddressType
                  values 'ipv4 (1)', and 'ipv6 (2)'."

        VARIATION   tmnxMcPathBdlChlStartAddr
            SYNTAX  InetAddress (SIZE (4))
            DESCRIPTION
                 "tmnxMcPathBdlChlStartAddr supports only InetAddressType 'ipv4
                  (1)' and 'ipv6 (2)'."

        VARIATION   tmnxMcPathBdlChlStartAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlStartAddrType supports only the
                  InetAddressType values 'ipv4 (1)', and 'ipv6 (2)'."

        VARIATION   tmnxMcPathBdlChlTunIfSdAddr
            SYNTAX  InetAddress (SIZE (0|4))
            DESCRIPTION
                 "tmnxMcPathBdlChlTunIfSdAddr supports only InetAddressType
                  'unknown (0)' and 'ipv4 (1)'."

        VARIATION   tmnxMcPathBdlChlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlChlTunIfSdAddrType supports only the
                  InetAddressType values 'unknown (0)' and 'ipv4 (1)'."

        VARIATION   tmnxMcPathBdlDefChlBwActivity
            SYNTAX  INTEGER {
                    -- none                 (0)
                       use-admin-bw         (1),
                       dynamic              (2)
                    }
            DESCRIPTION
                 "tmnxMcPathBdlDefChlBwActivity supports only 'use-admin-bw' and
                  'dynamic'."

        VARIATION   tmnxMcPathBdlTunIfSdAddr
            SYNTAX  InetAddress (SIZE (0|4))
            DESCRIPTION
                 "tmnxMcPathBdlTunIfSdAddr supports only InetAddressType
                  'unknown (0)' and 'ipv4 (1)'."

        VARIATION   tmnxMcPathBdlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlTunIfSdAddrType supports only the InetAddressType
                  values 'unknown (0)' and 'ipv4 (1)'."

        VARIATION   tmnxMcPathChlSrcSourceAddr
            SYNTAX  InetAddress (SIZE (4))
            DESCRIPTION
                 "tmnxMcPathChlSrcSourceAddr supports only InetAddressType 'ipv4
                  (1)' and 'ipv6 (2)'."

        VARIATION   tmnxMcPathChlSrcSourceAddrType
            SYNTAX  InetAddressType {
                    -- unknown              (0)
                       ipv4                 (1),
                       ipv6                 (2)
                    -- ipv4z                (3)
                    -- ipv6z                (4)
                    -- dns                  (16)
                    }
            DESCRIPTION
                 "tmnxMcPathChlSrcSourceAddrType supports only the
                  InetAddressType values 'ipv4 (1)', and 'ipv6 (2)'."

        VARIATION   tmnxMcPathChlSrcTunIfSdAddr
            SYNTAX  InetAddress (SIZE (0|4))
            DESCRIPTION
                 "tmnxMcPathChlSrcTunIfSdAddr supports only InetAddressType
                  'unknown (0)' and 'ipv4 (1)'."

        VARIATION   tmnxMcPathChlSrcTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathChlSrcTunIfSdAddrType supports only the
                  InetAddressType values 'unknown (0)' and 'ipv4 (1)'."

    ::= { tmnxSROSAgentV14v0  61 }

--
-- 7750c12 MCAST_PATH_MGMT CAPABILITIES
--
tmnx7750c12McastPathMgmtV14v0     AGENT-CAPABILITIES
    PRODUCT-RELEASE "Nokia SROS"
    STATUS          current
    DESCRIPTION
         "Implementation of support for multicast load balancing and for tunnel
          interfaces related to Point to Multipoint LSPs (P2MP) feature through
          Multicast Path Management feature on Nokia 7750 c12 systems release
          14.0."

    SUPPORTS        TIMETRA-MCAST-PATH-MGMT-MIB
        INCLUDES {
           tmnxMcPathBdlChlV6v0Group,
           tmnxMcPathBdlV6v0Group,
           tmnxMcPathChlSrcV6v0Group,
           tmnxMcPathGlobalExtV6v1Group,
           tmnxMcPathGlobalGroup,
           tmnxMcPathGlobalV10v0Group,
           tmnxMcPathGlobalV6v1Group,
           tmnxMcPathGlobalV7v0Group,
           tmnxMcPathGlobalV8v0Group,
           tmnxMcPathGlobalV9v0Group,
           tmnxMcPathNotificationGroup,
           tmnxMcPathOperChlV6v0Group,
           tmnxMcPathPlcyV6v0Group,
           tmnxMcPathPlcyV6v1Group,
           tmnxMcPathRprtDestV9v0Group,
           tmnxMcPathSwPlaneGroup,
           tmnxMcPathTunnelIfV7v0Group,
           tmnxMcPathVdoV13v0Group,
           tmnxMcPathVdoV7v0Group,
           tmnxMcPathVdoV9v0Group
        }

        VARIATION   tmnxMcPathBdlChlEndAddr
            SYNTAX  InetAddress (SIZE (4))
            DESCRIPTION
                 "tmnxMcPathBdlChlEndAddr supports only InetAddressType 'ipv4
                  (1)' and 'ipv6 (2)'."

        VARIATION   tmnxMcPathBdlChlEndAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlEndAddrType supports only the InetAddressType
                  values 'ipv4 (1)', and 'ipv6 (2)'."

        VARIATION   tmnxMcPathBdlChlStartAddr
            SYNTAX  InetAddress (SIZE (4))
            DESCRIPTION
                 "tmnxMcPathBdlChlStartAddr supports only InetAddressType 'ipv4
                  (1)' and 'ipv6 (2)'."

        VARIATION   tmnxMcPathBdlChlStartAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlStartAddrType supports only the
                  InetAddressType values 'ipv4 (1)', and 'ipv6 (2)'."

        VARIATION   tmnxMcPathBdlChlTunIfSdAddr
            SYNTAX  InetAddress (SIZE (0|4))
            DESCRIPTION
                 "tmnxMcPathBdlChlTunIfSdAddr supports only InetAddressType
                  'unknown (0)' and 'ipv4 (1)'."

        VARIATION   tmnxMcPathBdlChlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlChlTunIfSdAddrType supports only the
                  InetAddressType values 'unknown (0)' and 'ipv4 (1)'."

        VARIATION   tmnxMcPathBdlDefChlBwActivity
            SYNTAX  INTEGER {
                    -- none                 (0)
                       use-admin-bw         (1),
                       dynamic              (2)
                    }
            DESCRIPTION
                 "tmnxMcPathBdlDefChlBwActivity supports only 'use-admin-bw' and
                  'dynamic'."

        VARIATION   tmnxMcPathBdlTunIfSdAddr
            SYNTAX  InetAddress (SIZE (0|4))
            DESCRIPTION
                 "tmnxMcPathBdlTunIfSdAddr supports only InetAddressType
                  'unknown (0)' and 'ipv4 (1)'."

        VARIATION   tmnxMcPathBdlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlTunIfSdAddrType supports only the InetAddressType
                  values 'unknown (0)' and 'ipv4 (1)'."

        VARIATION   tmnxMcPathBwPlcyTableLastChanged
            ACCESS  not-implemented
            DESCRIPTION
                 "tmnxMcPathBwPlcyTableLastChanged is not implemented on Nokia
                  7750 c12 in release 14.0."

        VARIATION   tmnxMcPathChlSrcSourceAddr
            SYNTAX  InetAddress (SIZE (4))
            DESCRIPTION
                 "tmnxMcPathChlSrcSourceAddr supports only InetAddressType 'ipv4
                  (1)' and 'ipv6 (2)'."

        VARIATION   tmnxMcPathChlSrcSourceAddrType
            SYNTAX  InetAddressType {
                    -- unknown              (0)
                       ipv4                 (1),
                       ipv6                 (2)
                    -- ipv4z                (3)
                    -- ipv6z                (4)
                    -- dns                  (16)
                    }
            DESCRIPTION
                 "tmnxMcPathChlSrcSourceAddrType supports only the
                  InetAddressType values 'ipv4 (1)', and 'ipv6 (2)'."

        VARIATION   tmnxMcPathChlSrcTunIfSdAddr
            SYNTAX  InetAddress (SIZE (0|4))
            DESCRIPTION
                 "tmnxMcPathChlSrcTunIfSdAddr supports only InetAddressType
                  'unknown (0)' and 'ipv4 (1)'."

        VARIATION   tmnxMcPathChlSrcTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathChlSrcTunIfSdAddrType supports only the
                  InetAddressType values 'unknown (0)' and 'ipv4 (1)'."

    ::= { tmnx7750c12AgentV14v0  61 }

--
-- 7750c4 MCAST_PATH_MGMT CAPABILITIES
--
tmnx7750c4McastPathMgmtV14v0      AGENT-CAPABILITIES
    PRODUCT-RELEASE "Nokia SROS"
    STATUS          current
    DESCRIPTION
         "Implementation of support for multicast load balancing and for tunnel
          interfaces related to Point to Multipoint LSPs (P2MP) feature through
          Multicast Path Management feature on Nokia 7750 c4 systems release
          14.0."

    SUPPORTS        TIMETRA-MCAST-PATH-MGMT-MIB
        INCLUDES {
           tmnxMcPathBdlChlV6v0Group,
           tmnxMcPathBdlV6v0Group,
           tmnxMcPathChlSrcV6v0Group,
           tmnxMcPathGlobalExtV6v1Group,
           tmnxMcPathGlobalGroup,
           tmnxMcPathGlobalV10v0Group,
           tmnxMcPathGlobalV6v1Group,
           tmnxMcPathGlobalV7v0Group,
           tmnxMcPathGlobalV8v0Group,
           tmnxMcPathGlobalV9v0Group,
           tmnxMcPathNotificationGroup,
           tmnxMcPathOperChlV6v0Group,
           tmnxMcPathPlcyV6v0Group,
           tmnxMcPathPlcyV6v1Group,
           tmnxMcPathRprtDestV9v0Group,
           tmnxMcPathSwPlaneGroup,
           tmnxMcPathTunnelIfV7v0Group,
           tmnxMcPathVdoV13v0Group,
           tmnxMcPathVdoV7v0Group,
           tmnxMcPathVdoV9v0Group
        }

        VARIATION   tmnxMcPathBdlChlEndAddr
            SYNTAX  InetAddress (SIZE (4))
            DESCRIPTION
                 "tmnxMcPathBdlChlEndAddr supports only InetAddressType 'ipv4
                  (1)' and 'ipv6 (2)'."

        VARIATION   tmnxMcPathBdlChlEndAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlEndAddrType supports only the InetAddressType
                  values 'ipv4 (1)', and 'ipv6 (2)'."

        VARIATION   tmnxMcPathBdlChlStartAddr
            SYNTAX  InetAddress (SIZE (4))
            DESCRIPTION
                 "tmnxMcPathBdlChlStartAddr supports only InetAddressType 'ipv4
                  (1)' and 'ipv6 (2)'."

        VARIATION   tmnxMcPathBdlChlStartAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlStartAddrType supports only the
                  InetAddressType values 'ipv4 (1)', and 'ipv6 (2)'."

        VARIATION   tmnxMcPathBdlChlTunIfSdAddr
            SYNTAX  InetAddress (SIZE (0|4))
            DESCRIPTION
                 "tmnxMcPathBdlChlTunIfSdAddr supports only InetAddressType
                  'unknown (0)' and 'ipv4 (1)'."

        VARIATION   tmnxMcPathBdlChlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlChlTunIfSdAddrType supports only the
                  InetAddressType values 'unknown (0)' and 'ipv4 (1)'."

        VARIATION   tmnxMcPathBdlDefChlBwActivity
            SYNTAX  INTEGER {
                    -- none                 (0)
                       use-admin-bw         (1),
                       dynamic              (2)
                    }
            DESCRIPTION
                 "tmnxMcPathBdlDefChlBwActivity supports only 'use-admin-bw' and
                  'dynamic'."

        VARIATION   tmnxMcPathBdlTunIfSdAddr
            SYNTAX  InetAddress (SIZE (0|4))
            DESCRIPTION
                 "tmnxMcPathBdlTunIfSdAddr supports only InetAddressType
                  'unknown (0)' and 'ipv4 (1)'."

        VARIATION   tmnxMcPathBdlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlTunIfSdAddrType supports only the InetAddressType
                  values 'unknown (0)' and 'ipv4 (1)'."

        VARIATION   tmnxMcPathBwPlcyTableLastChanged
            ACCESS  not-implemented
            DESCRIPTION
                 "tmnxMcPathBwPlcyTableLastChanged is not implemented on Nokia
                  7750 c4 in release 14.0."

        VARIATION   tmnxMcPathChlSrcSourceAddr
            SYNTAX  InetAddress (SIZE (4))
            DESCRIPTION
                 "tmnxMcPathChlSrcSourceAddr supports only InetAddressType 'ipv4
                  (1)' and 'ipv6 (2)'."

        VARIATION   tmnxMcPathChlSrcSourceAddrType
            SYNTAX  InetAddressType {
                    -- unknown              (0)
                       ipv4                 (1),
                       ipv6                 (2)
                    -- ipv4z                (3)
                    -- ipv6z                (4)
                    -- dns                  (16)
                    }
            DESCRIPTION
                 "tmnxMcPathChlSrcSourceAddrType supports only the
                  InetAddressType values 'ipv4 (1)', and 'ipv6 (2)'."

        VARIATION   tmnxMcPathChlSrcTunIfSdAddr
            SYNTAX  InetAddress (SIZE (0|4))
            DESCRIPTION
                 "tmnxMcPathChlSrcTunIfSdAddr supports only InetAddressType
                  'unknown (0)' and 'ipv4 (1)'."

        VARIATION   tmnxMcPathChlSrcTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathChlSrcTunIfSdAddrType supports only the
                  InetAddressType values 'unknown (0)' and 'ipv4 (1)'."

    ::= { tmnx7750c4AgentV14v0  61 }

--
-- 7710 MCAST_PATH_MGMT CAPABILITIES
--
tmnx7710McastPathMgmtV14v0        AGENT-CAPABILITIES
    PRODUCT-RELEASE "Nokia SROS"
    STATUS          current
    DESCRIPTION
         "Implementation of support for multicast load balancing and for tunnel
          interfaces related to Point to Multipoint LSPs (P2MP) feature through
          Multicast Path Management feature on Nokia 7710 systems release 14.0."

    SUPPORTS        TIMETRA-MCAST-PATH-MGMT-MIB
        INCLUDES {
           tmnxMcPathBdlChlV6v0Group,
           tmnxMcPathBdlV6v0Group,
           tmnxMcPathChlSrcV6v0Group,
           tmnxMcPathGlobalExtV6v1Group,
           tmnxMcPathGlobalGroup,
           tmnxMcPathGlobalV10v0Group,
           tmnxMcPathGlobalV6v1Group,
           tmnxMcPathGlobalV7v0Group,
           tmnxMcPathGlobalV8v0Group,
           tmnxMcPathGlobalV9v0Group,
           tmnxMcPathNotificationGroup,
           tmnxMcPathOperChlV6v0Group,
           tmnxMcPathPlcyV6v0Group,
           tmnxMcPathPlcyV6v1Group,
           tmnxMcPathRprtDestV9v0Group,
           tmnxMcPathSwPlaneGroup,
           tmnxMcPathTunnelIfV7v0Group,
           tmnxMcPathVdoV13v0Group,
           tmnxMcPathVdoV7v0Group,
           tmnxMcPathVdoV9v0Group
        }

        VARIATION   tmnxMcPathBdlChlEndAddr
            SYNTAX  InetAddress (SIZE (4))
            DESCRIPTION
                 "tmnxMcPathBdlChlEndAddr supports only InetAddressType 'ipv4
                  (1)' and 'ipv6 (2)'."

        VARIATION   tmnxMcPathBdlChlEndAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlEndAddrType supports only the InetAddressType
                  values 'ipv4 (1)', and 'ipv6 (2)'."

        VARIATION   tmnxMcPathBdlChlStartAddr
            SYNTAX  InetAddress (SIZE (4))
            DESCRIPTION
                 "tmnxMcPathBdlChlStartAddr supports only InetAddressType 'ipv4
                  (1)' and 'ipv6 (2)'."

        VARIATION   tmnxMcPathBdlChlStartAddrType
            SYNTAX  InetAddressType {
                    -- unknown              (0)
                       ipv4                 (1),
                       ipv6                 (2)
                    -- ipv4z                (3)
                    -- ipv6z                (4)
                    -- dns                  (16)
                    }
            DESCRIPTION
                 "tmnxMcPathBdlChlStartAddrType supports only the
                  InetAddressType values 'ipv4 (1)', and 'ipv6 (2)'."

        VARIATION   tmnxMcPathBdlChlTunIfSdAddr
            SYNTAX  InetAddress (SIZE (0|4))
            DESCRIPTION
                 "tmnxMcPathBdlChlTunIfSdAddr supports only InetAddressType
                  'unknown (0)' and 'ipv4 (1)'."

        VARIATION   tmnxMcPathBdlChlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlChlTunIfSdAddrType supports only the
                  InetAddressType values 'unknown (0)' and 'ipv4 (1)'."

        VARIATION   tmnxMcPathBdlDefChlBwActivity
            SYNTAX  INTEGER {
                    -- none                 (0)
                       use-admin-bw         (1),
                       dynamic              (2)
                    }
            DESCRIPTION
                 "tmnxMcPathBdlDefChlBwActivity supports only 'use-admin-bw' and
                  'dynamic'."

        VARIATION   tmnxMcPathBdlTunIfSdAddr
            SYNTAX  InetAddress (SIZE (0|4))
            DESCRIPTION
                 "tmnxMcPathBdlTunIfSdAddr supports only InetAddressType
                  'unknown (0)' and 'ipv4 (1)'."

        VARIATION   tmnxMcPathBdlTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathBdlTunIfSdAddrType supports only the InetAddressType
                  values 'unknown (0)' and 'ipv4 (1)'."

        VARIATION   tmnxMcPathBwPlcyTableLastChanged
            ACCESS  not-implemented
            DESCRIPTION
                 "tmnxMcPathBwPlcyTableLastChanged is not implemented on Nokia
                  7710 in release 14.0."

        VARIATION   tmnxMcPathChlSrcSourceAddr
            SYNTAX  InetAddress (SIZE (4))
            DESCRIPTION
                 "tmnxMcPathChlSrcSourceAddr supports only InetAddressType 'ipv4
                  (1)' and 'ipv6 (2)'."

        VARIATION   tmnxMcPathChlSrcSourceAddrType
            SYNTAX  InetAddressType {
                    -- unknown              (0)
                       ipv4                 (1),
                       ipv6                 (2)
                    -- ipv4z                (3)
                    -- ipv6z                (4)
                    -- dns                  (16)
                    }
            DESCRIPTION
                 "tmnxMcPathChlSrcSourceAddrType supports only the
                  InetAddressType values 'ipv4 (1)', and 'ipv6 (2)'."

        VARIATION   tmnxMcPathChlSrcTunIfSdAddr
            SYNTAX  InetAddress (SIZE (0|4))
            DESCRIPTION
                 "tmnxMcPathChlSrcTunIfSdAddr supports only InetAddressType
                  'unknown (0)' and 'ipv4 (1)'."

        VARIATION   tmnxMcPathChlSrcTunIfSdAddrType
            SYNTAX  InetAddressType {
                       unknown              (0),
                       ipv4                 (1)
                    -- ipv6                 (2)
                    -- ipv4z                (3)
                    -- ipv6z                (4)
                    -- dns                  (16)
                    }
            DESCRIPTION
                 "tmnxMcPathChlSrcTunIfSdAddrType supports only the
                  InetAddressType values 'unknown (0)' and 'ipv4 (1)'."

    ::= { tmnx7710AgentV14v0  61 }

--
-- SROS MC_REDUNDANCY CAPABILITIES
--
tmnxSROSMcRedundancyV14v0         AGENT-CAPABILITIES
    PRODUCT-RELEASE "Nokia SROS"
    STATUS          current
    DESCRIPTION
         "Implementation of the Multi-Chassis Redundancy feature on Nokia SROS
          systems release 14.0."

    SUPPORTS        TIMETRA-MC-REDUNDANCY-MIB
        INCLUDES {
           tmnxMcL3RingGroup,
           tmnxMcLagPbbGroup,
           tmnxMcMobRedundancyV4v0Group,
           tmnxMcOmcrNotifGroup,
           tmnxMcPeerEPGroup,
           tmnxMcPeerEPNotifyObjsV7v0Group,
           tmnxMcPeerEPV7v0NotifGroup,
           tmnxMcPeerIPsecTnlGrpV10v0Group,
           tmnxMcPeerNotifyObjsV10v0Group,
           tmnxMcPeerSyncGroup,
           tmnxMcPeerV10v0NotifGroup,
           tmnxMcRedBgpEvpnGroup,
           tmnxMcRedBgpMHSiteGroup,
           tmnxMcRedBgpMultiHomeGroup,
           tmnxMcRedundancySrrpNotifGroup,
           tmnxMcRedundancyV10v0Group,
           tmnxMcRedundancyV12v0Group,
           tmnxMcRedundancyV13v0Group,
           tmnxMcRedundancyV14v0Group,
           tmnxMcRedundancyV5v0NotifGroup,
           tmnxMcRedundancyV9v0Group,
           tmnxMcRingV6v0Group,
           tmnxMcRingV6v0NotifGroup,
           tmnxMcTlsSapGroup,
           tmnxMcWarmStandbyGroup,
           tmnxMcsDhcpsV11v0Group,
           tmnxMcsDhcpsV6v0Group,
           tmnxMcsSubHostTrkGroup,
           tmnxSrrpNotifV6v1Group,
           tmnxSrrpNotificationV10v0Group,
           tmnxSrrpV10v0Group,
           tmnxSrrpV5v0Group,
           tmnxSrrpV6v1Group,
           tmnxSrrpV8v0Group,
           tmnxSrrpV9v0Group
        }

        VARIATION   tMcPeerIPsecBfdEnableSvc
            SYNTAX  TmnxServId (0)
            DESCRIPTION
                 "tMcPeerIPsecBfdEnableSvc supports only default value of zero."

        VARIATION   tMcPeerIPsecBfdIntfDestIp
            SYNTAX  InetAddress
            DESCRIPTION
                 "tMcPeerIPsecBfdIntfDestIp supports only default value of ''H."

        VARIATION   tMcPeerIPsecBfdIntfDestIpType
            SYNTAX  InetAddressType
            DESCRIPTION
                 "tMcPeerIPsecBfdIntfDestIpType supports only default value of
                  'unknown'."

        VARIATION   tMcPeerIPsecBfdIntfIfName
            SYNTAX  TNamedItemOrEmpty
            DESCRIPTION
                 "tMcPeerIPsecBfdIntfIfName supports only default value of ''H."

        VARIATION   tMcPeerIPsecTnlGrpPreempt
            SYNTAX  INTEGER {
                    -- true                 (1)
                       false                (2)
                    }
            DESCRIPTION
                 "tMcPeerIPsecTnlGrpPreempt supports only 'false (2)' value."

        VARIATION   tmnxMcDiamPrxPeerIpAddrType
            SYNTAX  InetAddressType {
                       unknown              (0),
                       ipv4                 (1),
                       ipv6                 (2)
                    -- ipv4z                (3)
                    -- ipv6z                (4)
                    -- dns                  (16)
                    }
            DESCRIPTION
                 "tmnxMcDiamPrxPeerIpAddrType supports only the InetAddressType
                  values 'unknown (0)', 'ipv4 (1)', and 'ipv6 (2)'."

        VARIATION   tmnxMcDiamPrxRowStatus
            SYNTAX  RowStatus {
                       active               (1),
                    -- notInService         (2)
                    -- notReady             (3)
                       createAndGo          (4),
                    -- createAndWait        (5)
                       destroy              (6)
                    }
            DESCRIPTION
                 "tmnxMcDiamPrxRowStatus supports only 'active (1)',
                  'createAndGo (4)', and 'destroy (6)'."

        VARIATION   tmnxMcEpipeSapRowStatus
            SYNTAX  RowStatus {
                       active               (1),
                    -- notInService         (2)
                    -- notReady             (3)
                       createAndGo          (4),
                    -- createAndWait        (5)
                       destroy              (6)
                    }
            DESCRIPTION
                 "tmnxMcEpipeSapRowStatus supports only 'active (1)',
                  'createAndGo (4)', and 'destroy (6)'."

        VARIATION   tmnxMcL2tpPeerIpAddr
            SYNTAX  InetAddress (SIZE (0|4))
            DESCRIPTION
                 "tmnxMcL2tpPeerIpAddr supports only InetAddressType values
                  'unknown (0)' and 'ipv4 (1)'."

        VARIATION   tmnxMcL2tpPeerIpAddrType
            SYNTAX  InetAddressType {
                       unknown              (0),
                       ipv4                 (1)
                    -- ipv6                 (2)
                    -- ipv4z                (3)
                    -- ipv6z                (4)
                    -- dns                  (16)
                    }
            DESCRIPTION
                 "tmnxMcL2tpPeerIpAddrType supports only the InetAddressType
                  values 'unknown (0)' and 'ipv4 (1)'."

        VARIATION   tmnxMcL2tpRowStatus
            SYNTAX  RowStatus {
                       active               (1),
                    -- notInService         (2)
                    -- notReady             (3)
                       createAndGo          (4),
                    -- createAndWait        (5)
                       destroy              (6)
                    }
            DESCRIPTION
                 "tmnxMcL2tpRowStatus supports only 'active (1)', 'createAndGo
                  (4)', and 'destroy (6)'."

        VARIATION   tmnxMcLagConfigLagRowStatus
            SYNTAX  RowStatus {
                       active               (1),
                    -- notInService         (2)
                    -- notReady             (3)
                       createAndGo          (4),
                    -- createAndWait        (5)
                       destroy              (6)
                    }
            DESCRIPTION
                 "tmnxMcLagConfigLagRowStatus supports only 'active (1)',
                  'createAndGo (4)', and 'destroy (6)'."

        VARIATION   tmnxMcLagConfigPeerAdminstate
            SYNTAX  INTEGER {
                    -- noop                 (1)
                       inService            (2),
                       outOfService         (3)
                    }
            DESCRIPTION
                 "tmnxMcLagConfigPeerAdminstate supports only the values
                  'inService (2)' and 'outOfService (3)'."

        VARIATION   tmnxMcPeerIpType
            SYNTAX  InetAddressType {
                    -- unknown              (0)
                       ipv4                 (1),
                       ipv6                 (2)
                    -- ipv4z                (3)
                    -- ipv6z                (4)
                    -- dns                  (16)
                    }
            DESCRIPTION
                 "tmnxMcPeerIpType supports only the InetAddressType values
                  'ipv4 (1)', and 'ipv6 (2)'."

        VARIATION   tmnxMcPeerSrcIpOperType
            SYNTAX  InetAddressType {
                       unknown              (0),
                       ipv4                 (1),
                       ipv6                 (2)
                    -- ipv4z                (3)
                    -- ipv6z                (4)
                    -- dns                  (16)
                    }
            DESCRIPTION
                 "tmnxMcPeerSrcIpOperType supports only the InetAddressType
                  values 'unknown (0)', 'ipv4 (1)', and 'ipv6 (2)'."

        VARIATION   tmnxMcPeerSrcIpType
            SYNTAX  InetAddressType {
                       unknown              (0),
                       ipv4                 (1),
                       ipv6                 (2)
                    -- ipv4z                (3)
                    -- ipv6z                (4)
                    -- dns                  (16)
                    }
            DESCRIPTION
                 "tmnxMcPeerSrcIpType supports only the InetAddressType values
                  'unknown (0)', 'ipv4 (1)', and 'ipv6 (2)'."

        VARIATION   tmnxMcPeerSyncMobile
            ACCESS  not-implemented
            DESCRIPTION
                 "tmnxMcPeerSyncMobile is not implemented on Nokia SROS in
                  release 14.0."

        VARIATION   tmnxMcRingAdminState
            SYNTAX  INTEGER {
                    -- noop                 (1)
                       inService            (2),
                       outOfService         (3)
                    }
            DESCRIPTION
                 "tmnxMcRingAdminState supports only the values 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  InetAddressType {
                       unknown              (0),
                       ipv4                 (1)
                    -- ipv6                 (2)
                    -- ipv4z                (3)
                    -- ipv6z                (4)
                    -- dns                  (16)
                    }
            DESCRIPTION
                 "tmnxMcRingInbCtrlDestIpType supports only the InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  InetAddressType {
                       unknown              (0),
                       ipv4                 (1)
                    -- ipv6                 (2)
                    -- ipv4z                (3)
                    -- ipv6z                (4)
                    -- dns                  (16)
                    }
            DESCRIPTION
                 "tmnxMcRingInfoInbCtrlSrcIpType supports only the
                  InetAddressType values 'unknown (0)' and 'ipv4 (1)'."

        VARIATION   tmnxMcRingNodeRncvAdminState
            SYNTAX  INTEGER {
                    -- noop                 (1)
                       inService            (2),
                       outOfService         (3)
                    }
            DESCRIPTION
                 "tmnxMcRingNodeRncvAdminState supports only the values
                  'inService (2)' and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvDestIpType supports only the InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvSrcIpType supports only the InetAddressType
                  values 'unknown (0)' and 'ipv4 (1)'."

        VARIATION   tmnxMcRingNodeRowStatus
            SYNTAX  RowStatus {
                       active               (1),
                    -- notInService         (2)
                    -- notReady             (3)
                       createAndGo          (4),
                    -- createAndWait        (5)
                       destroy              (6)
                    }
            DESCRIPTION
                 "tmnxMcRingNodeRowStatus supports only 'active (1)',
                  'createAndGo (4)', and 'destroy (6)'."

        VARIATION   tmnxMcRingRowStatus
            SYNTAX  RowStatus {
                       active               (1),
                    -- notInService         (2)
                    -- notReady             (3)
                       createAndGo          (4),
                    -- createAndWait        (5)
                       destroy              (6)
                    }
            DESCRIPTION
                 "tmnxMcRingRowStatus supports only 'active (1)', 'createAndGo
                  (4)', and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  InetAddressType {
                       unknown              (0),
                       ipv4                 (1)
                    -- ipv6                 (2)
                    -- ipv4z                (3)
                    -- ipv6z                (4)
                    -- dns                  (16)
                    }
            DESCRIPTION
                 "tmnxMcTlsCfgDefGwIpType supports only the InetAddressType
                  values 'unknown (0)' and 'ipv4 (1)'."

        VARIATION   tmnxMcTrkSrrpPeerAddrType
            SYNTAX  InetAddressType {
                    -- unknown              (0)
                       ipv4                 (1)
                    -- ipv6                 (2)
                    -- ipv4z                (3)
                    -- ipv6z                (4)
                    -- dns                  (16)
                    }
            DESCRIPTION
                 "tmnxMcTrkSrrpPeerAddrType supports only the InetAddressType
                  value 'ipv4 (1)'."

        VARIATION   tmnxMcTrkSrrpRowStatus
            SYNTAX  RowStatus {
                       active               (1),
                    -- notInService         (2)
                    -- notReady             (3)
                       createAndGo          (4),
                    -- createAndWait        (5)
                       destroy              (6)
                    }
            DESCRIPTION
                 "tmnxMcTrkSrrpRowStatus supports only 'active (1)',
                  'createAndGo (4)', and 'destroy (6)'."

        VARIATION   tmnxMcsPyPlcyPeerIpAddrType
            SYNTAX  InetAddressType {
                       unknown              (0),
                       ipv4                 (1),
                       ipv6                 (2)
                    -- ipv4z                (3)
                    -- ipv6z                (4)
                    -- dns                  (16)
                    }
            DESCRIPTION
                 "tmnxMcsPyPlcyPeerIpAddrType supports only the InetAddressType
                  values 'unknown (0)', 'ipv4 (1)', and 'ipv6 (2)'."

        VARIATION   tmnxMcsPyPlcyRowStatus
            SYNTAX  RowStatus {
                       active               (1),
                    -- notInService         (2)
                    -- notReady             (3)
                       createAndGo          (4),
                    -- createAndWait        (5)
                       destroy              (6)
                    }
            DESCRIPTION
                 "tmnxMcsPyPlcyRowStatus supports only 'active (1)',
                  'createAndGo (4)', and 'destroy (6)'."

        VARIATION   tmnxSrrpOperAdminState
            SYNTAX  INTEGER {
                    -- noop                 (1)
                       inService            (2),
                       outOfService         (3)
                    }
            DESCRIPTION
                 "tmnxSrrpOperAdminState supports only the values 'inService
                  (2)' and 'outOfService (3)'."

        VARIATION   tmnxSrrpOperRowStatus
            SYNTAX  RowStatus {
                       active               (1),
                    -- notInService         (2)
                    -- notReady             (3)
                       createAndGo          (4),
                    -- createAndWait        (5)
                       destroy              (6)
                    }
            DESCRIPTION
                 "tmnxSrrpOperRowStatus supports only 'active (1)', 'createAndGo
                  (4)', and 'destroy (6)'."

    ::= { tmnxSROSAgentV14v0  51 }

--
-- 7750c12 MC_REDUNDANCY CAPABILITIES
--
tmnx7750c12McRedundancyV14v0      AGENT-CAPABILITIES
    PRODUCT-RELEASE "Nokia SROS"
    STATUS          current
    DESCRIPTION
         "Implementation of the Multi-Chassis Redundancy feature on Nokia 7750
          c12 systems release 14.0."

    SUPPORTS        TIMETRA-MC-REDUNDANCY-MIB
        INCLUDES {
           tmnxMcL3RingGroup,
           tmnxMcLagPbbGroup,
           tmnxMcMobRedundancyV4v0Group,
           tmnxMcOmcrNotifGroup,
           tmnxMcPeerEPGroup,
           tmnxMcPeerEPNotifyObjsV7v0Group,
           tmnxMcPeerEPV7v0NotifGroup,
           tmnxMcPeerIPsecTnlGrpV10v0Group,
           tmnxMcPeerNotifyObjsV10v0Group,
           tmnxMcPeerSyncGroup,
           tmnxMcPeerV10v0NotifGroup,
           tmnxMcRedBgpEvpnGroup,
           tmnxMcRedBgpMHSiteGroup,
           tmnxMcRedBgpMultiHomeGroup,
           tmnxMcRedundancySrrpNotifGroup,
           tmnxMcRedundancyV10v0Group,
           tmnxMcRedundancyV12v0Group,
           tmnxMcRedundancyV13v0Group,
           tmnxMcRedundancyV14v0Group,
           tmnxMcRedundancyV5v0NotifGroup,
           tmnxMcRedundancyV9v0Group,
           tmnxMcRingV6v0Group,
           tmnxMcRingV6v0NotifGroup,
           tmnxMcTlsSapGroup,
           tmnxMcWarmStandbyGroup,
           tmnxMcsDhcpsV11v0Group,
           tmnxMcsDhcpsV6v0Group,
           tmnxMcsSubHostTrkGroup,
-- EXCLUDE tmnxSrrpNotifV6v1Group
           tmnxSrrpNotificationV10v0Group,
           tmnxSrrpV10v0Group,
           tmnxSrrpV5v0Group,
           tmnxSrrpV6v1Group,
           tmnxSrrpV8v0Group,
           tmnxSrrpV9v0Group
        }

        VARIATION   tMcPeerIPsecBfdEnableSvc
            SYNTAX  TmnxServId (0)
            DESCRIPTION
                 "tMcPeerIPsecBfdEnableSvc supports only default value of zero."

        VARIATION   tMcPeerIPsecBfdIntfDestIp
            SYNTAX  InetAddress
            DESCRIPTION
                 "tMcPeerIPsecBfdIntfDestIp supports only default value of ''H."

        VARIATION   tMcPeerIPsecBfdIntfDestIpType
            SYNTAX  InetAddressType
            DESCRIPTION
                 "tMcPeerIPsecBfdIntfDestIpType supports only default value of
                  'unknown'."

        VARIATION   tMcPeerIPsecBfdIntfIfName
            SYNTAX  TNamedItemOrEmpty
            DESCRIPTION
                 "tMcPeerIPsecBfdIntfIfName supports only default value of ''H."

        VARIATION   tMcPeerIPsecTnlGrpPreempt
            SYNTAX  INTEGER {
                    -- true                 (1)
                       false                (2)
                    }
            DESCRIPTION
                 "tMcPeerIPsecTnlGrpPreempt supports only 'false (2)' value."

        VARIATION   tmnxMcDiamPrxPeerIpAddrType
            SYNTAX  InetAddressType {
                       unknown              (0),
                       ipv4                 (1),
                       ipv6                 (2)
                    -- ipv4z                (3)
                    -- ipv6z                (4)
                    -- dns                  (16)
                    }
            DESCRIPTION
                 "tmnxMcDiamPrxPeerIpAddrType supports only the InetAddressType
                  values 'unknown (0)', 'ipv4 (1)', and 'ipv6 (2)'."

        VARIATION   tmnxMcDiamPrxRowStatus
            SYNTAX  RowStatus {
                       active               (1),
                    -- notInService         (2)
                    -- notReady             (3)
                       createAndGo          (4),
                    -- createAndWait        (5)
                       destroy              (6)
                    }
            DESCRIPTION
                 "tmnxMcDiamPrxRowStatus supports only 'active (1)',
                  'createAndGo (4)', and 'destroy (6)'."

        VARIATION   tmnxMcEpipeSapRowStatus
            SYNTAX  RowStatus {
                       active               (1),
                    -- notInService         (2)
                    -- notReady             (3)
                       createAndGo          (4),
                    -- createAndWait        (5)
                       destroy              (6)
                    }
            DESCRIPTION
                 "tmnxMcEpipeSapRowStatus supports only 'active (1)',
                  'createAndGo (4)', and 'destroy (6)'."

        VARIATION   tmnxMcL2tpPeerIpAddr
            SYNTAX  InetAddress (SIZE (0|4))
            DESCRIPTION
                 "tmnxMcL2tpPeerIpAddr supports only InetAddressType values
                  'unknown (0)' and 'ipv4 (1)'."

        VARIATION   tmnxMcL2tpPeerIpAddrType
            SYNTAX  InetAddressType {
                       unknown              (0),
                       ipv4                 (1)
                    -- ipv6                 (2)
                    -- ipv4z                (3)
                    -- ipv6z                (4)
                    -- dns                  (16)
                    }
            DESCRIPTION
                 "tmnxMcL2tpPeerIpAddrType supports only the InetAddressType
                  values 'unknown (0)' and 'ipv4 (1)'."

        VARIATION   tmnxMcL2tpRowStatus
            SYNTAX  RowStatus {
                       active               (1),
                    -- notInService         (2)
                    -- notReady             (3)
                       createAndGo          (4),
                    -- createAndWait        (5)
                       destroy              (6)
                    }
            DESCRIPTION
                 "tmnxMcL2tpRowStatus supports only 'active (1)', 'createAndGo
                  (4)', and 'destroy (6)'."

        VARIATION   tmnxMcLagConfigLagRowStatus
            SYNTAX  RowStatus {
                       active               (1),
                    -- notInService         (2)
                    -- notReady             (3)
                       createAndGo          (4),
                    -- createAndWait        (5)
                       destroy              (6)
                    }
            DESCRIPTION
                 "tmnxMcLagConfigLagRowStatus supports only 'active (1)',
                  'createAndGo (4)', and 'destroy (6)'."

        VARIATION   tmnxMcLagConfigPeerAdminstate
            SYNTAX  INTEGER {
                    -- noop                 (1)
                       inService            (2),
                       outOfService         (3)
                    }
            DESCRIPTION
                 "tmnxMcLagConfigPeerAdminstate supports only the values
                  'inService (2)' and 'outOfService (3)'."

        VARIATION   tmnxMcPeerIpType
            SYNTAX  InetAddressType {
                    -- unknown              (0)
                       ipv4                 (1),
                       ipv6                 (2)
                    -- ipv4z                (3)
                    -- ipv6z                (4)
                    -- dns                  (16)
                    }
            DESCRIPTION
                 "tmnxMcPeerIpType supports only the InetAddressType values
                  'ipv4 (1)', and 'ipv6 (2)'."

        VARIATION   tmnxMcPeerSrcIpOperType
            SYNTAX  InetAddressType {
                       unknown              (0),
                       ipv4                 (1),
                       ipv6                 (2)
                    -- ipv4z                (3)
                    -- ipv6z                (4)
                    -- dns                  (16)
                    }
            DESCRIPTION
                 "tmnxMcPeerSrcIpOperType supports only the InetAddressType
                  values 'unknown (0)', 'ipv4 (1)', and 'ipv6 (2)'."

        VARIATION   tmnxMcPeerSrcIpType
            SYNTAX  InetAddressType {
                       unknown              (0),
                       ipv4                 (1),
                       ipv6                 (2)
                    -- ipv4z                (3)
                    -- ipv6z                (4)
                    -- dns                  (16)
                    }
            DESCRIPTION
                 "tmnxMcPeerSrcIpType supports only the InetAddressType values
                  'unknown (0)', 'ipv4 (1)', and 'ipv6 (2)'."

        VARIATION   tmnxMcPeerSyncMobile
            ACCESS  not-implemented
            DESCRIPTION
                 "tmnxMcPeerSyncMobile is not implemented on Nokia 7750 c12 in
                  release 14.0."

        VARIATION   tmnxMcRingAdminState
            SYNTAX  INTEGER {
                    -- noop                 (1)
                       inService            (2),
                       outOfService         (3)
                    }
            DESCRIPTION
                 "tmnxMcRingAdminState supports only the values 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  InetAddressType {
                       unknown              (0),
                       ipv4                 (1)
                    -- ipv6                 (2)
                    -- ipv4z                (3)
                    -- ipv6z                (4)
                    -- dns                  (16)
                    }
            DESCRIPTION
                 "tmnxMcRingInbCtrlDestIpType supports only the InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  InetAddressType {
                       unknown              (0),
                       ipv4                 (1)
                    -- ipv6                 (2)
                    -- ipv4z                (3)
                    -- ipv6z                (4)
                    -- dns                  (16)
                    }
            DESCRIPTION
                 "tmnxMcRingInfoInbCtrlSrcIpType supports only the
                  InetAddressType values 'unknown (0)' and 'ipv4 (1)'."

        VARIATION   tmnxMcRingNodeRncvAdminState
            SYNTAX  INTEGER {
                    -- noop                 (1)
                       inService            (2),
                       outOfService         (3)
                    }
            DESCRIPTION
                 "tmnxMcRingNodeRncvAdminState supports only the values
                  'inService (2)' and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvDestIpType supports only the InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvSrcIpType supports only the InetAddressType
                  values 'unknown (0)' and 'ipv4 (1)'."

        VARIATION   tmnxMcRingNodeRowStatus
            SYNTAX  RowStatus {
                       active               (1),
                    -- notInService         (2)
                    -- notReady             (3)
                       createAndGo          (4),
                    -- createAndWait        (5)
                       destroy              (6)
                    }
            DESCRIPTION
                 "tmnxMcRingNodeRowStatus supports only 'active (1)',
                  'createAndGo (4)', and 'destroy (6)'."

        VARIATION   tmnxMcRingRowStatus
            SYNTAX  RowStatus {
                       active               (1),
                    -- notInService         (2)
                    -- notReady             (3)
                       createAndGo          (4),
                    -- createAndWait        (5)
                       destroy              (6)
                    }
            DESCRIPTION
                 "tmnxMcRingRowStatus supports only 'active (1)', 'createAndGo
                  (4)', and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  InetAddressType {
                       unknown              (0),
                       ipv4                 (1)
                    -- ipv6                 (2)
                    -- ipv4z                (3)
                    -- ipv6z                (4)
                    -- dns                  (16)
                    }
            DESCRIPTION
                 "tmnxMcTlsCfgDefGwIpType supports only the InetAddressType
                  values 'unknown (0)' and 'ipv4 (1)'."

        VARIATION   tmnxMcTrkSrrpPeerAddrType
            SYNTAX  InetAddressType {
                    -- unknown              (0)
                       ipv4                 (1)
                    -- ipv6                 (2)
                    -- ipv4z                (3)
                    -- ipv6z                (4)
                    -- dns                  (16)
                    }
            DESCRIPTION
                 "tmnxMcTrkSrrpPeerAddrType supports only the InetAddressType
                  value 'ipv4 (1)'."

        VARIATION   tmnxMcTrkSrrpRowStatus
            SYNTAX  RowStatus {
                       active               (1),
                    -- notInService         (2)
                    -- notReady             (3)
                       createAndGo          (4),
                    -- createAndWait        (5)
                       destroy              (6)
                    }
            DESCRIPTION
                 "tmnxMcTrkSrrpRowStatus supports only 'active (1)',
                  'createAndGo (4)', and 'destroy (6)'."

        VARIATION   tmnxMcsPyPlcyPeerIpAddrType
            SYNTAX  InetAddressType {
                       unknown              (0),
                       ipv4                 (1),
                       ipv6                 (2)
                    -- ipv4z                (3)
                    -- ipv6z                (4)
                    -- dns                  (16)
                    }
            DESCRIPTION
                 "tmnxMcsPyPlcyPeerIpAddrType supports only the InetAddressType
                  values 'unknown (0)', 'ipv4 (1)', and 'ipv6 (2)'."

        VARIATION   tmnxMcsPyPlcyRowStatus
            SYNTAX  RowStatus {
                       active               (1),
                    -- notInService         (2)
                    -- notReady             (3)
                       createAndGo          (4),
                    -- createAndWait        (5)
                       destroy              (6)
                    }
            DESCRIPTION
                 "tmnxMcsPyPlcyRowStatus supports only 'active (1)',
                  'createAndGo (4)', and 'destroy (6)'."

        VARIATION   tmnxSrrpOperAdminState
            SYNTAX  INTEGER {
                    -- noop                 (1)
                       inService            (2),
                       outOfService         (3)
                    }
            DESCRIPTION
                 "tmnxSrrpOperAdminState supports only the values 'inService
                  (2)' and 'outOfService (3)'."

        VARIATION   tmnxSrrpOperRowStatus
            SYNTAX  RowStatus {
                       active               (1),
                    -- notInService         (2)
                    -- notReady             (3)
                       createAndGo          (4),
                    -- createAndWait        (5)
                       destroy              (6)
                    }
            DESCRIPTION
                 "tmnxSrrpOperRowStatus supports only 'active (1)', 'createAndGo
                  (4)', and 'destroy (6)'."

    ::= { tmnx7750c12AgentV14v0  51 }

--
-- 7750c4 MC_REDUNDANCY CAPABILITIES
--
tmnx7750c4McRedundancyV14v0       AGENT-CAPABILITIES
    PRODUCT-RELEASE "Nokia SROS"
    STATUS          current
    DESCRIPTION
         "Implementation of the Multi-Chassis Redundancy feature on Nokia 7750
          c4 systems release 14.0."

    SUPPORTS        TIMETRA-MC-REDUNDANCY-MIB
        INCLUDES {
           tmnxMcL3RingGroup,
           tmnxMcLagPbbGroup,
           tmnxMcMobRedundancyV4v0Group,
           tmnxMcOmcrNotifGroup,
           tmnxMcPeerEPGroup,
           tmnxMcPeerEPNotifyObjsV7v0Group,
           tmnxMcPeerEPV7v0NotifGroup,
           tmnxMcPeerIPsecTnlGrpV10v0Group,
           tmnxMcPeerNotifyObjsV10v0Group,
           tmnxMcPeerSyncGroup,
           tmnxMcPeerV10v0NotifGroup,
           tmnxMcRedBgpEvpnGroup,
           tmnxMcRedBgpMHSiteGroup,
           tmnxMcRedBgpMultiHomeGroup,
           tmnxMcRedundancySrrpNotifGroup,
           tmnxMcRedundancyV10v0Group,
           tmnxMcRedundancyV12v0Group,
           tmnxMcRedundancyV13v0Group,
           tmnxMcRedundancyV14v0Group,
           tmnxMcRedundancyV5v0NotifGroup,
           tmnxMcRedundancyV9v0Group,
           tmnxMcRingV6v0Group,
           tmnxMcRingV6v0NotifGroup,
           tmnxMcTlsSapGroup,
           tmnxMcWarmStandbyGroup,
           tmnxMcsDhcpsV11v0Group,
           tmnxMcsDhcpsV6v0Group,
           tmnxMcsSubHostTrkGroup,
-- EXCLUDE tmnxSrrpNotifV6v1Group
           tmnxSrrpNotificationV10v0Group,
           tmnxSrrpV10v0Group,
           tmnxSrrpV5v0Group,
           tmnxSrrpV6v1Group,
           tmnxSrrpV8v0Group,
           tmnxSrrpV9v0Group
        }

        VARIATION   tMcPeerIPsecBfdEnableSvc
            SYNTAX  TmnxServId (0)
            DESCRIPTION
                 "tMcPeerIPsecBfdEnableSvc supports only default value of zero."

        VARIATION   tMcPeerIPsecBfdIntfDestIp
            SYNTAX  InetAddress
            DESCRIPTION
                 "tMcPeerIPsecBfdIntfDestIp supports only default value of ''H."

        VARIATION   tMcPeerIPsecBfdIntfDestIpType
            SYNTAX  InetAddressType
            DESCRIPTION
                 "tMcPeerIPsecBfdIntfDestIpType supports only default value of
                  'unknown'."

        VARIATION   tMcPeerIPsecBfdIntfIfName
            SYNTAX  TNamedItemOrEmpty
            DESCRIPTION
                 "tMcPeerIPsecBfdIntfIfName supports only default value of ''H."

        VARIATION   tMcPeerIPsecTnlGrpPreempt
            SYNTAX  INTEGER {
                    -- true                 (1)
                       false                (2)
                    }
            DESCRIPTION
                 "tMcPeerIPsecTnlGrpPreempt supports only 'false (2)' value."

        VARIATION   tmnxMcDiamPrxPeerIpAddrType
            SYNTAX  InetAddressType {
                       unknown              (0),
                       ipv4                 (1),
                       ipv6                 (2)
                    -- ipv4z                (3)
                    -- ipv6z                (4)
                    -- dns                  (16)
                    }
            DESCRIPTION
                 "tmnxMcDiamPrxPeerIpAddrType supports only the InetAddressType
                  values 'unknown (0)', 'ipv4 (1)', and 'ipv6 (2)'."

        VARIATION   tmnxMcDiamPrxRowStatus
            SYNTAX  RowStatus {
                       active               (1),
                    -- notInService         (2)
                    -- notReady             (3)
                       createAndGo          (4),
                    -- createAndWait        (5)
                       destroy              (6)
                    }
            DESCRIPTION
                 "tmnxMcDiamPrxRowStatus supports only 'active (1)',
                  'createAndGo (4)', and 'destroy (6)'."

        VARIATION   tmnxMcEpipeSapRowStatus
            SYNTAX  RowStatus {
                       active               (1),
                    -- notInService         (2)
                    -- notReady             (3)
                       createAndGo          (4),
                    -- createAndWait        (5)
                       destroy              (6)
                    }
            DESCRIPTION
                 "tmnxMcEpipeSapRowStatus supports only 'active (1)',
                  'createAndGo (4)', and 'destroy (6)'."

        VARIATION   tmnxMcL2tpPeerIpAddr
            SYNTAX  InetAddress (SIZE (0|4))
            DESCRIPTION
                 "tmnxMcL2tpPeerIpAddr supports only InetAddressType values
                  'unknown (0)' and 'ipv4 (1)'."

        VARIATION   tmnxMcL2tpPeerIpAddrType
            SYNTAX  InetAddressType {
                       unknown              (0),
                       ipv4                 (1)
                    -- ipv6                 (2)
                    -- ipv4z                (3)
                    -- ipv6z                (4)
                    -- dns                  (16)
                    }
            DESCRIPTION
                 "tmnxMcL2tpPeerIpAddrType supports only the InetAddressType
                  values 'unknown (0)' and 'ipv4 (1)'."

        VARIATION   tmnxMcL2tpRowStatus
            SYNTAX  RowStatus {
                       active               (1),
                    -- notInService         (2)
                    -- notReady             (3)
                       createAndGo          (4),
                    -- createAndWait        (5)
                       destroy              (6)
                    }
            DESCRIPTION
                 "tmnxMcL2tpRowStatus supports only 'active (1)', 'createAndGo
                  (4)', and 'destroy (6)'."

        VARIATION   tmnxMcLagConfigLagRowStatus
            SYNTAX  RowStatus {
                       active               (1),
                    -- notInService         (2)
                    -- notReady             (3)
                       createAndGo          (4),
                    -- createAndWait        (5)
                       destroy              (6)
                    }
            DESCRIPTION
                 "tmnxMcLagConfigLagRowStatus supports only 'active (1)',
                  'createAndGo (4)', and 'destroy (6)'."

        VARIATION   tmnxMcLagConfigPeerAdminstate
            SYNTAX  INTEGER {
                    -- noop                 (1)
                       inService            (2),
                       outOfService         (3)
                    }
            DESCRIPTION
                 "tmnxMcLagConfigPeerAdminstate supports only the values
                  'inService (2)' and 'outOfService (3)'."

        VARIATION   tmnxMcPeerIpType
            SYNTAX  InetAddressType {
                    -- unknown              (0)
                       ipv4                 (1),
                       ipv6                 (2)
                    -- ipv4z                (3)
                    -- ipv6z                (4)
                    -- dns                  (16)
                    }
            DESCRIPTION
                 "tmnxMcPeerIpType supports only the InetAddressType values
                  'ipv4 (1)', and 'ipv6 (2)'."

        VARIATION   tmnxMcPeerSrcIpOperType
            SYNTAX  InetAddressType {
                       unknown              (0),
                       ipv4                 (1),
                       ipv6                 (2)
                    -- ipv4z                (3)
                    -- ipv6z                (4)
                    -- dns                  (16)
                    }
            DESCRIPTION
                 "tmnxMcPeerSrcIpOperType supports only the InetAddressType
                  values 'unknown (0)', 'ipv4 (1)', and 'ipv6 (2)'."

        VARIATION   tmnxMcPeerSrcIpType
            SYNTAX  InetAddressType {
                       unknown              (0),
                       ipv4                 (1),
                       ipv6                 (2)
                    -- ipv4z                (3)
                    -- ipv6z                (4)
                    -- dns                  (16)
                    }
            DESCRIPTION
                 "tmnxMcPeerSrcIpType supports only the InetAddressType values
                  'unknown (0)', 'ipv4 (1)', and 'ipv6 (2)'."

        VARIATION   tmnxMcPeerSyncMobile
            ACCESS  not-implemented
            DESCRIPTION
                 "tmnxMcPeerSyncMobile is not implemented on Nokia 7750 c4 in
                  release 14.0."

        VARIATION   tmnxMcRingAdminState
            SYNTAX  INTEGER {
                    -- noop                 (1)
                       inService            (2),
                       outOfService         (3)
                    }
            DESCRIPTION
                 "tmnxMcRingAdminState supports only the values 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  InetAddressType {
                       unknown              (0),
                       ipv4                 (1)
                    -- ipv6                 (2)
                    -- ipv4z                (3)
                    -- ipv6z                (4)
                    -- dns                  (16)
                    }
            DESCRIPTION
                 "tmnxMcRingInbCtrlDestIpType supports only the InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  InetAddressType {
                       unknown              (0),
                       ipv4                 (1)
                    -- ipv6                 (2)
                    -- ipv4z                (3)
                    -- ipv6z                (4)
                    -- dns                  (16)
                    }
            DESCRIPTION
                 "tmnxMcRingInfoInbCtrlSrcIpType supports only the
                  InetAddressType values 'unknown (0)' and 'ipv4 (1)'."

        VARIATION   tmnxMcRingNodeRncvAdminState
            SYNTAX  INTEGER {
                    -- noop                 (1)
                       inService            (2),
                       outOfService         (3)
                    }
            DESCRIPTION
                 "tmnxMcRingNodeRncvAdminState supports only the values
                  'inService (2)' and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvDestIpType supports only the InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvSrcIpType supports only the InetAddressType
                  values 'unknown (0)' and 'ipv4 (1)'."

        VARIATION   tmnxMcRingNodeRowStatus
            SYNTAX  RowStatus {
                       active               (1),
                    -- notInService         (2)
                    -- notReady             (3)
                       createAndGo          (4),
                    -- createAndWait        (5)
                       destroy              (6)
                    }
            DESCRIPTION
                 "tmnxMcRingNodeRowStatus supports only 'active (1)',
                  'createAndGo (4)', and 'destroy (6)'."

        VARIATION   tmnxMcRingRowStatus
            SYNTAX  RowStatus {
                       active               (1),
                    -- notInService         (2)
                    -- notReady             (3)
                       createAndGo          (4),
                    -- createAndWait        (5)
                       destroy              (6)
                    }
            DESCRIPTION
                 "tmnxMcRingRowStatus supports only 'active (1)', 'createAndGo
                  (4)', and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  InetAddressType {
                       unknown              (0),
                       ipv4                 (1)
                    -- ipv6                 (2)
                    -- ipv4z                (3)
                    -- ipv6z                (4)
                    -- dns                  (16)
                    }
            DESCRIPTION
                 "tmnxMcTlsCfgDefGwIpType supports only the InetAddressType
                  values 'unknown (0)' and 'ipv4 (1)'."

        VARIATION   tmnxMcTrkSrrpPeerAddrType
            SYNTAX  InetAddressType {
                    -- unknown              (0)
                       ipv4                 (1)
                    -- ipv6                 (2)
                    -- ipv4z                (3)
                    -- ipv6z                (4)
                    -- dns                  (16)
                    }
            DESCRIPTION
                 "tmnxMcTrkSrrpPeerAddrType supports only the InetAddressType
                  value 'ipv4 (1)'."

        VARIATION   tmnxMcTrkSrrpRowStatus
            SYNTAX  RowStatus {
                       active               (1),
                    -- notInService         (2)
                    -- notReady             (3)
                       createAndGo          (4),
                    -- createAndWait        (5)
                       destroy              (6)
                    }
            DESCRIPTION
                 "tmnxMcTrkSrrpRowStatus supports only 'active (1)',
                  'createAndGo (4)', and 'destroy (6)'."

        VARIATION   tmnxMcsPyPlcyPeerIpAddrType
            SYNTAX  InetAddressType {
                       unknown              (0),
                       ipv4                 (1),
                       ipv6                 (2)
                    -- ipv4z                (3)
                    -- ipv6z                (4)
                    -- dns                  (16)
                    }
            DESCRIPTION
                 "tmnxMcsPyPlcyPeerIpAddrType supports only the InetAddressType
                  values 'unknown (0)', 'ipv4 (1)', and 'ipv6 (2)'."

        VARIATION   tmnxMcsPyPlcyRowStatus
            SYNTAX  RowStatus {
                       active               (1),
                    -- notInService         (2)
                    -- notReady             (3)
                       createAndGo          (4),
                    -- createAndWait        (5)
                       destroy              (6)
                    }
            DESCRIPTION
                 "tmnxMcsPyPlcyRowStatus supports only 'active (1)',
                  'createAndGo (4)', and 'destroy (6)'."

        VARIATION   tmnxSrrpOperAdminState
            SYNTAX  INTEGER {
                    -- noop                 (1)
                       inService            (2),
                       outOfService         (3)
                    }
            DESCRIPTION
                 "tmnxSrrpOperAdminState supports only the values 'inService
                  (2)' and 'outOfService (3)'."

        VARIATION   tmnxSrrpOperRowStatus
            SYNTAX  RowStatus {
                       active               (1),
                    -- notInService         (2)
                    -- notReady             (3)
                       createAndGo          (4),
                    -- createAndWait        (5)
                       destroy              (6)
                    }
            DESCRIPTION
                 "tmnxSrrpOperRowStatus supports only 'active (1)', 'createAndGo
                  (4)', and 'destroy (6)'."

    ::= { tmnx7750c4AgentV14v0  51 }

--
-- 7710 MC_REDUNDANCY CAPABILITIES
--
tmnx7710McRedundancyV14v0         AGENT-CAPABILITIES
    PRODUCT-RELEASE "Nokia SROS"
    STATUS          current
    DESCRIPTION
         "Implementation of the Multi-Chassis Redundancy feature on Nokia 7710
          systems release 14.0."

    SUPPORTS        TIMETRA-MC-REDUNDANCY-MIB
        INCLUDES {
           tmnxMcL3RingGroup,
           tmnxMcLagPbbGroup,
           tmnxMcMobRedundancyV4v0Group,
           tmnxMcOmcrNotifGroup,
           tmnxMcPeerEPGroup,
           tmnxMcPeerEPNotifyObjsV7v0Group,
           tmnxMcPeerEPV7v0NotifGroup,
           tmnxMcPeerIPsecTnlGrpV10v0Group,
           tmnxMcPeerNotifyObjsV10v0Group,
           tmnxMcPeerSyncGroup,
           tmnxMcPeerV10v0NotifGroup,
           tmnxMcRedBgpEvpnGroup,
           tmnxMcRedBgpMHSiteGroup,
           tmnxMcRedBgpMultiHomeGroup,
           tmnxMcRedundancySrrpNotifGroup,
           tmnxMcRedundancyV10v0Group,
           tmnxMcRedundancyV12v0Group,
           tmnxMcRedundancyV13v0Group,
           tmnxMcRedundancyV14v0Group,
           tmnxMcRedundancyV5v0NotifGroup,
           tmnxMcRedundancyV9v0Group,
           tmnxMcRingV6v0Group,
           tmnxMcRingV6v0NotifGroup,
           tmnxMcTlsSapGroup,
           tmnxMcWarmStandbyGroup,
           tmnxMcsDhcpsV11v0Group,
           tmnxMcsDhcpsV6v0Group,
           tmnxMcsSubHostTrkGroup,
-- EXCLUDE tmnxSrrpNotifV6v1Group
           tmnxSrrpNotificationV10v0Group,
           tmnxSrrpV10v0Group,
           tmnxSrrpV5v0Group,
           tmnxSrrpV6v1Group,
           tmnxSrrpV8v0Group,
           tmnxSrrpV9v0Group
        }

        VARIATION   tMcPeerIPsecBfdEnableSvc
            SYNTAX  TmnxServId (0)
            DESCRIPTION
                 "tMcPeerIPsecBfdEnableSvc supports only default value of zero."

        VARIATION   tMcPeerIPsecBfdIntfDestIp
            SYNTAX  InetAddress
            DESCRIPTION
                 "tMcPeerIPsecBfdIntfDestIp supports only default value of ''H."

        VARIATION   tMcPeerIPsecBfdIntfDestIpType
            SYNTAX  InetAddressType
            DESCRIPTION
                 "tMcPeerIPsecBfdIntfDestIpType supports only default value of
                  'unknown'."

        VARIATION   tMcPeerIPsecBfdIntfIfName
            SYNTAX  TNamedItemOrEmpty
            DESCRIPTION
                 "tMcPeerIPsecBfdIntfIfName supports only default value of ''H."

        VARIATION   tMcPeerIPsecTnlGrpPreempt
            SYNTAX  INTEGER {
                    -- true                 (1)
                       false                (2)
                    }
            DESCRIPTION
                 "tMcPeerIPsecTnlGrpPreempt supports only 'false (2)' value."

        VARIATION   tmnxMcDiamPrxPeerIpAddrType
            SYNTAX  InetAddressType {
                       unknown              (0),
                       ipv4                 (1),
                       ipv6                 (2)
                    -- ipv4z                (3)
                    -- ipv6z                (4)
                    -- dns                  (16)
                    }
            DESCRIPTION
                 "tmnxMcDiamPrxPeerIpAddrType supports only the InetAddressType
                  values 'unknown (0)', 'ipv4 (1)', and 'ipv6 (2)'."

        VARIATION   tmnxMcDiamPrxRowStatus
            SYNTAX  RowStatus {
                       active               (1),
                    -- notInService         (2)
                    -- notReady             (3)
                       createAndGo          (4),
                    -- createAndWait        (5)
                       destroy              (6)
                    }
            DESCRIPTION
                 "tmnxMcDiamPrxRowStatus supports only 'active (1)',
                  'createAndGo (4)', and 'destroy (6)'."

        VARIATION   tmnxMcEpipeSapRowStatus
            SYNTAX  RowStatus {
                       active               (1),
                    -- notInService         (2)
                    -- notReady             (3)
                       createAndGo          (4),
                    -- createAndWait        (5)
                       destroy              (6)
                    }
            DESCRIPTION
                 "tmnxMcEpipeSapRowStatus supports only 'active (1)',
                  'createAndGo (4)', and 'destroy (6)'."

        VARIATION   tmnxMcL2tpPeerIpAddr
            SYNTAX  InetAddress (SIZE (0|4))
            DESCRIPTION
                 "tmnxMcL2tpPeerIpAddr supports only InetAddressType values
                  'unknown (0)' and 'ipv4 (1)'."

        VARIATION   tmnxMcL2tpPeerIpAddrType
            SYNTAX  InetAddressType {
                       unknown              (0),
                       ipv4                 (1)
                    -- ipv6                 (2)
                    -- ipv4z                (3)
                    -- ipv6z                (4)
                    -- dns                  (16)
                    }
            DESCRIPTION
                 "tmnxMcL2tpPeerIpAddrType supports only the InetAddressType
                  values 'unknown (0)' and 'ipv4 (1)'."

        VARIATION   tmnxMcL2tpRowStatus
            SYNTAX  RowStatus {
                       active               (1),
                    -- notInService         (2)
                    -- notReady             (3)
                       createAndGo          (4),
                    -- createAndWait        (5)
                       destroy              (6)
                    }
            DESCRIPTION
                 "tmnxMcL2tpRowStatus supports only 'active (1)', 'createAndGo
                  (4)', and 'destroy (6)'."

        VARIATION   tmnxMcLagConfigLagRowStatus
            SYNTAX  RowStatus {
                       active               (1),
                    -- notInService         (2)
                    -- notReady             (3)
                       createAndGo          (4),
                    -- createAndWait        (5)
                       destroy              (6)
                    }
            DESCRIPTION
                 "tmnxMcLagConfigLagRowStatus supports only 'active (1)',
                  'createAndGo (4)', and 'destroy (6)'."

        VARIATION   tmnxMcLagConfigLagSrcBMacLSB
            ACCESS  not-implemented
            DESCRIPTION
                 "tmnxMcLagConfigLagSrcBMacLSB is not implemented on Nokia 7710
                  in release 14.0."

        VARIATION   tmnxMcLagConfigPeerAdminstate
            SYNTAX  INTEGER {
                    -- noop                 (1)
                       inService            (2),
                       outOfService         (3)
                    }
            DESCRIPTION
                 "tmnxMcLagConfigPeerAdminstate supports only the values
                  'inService (2)' and 'outOfService (3)'."

        VARIATION   tmnxMcPeerIpType
            SYNTAX  InetAddressType {
                    -- unknown              (0)
                       ipv4                 (1),
                       ipv6                 (2)
                    -- ipv4z                (3)
                    -- ipv6z                (4)
                    -- dns                  (16)
                    }
            DESCRIPTION
                 "tmnxMcPeerIpType supports only the InetAddressType values
                  'ipv4 (1)', and 'ipv6 (2)'."

        VARIATION   tmnxMcPeerSrcIpOperType
            SYNTAX  InetAddressType {
                       unknown              (0),
                       ipv4                 (1),
                       ipv6                 (2)
                    -- ipv4z                (3)
                    -- ipv6z                (4)
                    -- dns                  (16)
                    }
            DESCRIPTION
                 "tmnxMcPeerSrcIpOperType supports only the InetAddressType
                  values 'unknown (0)', 'ipv4 (1)', and 'ipv6 (2)'."

        VARIATION   tmnxMcPeerSrcIpType
            SYNTAX  InetAddressType {
                       unknown              (0),
                       ipv4                 (1),
                       ipv6                 (2)
                    -- ipv4z                (3)
                    -- ipv6z                (4)
                    -- dns                  (16)
                    }
            DESCRIPTION
                 "tmnxMcPeerSrcIpType supports only the InetAddressType values
                  'unknown (0)', 'ipv4 (1)', and 'ipv6 (2)'."

        VARIATION   tmnxMcPeerSyncMobile
            ACCESS  not-implemented
            DESCRIPTION
                 "tmnxMcPeerSyncMobile is not implemented on Nokia 7710 in
                  release 14.0."

        VARIATION   tmnxMcRingAdminState
            SYNTAX  INTEGER {
                    -- noop                 (1)
                       inService            (2),
                       outOfService         (3)
                    }
            DESCRIPTION
                 "tmnxMcRingAdminState supports only the values 'inService (2)'
                  and 'outOfService (3)'."

        VARIATION   tmnxMcRingInbCtrlDestIp
            SYNTAX  InetAddress (SIZE (0|4))
            DESCRIPTION
                 "tmnxMcRingInbCtrlDestIp supports only InetAddressType values
                  'unknown (0)' and 'ipv4 (1)'."

        VARIATION   tmnxMcRingInbCtrlDestIpType
            SYNTAX  InetAddressType {
                       unknown              (0),
                       ipv4                 (1)
                    -- ipv6                 (2)
                    -- ipv4z                (3)
                    -- ipv6z                (4)
                    -- dns                  (16)
                    }
            DESCRIPTION
                 "tmnxMcRingInbCtrlDestIpType supports only the InetAddressType
                  values 'unknown (0)' and 'ipv4 (1)'."

        VARIATION   tmnxMcRingInfoInbCtrlSrcIp
            SYNTAX  InetAddress (SIZE (0|4))
            DESCRIPTION
                 "tmnxMcRingInfoInbCtrlSrcIp supports only InetAddressType
                  values 'unknown (0)' and 'ipv4 (1)'."

        VARIATION   tmnxMcRingInfoInbCtrlSrcIpType
            SYNTAX  InetAddressType {
                       unknown              (0),
                       ipv4                 (1)
                    -- ipv6                 (2)
                    -- ipv4z                (3)
                    -- ipv6z                (4)
                    -- dns                  (16)
                    }
            DESCRIPTION
                 "tmnxMcRingInfoInbCtrlSrcIpType supports only the
                  InetAddressType values 'unknown (0)' and 'ipv4 (1)'."

        VARIATION   tmnxMcRingNodeRncvAdminState
            SYNTAX  INTEGER {
                    -- noop                 (1)
                       inService            (2),
                       outOfService         (3)
                    }
            DESCRIPTION
                 "tmnxMcRingNodeRncvAdminState supports only the values
                  'inService (2)' and 'outOfService (3)'."

        VARIATION   tmnxMcRingNodeRncvDestIp
            SYNTAX  InetAddress (SIZE (0|4))
            DESCRIPTION
                 "tmnxMcRingNodeRncvDestIp supports only InetAddressType values
                  'unknown (0)' and 'ipv4 (1)'."

        VARIATION   tmnxMcRingNodeRncvDestIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvDestIpType supports only the InetAddressType
                  values 'unknown (0)' and 'ipv4 (1)'."

        VARIATION   tmnxMcRingNodeRncvSrcIp
            SYNTAX  InetAddress (SIZE (0|4))
            DESCRIPTION
                 "tmnxMcRingNodeRncvSrcIp supports only InetAddressType values
                  'unknown (0)' and 'ipv4 (1)'."

        VARIATION   tmnxMcRingNodeRncvSrcIpType
            SYNTAX  InetAddressType {
                       unknown              (0),
                       ipv4                 (1)
                    -- ipv6                 (2)
                    -- ipv4z                (3)
                    -- ipv6z                (4)
                    -- dns                  (16)
                    }
            DESCRIPTION
                 "tmnxMcRingNodeRncvSrcIpType supports only the InetAddressType
                  values 'unknown (0)' and 'ipv4 (1)'."

        VARIATION   tmnxMcRingNodeRowStatus
            SYNTAX  RowStatus {
                       active               (1),
                    -- notInService         (2)
                    -- notReady             (3)
                       createAndGo          (4),
                    -- createAndWait        (5)
                       destroy              (6)
                    }
            DESCRIPTION
                 "tmnxMcRingNodeRowStatus supports only 'active (1)',
                  'createAndGo (4)', and 'destroy (6)'."

        VARIATION   tmnxMcRingRowStatus
            SYNTAX  RowStatus {
                       active               (1),
                    -- notInService         (2)
                    -- notReady             (3)
                       createAndGo          (4),
                    -- createAndWait        (5)
                       destroy              (6)
                    }
            DESCRIPTION
                 "tmnxMcRingRowStatus supports only 'active (1)', 'createAndGo
                  (4)', and 'destroy (6)'."

        VARIATION   tmnxMcTlsCfgDefGwIp
            SYNTAX  InetAddress (SIZE (0|4))
            DESCRIPTION
                 "tmnxMcTlsCfgDefGwIp supports only InetAddressType values
                  'unknown (0)' and 'ipv4 (1)'."

        VARIATION   tmnxMcTlsCfgDefGwIpType
            SYNTAX  InetAddressType {
                       unknown              (0),
                       ipv4                 (1)
                    -- ipv6                 (2)
                    -- ipv4z                (3)
                    -- ipv6z                (4)
                    -- dns                  (16)
                    }
            DESCRIPTION
                 "tmnxMcTlsCfgDefGwIpType supports only the InetAddressType
                  values 'unknown (0)' and 'ipv4 (1)'."

        VARIATION   tmnxMcTrkSrrpPeerAddrType
            SYNTAX  InetAddressType {
                    -- unknown              (0)
                       ipv4                 (1)
                    -- ipv6                 (2)
                    -- ipv4z                (3)
                    -- ipv6z                (4)
                    -- dns                  (16)
                    }
            DESCRIPTION
                 "tmnxMcTrkSrrpPeerAddrType supports only the InetAddressType
                  value 'ipv4 (1)'."

        VARIATION   tmnxMcTrkSrrpRowStatus
            SYNTAX  RowStatus {
                       active               (1),
                    -- notInService         (2)
                    -- notReady             (3)
                       createAndGo          (4),
                    -- createAndWait        (5)
                       destroy              (6)
                    }
            DESCRIPTION
                 "tmnxMcTrkSrrpRowStatus supports only 'active (1)',
                  'createAndGo (4)', and 'destroy (6)'."

        VARIATION   tmnxMcsPyPlcyPeerIpAddrType
            SYNTAX  InetAddressType {
                       unknown              (0),
                       ipv4                 (1),
                       ipv6                 (2)
                    -- ipv4z                (3)
                    -- ipv6z                (4)
                    -- dns                  (16)
                    }
            DESCRIPTION
                 "tmnxMcsPyPlcyPeerIpAddrType supports only the InetAddressType
                  values 'unknown (0)', 'ipv4 (1)', and 'ipv6 (2)'."

        VARIATION   tmnxMcsPyPlcyRowStatus
            SYNTAX  RowStatus {
                       active               (1),
                    -- notInService         (2)
                    -- notReady             (3)
                       createAndGo          (4),
                    -- createAndWait        (5)
                       destroy              (6)
                    }
            DESCRIPTION
                 "tmnxMcsPyPlcyRowStatus supports only 'active (1)',
                  'createAndGo (4)', and 'destroy (6)'."

        VARIATION   tmnxSrrpOperAdminState
            SYNTAX  INTEGER {
                    -- noop                 (1)
                       inService            (2),
                       outOfService         (3)
                    }
            DESCRIPTION
                 "tmnxSrrpOperAdminState supports only the values 'inService
                  (2)' and 'outOfService (3)'."

        VARIATION   tmnxSrrpOperRowStatus
            SYNTAX  RowStatus {
                       active               (1),
                    -- notInService         (2)
                    -- notReady             (3)
                       createAndGo          (4),
                    -- createAndWait        (5)
                       destroy              (6)
                    }
            DESCRIPTION
                 "tmnxSrrpOperRowStatus supports only 'active (1)', 'createAndGo
                  (4)', and 'destroy (6)'."

    ::= { tmnx7710AgentV14v0  51 }

--
-- SROS MIRROR CAPABILITIES
--
tmnxSROSMirrorV14v0               AGENT-CAPABILITIES
    PRODUCT-RELEASE "Nokia SROS"
    STATUS          current
    DESCRIPTION
         "Implementation of port mirroring capabilities for Nokia SROS systems
          release 14.0."

    SUPPORTS        TIMETRA-MIRROR-MIB
        INCLUDES {
-- EXCLUDE tMirrorBsxV6v0Group
           tMirrorDestV8v0Group,
           tMirrorDestinationR2r1RemoteSourceGroup,
           tMirrorDestinationV11v0Group,
           tMirrorDestinationV8v0Group,
           tMirrorEncapV10v0Group,
           tMirrorLiGroup,
           tMirrorLiSourceV12v0Group,
           tMirrorLiSourceV13v0Group,
           tMirrorNotifV10v0Group,
           tMirrorNotifV13v0Group,
           tMirrorNotificationsGroup,
           tMirrorRadiusLiV8v0Group,
           tMirrorSourceNotifGroup,
           tMirrorSourceNotificationsV6v0Group,
           tMirrorSourceV10v0Group
        }

        VARIATION   tMirrorDestinationEncapsulation
            SYNTAX  INTEGER {
                       ether                (1),
                       frameRelay           (2),
                       ppp                  (3),
                       atmSdu               (4),
                       satopE1              (5),
                       satopT1              (6),
                    -- satopE3              (7)
                    -- satopT3              (8)
                       cesopsn              (9),
                       cesopsnCas           (10),
                       ipOnly               (11)
                    }
            DESCRIPTION
                 "The values - 'satopE3 (7)', - 'satopT3 (8)', are invalid on a
                  SROS system, as they are not implemented."

        VARIATION   tMirrorSourceRemovedBySystem
            ACCESS  not-implemented
            DESCRIPTION
                 "tMirrorSourceRemovedBySystem notification is not implemented."

        VARIATION   tMirrorSourceSubIpAddr
            SYNTAX  InetAddress (SIZE (0|4))
            DESCRIPTION
                 "The tMirrorSourceSubIpAddr supports only InetAddressType
                  values 'unknown (0)' and 'ipv4 (1)'."

        VARIATION   tMirrorSourceSubIpAddrType
            SYNTAX  InetAddressType {
                       unknown              (0),
                       ipv4                 (1)
                    -- ipv6                 (2)
                    -- ipv4z                (3)
                    -- ipv6z                (4)
                    -- dns                  (16)
                    }
            DESCRIPTION
                 "tMirrorSourceSubIpAddrType supports only the InetAddressType
                  values 'unknown (0)' and 'ipv4 (1)'."

    ::= { tmnxSROSAgentV14v0  25 }

--
-- 7750 MIRROR CAPABILITIES
--
tmnx7750MirrorV14v0               AGENT-CAPABILITIES
    PRODUCT-RELEASE "Nokia SROS"
    STATUS          current
    DESCRIPTION
         "Implementation of port mirroring capabilities for Nokia 7750 systems
          release 14.0."

    SUPPORTS        TIMETRA-MIRROR-MIB
        INCLUDES {
           tMirrorBsxV6v0Group,
           tMirrorDestV8v0Group,
           tMirrorDestinationR2r1RemoteSourceGroup,
           tMirrorDestinationV11v0Group,
           tMirrorDestinationV8v0Group,
           tMirrorEncapV10v0Group,
           tMirrorLiGroup,
           tMirrorLiSourceV12v0Group,
           tMirrorLiSourceV13v0Group,
           tMirrorNotifV10v0Group,
           tMirrorNotifV13v0Group,
           tMirrorNotificationsGroup,
           tMirrorRadiusLiV8v0Group,
           tMirrorSourceNotifGroup,
           tMirrorSourceNotificationsV6v0Group,
           tMirrorSourceV10v0Group
        }

        VARIATION   tMirrorDestinationEncapsulation
            SYNTAX  INTEGER {
                       ether                (1),
                       frameRelay           (2),
                       ppp                  (3),
                       atmSdu               (4),
                       satopE1              (5),
                       satopT1              (6),
                    -- satopE3              (7)
                    -- satopT3              (8)
                       cesopsn              (9),
                       cesopsnCas           (10),
                       ipOnly               (11)
                    }
            DESCRIPTION
                 "The values - 'satopE3 (7)', - 'satopT3 (8)', are invalid on a
                  SROS system, as they are not implemented."

        VARIATION   tMirrorSourceRemovedBySystem
            ACCESS  not-implemented
            DESCRIPTION
                 "tMirrorSourceRemovedBySystem notification is not implemented."

        VARIATION   tMirrorSourceSubIpAddr
            SYNTAX  InetAddress (SIZE (0|4))
            DESCRIPTION
                 "The tMirrorSourceSubIpAddr supports only InetAddressType
                  values 'unknown (0)' and 'ipv4 (1)'."

        VARIATION   tMirrorSourceSubIpAddrType
            SYNTAX  InetAddressType {
                       unknown              (0),
                       ipv4                 (1)
                    -- ipv6                 (2)
                    -- ipv4z                (3)
                    -- ipv6z                (4)
                    -- dns                  (16)
                    }
            DESCRIPTION
                 "tMirrorSourceSubIpAddrType supports only the InetAddressType
                  values 'unknown (0)' and 'ipv4 (1)'."

    ::= { tmnx7750AgentV14v0  25 }

--
-- 7450 MIRROR CAPABILITIES
--
tmnx7450MirrorV14v0               AGENT-CAPABILITIES
    PRODUCT-RELEASE "Nokia SROS"
    STATUS          current
    DESCRIPTION
         "Implementation of port mirroring capabilities for Nokia 7450 systems
          release 14.0."

    SUPPORTS        TIMETRA-MIRROR-MIB
        INCLUDES {
           tMirrorBsxV6v0Group,
           tMirrorDestV8v0Group,
           tMirrorDestinationR2r1RemoteSourceGroup,
           tMirrorDestinationV11v0Group,
           tMirrorDestinationV8v0Group,
           tMirrorEncapV10v0Group,
           tMirrorLiGroup,
           tMirrorLiSourceV12v0Group,
           tMirrorLiSourceV13v0Group,
           tMirrorNotifV10v0Group,
           tMirrorNotifV13v0Group,
           tMirrorNotificationsGroup,
           tMirrorRadiusLiV8v0Group,
           tMirrorSourceNotifGroup,
           tMirrorSourceNotificationsV6v0Group,
           tMirrorSourceV10v0Group
        }

        VARIATION   tMirrorDestinationEncapsulation
            SYNTAX  INTEGER {
                       ether                (1),
                       frameRelay           (2),
                       ppp                  (3),
                       atmSdu               (4)
                    -- satopE1              (5)
                    -- satopT1              (6)
                    -- satopE3              (7)
                    -- satopT3              (8)
                    -- cesopsn              (9)
                    -- cesopsnCas           (10)
                    }
            DESCRIPTION
                 "The values - 'satopE3 (7)', - 'satopT3 (8)', are invalid on a
                  SROS system, as they are not implemented. The values -
                  'satopE1 (5)', - 'satopT1 (6)', - 'cesopsn (9)', - 'cesopsnCas
                  (10)' are invalid on a SROS 7450 system, as Circuit Emulation
                  (CEM) is not supported."

        VARIATION   tMirrorSourceRemovedBySystem
            ACCESS  not-implemented
            DESCRIPTION
                 "tMirrorSourceRemovedBySystem notification is not implemented."

        VARIATION   tMirrorSourceSubIpAddr
            SYNTAX  InetAddress (SIZE (0|4))
            DESCRIPTION
                 "The tMirrorSourceSubIpAddr supports only InetAddressType
                  values 'unknown (0)' and 'ipv4 (1)'."

        VARIATION   tMirrorSourceSubIpAddrType
            SYNTAX  InetAddressType {
                       unknown              (0),
                       ipv4                 (1)
                    -- ipv6                 (2)
                    -- ipv4z                (3)
                    -- ipv6z                (4)
                    -- dns                  (16)
                    }
            DESCRIPTION
                 "tMirrorSourceSubIpAddrType supports only the InetAddressType
                  values 'unknown (0)' and 'ipv4 (1)'."

    ::= { tmnx7450AgentV14v0  25 }

--
-- SROS MLD CAPABILITIES
--
tmnxSROSMldV14v0                  AGENT-CAPABILITIES
    PRODUCT-RELEASE "Nokia SROS"
    STATUS          current
    DESCRIPTION
         "Implementation of MLD capabilities for Nokia SROS systems release
          14.0."

    SUPPORTS        TIMETRA-MLD-MIB
        INCLUDES {
           tmnxMldGlobalGroup,
           tmnxMldGlobalV12v0Group,
           tmnxMldIfGroup,
           tmnxMldIfV12v0Group,
           tmnxMldIfV14v0Group,
           tmnxMldIfV6v1Group,
           tmnxMldIfV8v0Group,
           tmnxMldNotificationGroup,
           tmnxMldNotificationV12v0Group,
           tmnxMldNotificationV14v0Group
        }

        VARIATION   vRtrMldGrpIfMcacConstAdminState
            SYNTAX  INTEGER {
                    -- noop                 (1)
                       inService            (2),
                       outOfService         (3)
                    }
            DESCRIPTION
                 "vRtrMldGrpIfMcacConstAdminState supports only the values
                  'inService (2)' and 'outOfService (3)'."

        VARIATION   vRtrMldGrpIfRowStatus
            SYNTAX  RowStatus {
                       active               (1),
                    -- notInService         (2)
                    -- notReady             (3)
                       createAndGo          (4),
                    -- createAndWait        (5)
                       destroy              (6)
                    }
            DESCRIPTION
                 "vRtrMldGrpIfRowStatus supports only 'active (1)', 'createAndGo
                  (4)', and 'destroy (6)'."

        VARIATION   vRtrMldIfMcacConstAdminState
            SYNTAX  INTEGER {
                    -- noop                 (1)
                       inService            (2),
                       outOfService         (3)
                    }
            DESCRIPTION
                 "vRtrMldIfMcacConstAdminState supports only the values
                  'inService (2)' and 'outOfService (3)'."

        VARIATION   vRtrMldIfMcacLagRowStatus
            SYNTAX  RowStatus {
                       active               (1),
                    -- notInService         (2)
                    -- notReady             (3)
                       createAndGo          (4),
                    -- createAndWait        (5)
                       destroy              (6)
                    }
            DESCRIPTION
                 "vRtrMldIfMcacLagRowStatus supports only 'active (1)',
                  'createAndGo (4)', and 'destroy (6)'."

        VARIATION   vRtrMldIfMcacLevelRowStatus
            SYNTAX  RowStatus {
                       active               (1),
                    -- notInService         (2)
                    -- notReady             (3)
                       createAndGo          (4),
                    -- createAndWait        (5)
                       destroy              (6)
                    }
            DESCRIPTION
                 "vRtrMldIfMcacLevelRowStatus supports only 'active (1)',
                  'createAndGo (4)', and 'destroy (6)'."

        VARIATION   vRtrMldIfRowStatus
            SYNTAX  RowStatus {
                       active               (1),
                    -- notInService         (2)
                    -- notReady             (3)
                       createAndGo          (4),
                    -- createAndWait        (5)
                       destroy              (6)
                    }
            DESCRIPTION
                 "vRtrMldIfRowStatus supports only 'active (1)', 'createAndGo
                  (4)', and 'destroy (6)'."

        VARIATION   vRtrMldIfSGrpRangeSrcRowStatus
            SYNTAX  RowStatus {
                       active               (1),
                    -- notInService         (2)
                    -- notReady             (3)
                       createAndGo          (4),
                    -- createAndWait        (5)
                       destroy              (6)
                    }
            DESCRIPTION
                 "vRtrMldIfSGrpRangeSrcRowStatus supports only 'active (1)',
                  'createAndGo (4)', and 'destroy (6)'."

        VARIATION   vRtrMldIfSsmTransRowStatus
            SYNTAX  RowStatus {
                       active               (1),
                    -- notInService         (2)
                    -- notReady             (3)
                       createAndGo          (4),
                    -- createAndWait        (5)
                       destroy              (6)
                    }
            DESCRIPTION
                 "vRtrMldIfSsmTransRowStatus supports only 'active (1)',
                  'createAndGo (4)', and 'destroy (6)'."

        VARIATION   vRtrMldIfStaticGrpSrcRowStatus
            SYNTAX  RowStatus {
                       active               (1),
                    -- notInService         (2)
                    -- notReady             (3)
                       createAndGo          (4),
                    -- createAndWait        (5)
                       destroy              (6)
                    }
            DESCRIPTION
                 "vRtrMldIfStaticGrpSrcRowStatus supports only 'active (1)',
                  'createAndGo (4)', and 'destroy (6)'."

        VARIATION   vRtrMldSsmTransRowStatus
            SYNTAX  RowStatus {
                       active               (1),
                    -- notInService         (2)
                    -- notReady             (3)
                       createAndGo          (4),
                    -- createAndWait        (5)
                       destroy              (6)
                    }
            DESCRIPTION
                 "vRtrMldSsmTransRowStatus supports only 'active (1)',
                  'createAndGo (4)', and 'destroy (6)'."

    ::= { tmnxSROSAgentV14v0  59 }

--
-- SROS MLD_SNOOPING CAPABILITIES
--
tmnxSROSMldSnoopingV14v0          AGENT-CAPABILITIES
    PRODUCT-RELEASE "Nokia SROS"
    STATUS          current
    DESCRIPTION
         "Implementation of MLD snooping capabilities for Nokia SROS systems
          release 14.0."

    SUPPORTS        TIMETRA-MLD-SNOOPING-MIB
        INCLUDES {
           tmnxMldMvrGroup,
           tmnxMldSnpgConfigGroup,
           tmnxMldSnpgConfigV12v0Group,
           tmnxMldSnpgConfigV14v0Group,
           tmnxMldSnpgConfigV8v0Group,
           tmnxMldSnpgGroup,
           tmnxMldSnpgMRouterGroup,
           tmnxMldSnpgNotifyGroup,
           tmnxMldSnpgProxyGroup,
           tmnxMldSnpgQuerierGroup,
           tmnxMldSnpgStaticGroup,
           tmnxMldSnpgStatsGroup,
           tmnxMldSnpgStatsV12v0Group
        }

        VARIATION   sapMldSnpgCfgFastLeave
            SYNTAX  INTEGER {
                    -- noop                 (1)
                       inService            (2),
                       outOfService         (3)
                    }
            DESCRIPTION
                 "sapMldSnpgCfgFastLeave only supports the values 'inService
                  (2)' and 'outOfService (3)'."

        VARIATION   sapMldSnpgCfgMcacConstAdmSt
            SYNTAX  INTEGER {
                    -- noop                 (1)
                       inService            (2),
                       outOfService         (3)
                    }
            DESCRIPTION
                 "sapMldSnpgCfgMcacConstAdmSt only supports the values
                  'inService (2)' and 'outOfService (3)'."

        VARIATION   sapMldSnpgCfgSendQueries
            SYNTAX  INTEGER {
                    -- noop                 (1)
                       inService            (2),
                       outOfService         (3)
                    }
            DESCRIPTION
                 "sapMldSnpgCfgSendQueries only supports the values 'inService
                  (2)' and 'outOfService (3)'."

        VARIATION   sapMldSnpgGrpAddress
            SYNTAX  InetAddress (SIZE (16))
            DESCRIPTION
                 "sapMldSnpgGrpAddress only supports an IP address of type 'ipv6
                  (2)'."

        VARIATION   sapMldSnpgGrpAddressType
            SYNTAX  INTEGER {
                    -- unknown              (0)
                    -- ipv4                 (1)
                       ipv6                 (2)
                    -- ipv4z                (3)
                    -- ipv6z                (4)
                    -- dns                  (16)
                    }
            DESCRIPTION
                 "sapMldSnpgGrpAddressType only supports the value 'ipv6 (2)'."

        VARIATION   sapMldSnpgGrpSrcAddr
            SYNTAX  InetAddress (SIZE (16))
            DESCRIPTION
                 "sapMldSnpgGrpSrcAddr only supports an IP address of type 'ipv6
                  (2)'."

        VARIATION   sapMldSnpgGrpSrcAddrType
            SYNTAX  INTEGER {
                    -- unknown              (0)
                    -- ipv4                 (1)
                       ipv6                 (2)
                    -- ipv4z                (3)
                    -- ipv6z                (4)
                    -- dns                  (16)
                    }
            DESCRIPTION
                 "sapMldSnpgGrpSrcAddrType only supports the value 'ipv6 (2)'."

        VARIATION   sapMldSnpgStaticGroupAddr
            SYNTAX  InetAddress (SIZE (16))
            DESCRIPTION
                 "sapMldSnpgStaticGroupAddr only supports an IP address of type
                  'ipv6 (2)'."

        VARIATION   sapMldSnpgStaticGroupAddrType
            SYNTAX  INTEGER {
                    -- unknown              (0)
                    -- ipv4                 (1)
                       ipv6                 (2)
                    -- ipv4z                (3)
                    -- ipv6z                (4)
                    -- dns                  (16)
                    }
            DESCRIPTION
                 "sapMldSnpgStaticGroupAddrType only supports the value 'ipv6
                  (2)'."

        VARIATION   sapMldSnpgStaticSourceAddr
            SYNTAX  InetAddress (SIZE (16))
            DESCRIPTION
                 "sapMldSnpgStaticSourceAddr only supports an IP address of type
                  'ipv6 (2)'."

        VARIATION   sapMldSnpgStaticSourceAddrType
            SYNTAX  INTEGER {
                    -- unknown              (0)
                    -- ipv4                 (1)
                       ipv6                 (2)
                    -- ipv4z                (3)
                    -- ipv6z                (4)
                    -- dns                  (16)
                    }
            DESCRIPTION
                 "sapMldSnpgStaticSourceAddrType only supports the value 'ipv6
                  (2)'."

        VARIATION   sdpBndMldSnpgCfgFastLeave
            SYNTAX  INTEGER {
                    -- noop                 (1)
                       inService            (2),
                       outOfService         (3)
                    }
            DESCRIPTION
                 "sdpBndMldSnpgCfgFastLeave only supports the values 'inService
                  (2)' and 'outOfService (3)'."

        VARIATION   sdpBndMldSnpgCfgSendQueries
            SYNTAX  INTEGER {
                    -- noop                 (1)
                       inService            (2),
                       outOfService         (3)
                    }
            DESCRIPTION
                 "sdpBndMldSnpgCfgSendQueries only supports the values
                  'inService (2)' and 'outOfService (3)'."

        VARIATION   sdpBndMldSnpgGrpAddress
            SYNTAX  InetAddress (SIZE (16))
            DESCRIPTION
                 "sdpBndMldSnpgGrpAddress only supports an IP address of type
                  'ipv6 (2)'."

        VARIATION   sdpBndMldSnpgGrpAddressType
            SYNTAX  INTEGER {
                    -- unknown              (0)
                    -- ipv4                 (1)
                       ipv6                 (2)
                    -- ipv4z                (3)
                    -- ipv6z                (4)
                    -- dns                  (16)
                    }
            DESCRIPTION
                 "sdpBndMldSnpgGrpAddressType only supports the value 'ipv6
                  (2)'."

        VARIATION   sdpBndMldSnpgGrpSrcAddr
            SYNTAX  InetAddress (SIZE (16))
            DESCRIPTION
                 "sdpBndMldSnpgGrpSrcAddr only supports an IP address of type
                  'ipv6 (2)'."

        VARIATION   sdpBndMldSnpgGrpSrcAddrType
            SYNTAX  INTEGER {
                    -- unknown              (0)
                    -- ipv4                 (1)
                       ipv6                 (2)
                    -- ipv4z                (3)
                    -- ipv6z                (4)
                    -- dns                  (16)
                    }
            DESCRIPTION
                 "sdpBndMldSnpgGrpSrcAddrType only supports the value 'ipv6
                  (2)'."

        VARIATION   sdpBndMldSnpgStaticGroupAddr
            SYNTAX  InetAddress (SIZE (16))
            DESCRIPTION
                 "sdpBndMldSnpgStaticGroupAddr only supports an IP address of
                  type 'ipv6 (2)'."

        VARIATION   sdpBndMldSnpgStaticGroupAddrType
            SYNTAX  INTEGER {
                    -- unknown              (0)
                    -- ipv4                 (1)
                       ipv6                 (2)
                    -- ipv4z                (3)
                    -- ipv6z                (4)
                    -- dns                  (16)
                    }
            DESCRIPTION
                 "sdpBndMldSnpgStaticGroupAddrType only supports the value 'ipv6
                  (2)'."

        VARIATION   sdpBndMldSnpgStaticSourceAddr
            SYNTAX  InetAddress (SIZE (16))
            DESCRIPTION
                 "sdpBndMldSnpgStaticSourceAddr only supports an IP address of
                  type 'ipv6 (2)'."

        VARIATION   sdpBndMldSnpgStaticSourceAddrTp
            SYNTAX  INTEGER {
                    -- unknown              (0)
                    -- ipv4                 (1)
                       ipv6                 (2)
                    -- ipv4z                (3)
                    -- ipv6z                (4)
                    -- dns                  (16)
                    }
            DESCRIPTION
                 "sdpBndMldSnpgStaticSourceAddrTp only supports the value 'ipv6
                  (2)'."

        VARIATION   tlsMldSnpgCfgAdminState
            SYNTAX  INTEGER {
                    -- noop                 (1)
                       inService            (2),
                       outOfService         (3)
                    }
            DESCRIPTION
                 "tlsMldSnpgCfgAdminState only supports the values 'inService
                  (2)' and 'outOfService (3)'."

        VARIATION   tlsMldSnpgCfgMvrAdminState
            SYNTAX  INTEGER {
                    -- noop                 (1)
                       inService            (2),
                       outOfService         (3)
                    }
            DESCRIPTION
                 "tlsMldSnpgCfgMvrAdminState only supports the values 'inService
                  (2)' and 'outOfService (3)'."

        VARIATION   tlsMldSnpgMRouterAddress
            SYNTAX  InetAddress (SIZE (16))
            DESCRIPTION
                 "tlsMldSnpgMRouterAddress only supports an IP address of type
                  'ipv6 (2)'."

        VARIATION   tlsMldSnpgMRouterAddressType
            SYNTAX  INTEGER {
                    -- unknown              (0)
                    -- ipv4                 (1)
                       ipv6                 (2)
                    -- ipv4z                (3)
                    -- ipv6z                (4)
                    -- dns                  (16)
                    }
            DESCRIPTION
                 "tlsMldSnpgMRouterAddressType only supports the value 'ipv6
                  (2)'."

        VARIATION   tlsMldSnpgProxyGroupAddress
            SYNTAX  InetAddress (SIZE (16))
            DESCRIPTION
                 "tlsMldSnpgProxyGroupAddress only supports an IP address of
                  type 'ipv6 (2)'."

        VARIATION   tlsMldSnpgProxyGroupAddressType
            SYNTAX  INTEGER {
                    -- unknown              (0)
                    -- ipv4                 (1)
                       ipv6                 (2)
                    -- ipv4z                (3)
                    -- ipv6z                (4)
                    -- dns                  (16)
                    }
            DESCRIPTION
                 "tlsMldSnpgProxyGroupAddressType only supports the value 'ipv6
                  (2)'."

        VARIATION   tlsMldSnpgProxyGrpSrcAddr
            SYNTAX  InetAddress (SIZE (16))
            DESCRIPTION
                 "tlsMldSnpgProxyGrpSrcAddr only supports an IP address of type
                  'ipv6 (2)'."

        VARIATION   tlsMldSnpgProxyGrpSrcAddrTp
            SYNTAX  INTEGER {
                    -- unknown              (0)
                    -- ipv4                 (1)
                       ipv6                 (2)
                    -- ipv4z                (3)
                    -- ipv6z                (4)
                    -- dns                  (16)
                    }
            DESCRIPTION
                 "tlsMldSnpgProxyGrpSrcAddrTp only supports the value 'ipv6
                  (2)'."

        VARIATION   tlsMldSnpgQuerierAddress
            SYNTAX  InetAddress (SIZE (16))
            DESCRIPTION
                 "tlsMldSnpgQuerierAddress only supports an IP address of type
                  'ipv6 (2)'."

        VARIATION   tlsMldSnpgQuerierAddressType
            SYNTAX  INTEGER {
                    -- unknown              (0)
                    -- ipv4                 (1)
                       ipv6                 (2)
                    -- ipv4z                (3)
                    -- ipv6z                (4)
                    -- dns                  (16)
                    }
            DESCRIPTION
                 "tlsMldSnpgQuerierAddressType only supports the value 'ipv6
                  (2)'."

    ::= { tmnxSROSAgentV14v0  55 }

--
-- SROS MPLS CAPABILITIES
--
tmnxSROSMplsV14v0                 AGENT-CAPABILITIES
    PRODUCT-RELEASE "Nokia SROS"
    STATUS          current
    DESCRIPTION
         "Implementation of MPLS protocol capabilities for Nokia SROS systems
          release 14.0."

    SUPPORTS        MPLS-LSR-MIB
        INCLUDES {
-- EXCLUDE mplsHCInSegmentPerfGroup,
-- EXCLUDE mplsHCOutSegmentPerfGroup,
           mplsInSegmentGroup,
           mplsInterfaceGroup,
-- EXCLUDE mplsLabelStackGroup
           mplsLsrNotificationGroup,
           mplsOutSegmentGroup,
-- EXCLUDE mplsPerfGroup,
-- EXCLUDE mplsSegmentDiscontinuityGroup,
           mplsTrafficParamGroup,
           mplsXCGroup,
           mplsXCIsNotPersistentGroup,
           mplsXCIsPersistentGroup
        }

        VARIATION   mplsInSegmentPerfTable
            ACCESS  not-implemented
            DESCRIPTION
                 "mplsInSegmentPerfTable is not implemented on Nokia SROS in
                  release 14.0."

        VARIATION   mplsInSegmentTrafficParamPtr
            ACCESS  not-implemented
            DESCRIPTION
                 "mplsInSegmentTrafficParamPtr is not implemented on Nokia SROS
                  in release 14.0."

        VARIATION   mplsInterfaceConfStorageType
            ACCESS  read-only
            DESCRIPTION
                 "mplsInterfaceConfStorageType is implemented as read-only on
                  Nokia SROS in release 14.0."

        VARIATION   mplsOutSegmentNextHopIpv6Addr
            ACCESS  not-implemented
            DESCRIPTION
                 "IPv6 MPLS is not implemented on Nokia SROS."

        VARIATION   mplsOutSegmentPerfTable
            ACCESS  not-implemented
            DESCRIPTION
                 "mplsOutSegmentPerfTable is not implemented on Nokia SROS in
                  release 14.0."

        VARIATION   mplsOutSegmentTrafficParamPtr
            ACCESS  not-implemented
            DESCRIPTION
                 "mplsOutSegmentTrafficParamPtr is not implemented on Nokia SROS
                  in release 14.0."

        VARIATION   mplsTrafficParamMaxBurstSize
            ACCESS  read-only
            DESCRIPTION
                 "mplsTrafficParamMaxBurstSize is implemented as read-only on
                  Nokia SROS in release 14.0."

        VARIATION   mplsTrafficParamMaxRate
            ACCESS  read-only
            DESCRIPTION
                 "mplsTrafficParamMaxRate is implemented as read-only on Nokia
                  SROS in release 14.0."

        VARIATION   mplsTrafficParamMeanRate
            ACCESS  read-only
            DESCRIPTION
                 "mplsTrafficParamMeanRate is implemented as read-only on Nokia
                  SROS in release 14.0."

        VARIATION   mplsTrafficParamRowStatus
            ACCESS  read-only
            DESCRIPTION
                 "The mplsTrafficParamTable is implemented as read-only. Row
                  entries cannot be created by SNMP SET requests."

        VARIATION   mplsTrafficParamStorageType
            ACCESS  read-only
            DESCRIPTION
                 "mplsTrafficParamStorageType is implemented as read-only on
                  Nokia SROS in release 14.0."

        VARIATION   mplsXCAdminStatus
            SYNTAX  INTEGER {
                       up                   (1), -- ready to pass packets
                       down                 (2)
                    -- testing              (3)
                    }
            DESCRIPTION
                 "Write access using value 'testing (3)' is not supported."

        VARIATION   mplsXCIsPersistent
            ACCESS  read-only
            DESCRIPTION
                 "mplsXCIsPersistent is implemented as read-only on Nokia SROS
                  in release 14.0."

        VARIATION   mplsXCLabelStackIndex
            ACCESS  read-only
            DESCRIPTION
                 "mplsXCLabelStackIndex is implemented as read-only on Nokia
                  SROS in release 14.0."

        VARIATION   mplsXCLspId
            ACCESS  read-only
            DESCRIPTION
                 "mplsXCLspId is implemented as read-only on Nokia SROS in
                  release 14.0."

        VARIATION   mplsXCTrapEnable
            ACCESS  not-implemented
            DESCRIPTION
                 "Generation of MPLS traps is controlled by the TIMETRA-LOG-MIB
                  tmnxEventTable."

    SUPPORTS        MPLS-TE-MIB
        INCLUDES {
-- EXCLUDE mplsTeNotificationGroup
           mplsTunnelGroup,
           mplsTunnelIsIntfcGroup,
           mplsTunnelIsNotIntfcGroup,
           mplsTunnelManualGroup,
           mplsTunnelOptionalGroup,
           mplsTunnelSignaledGroup
        }

        VARIATION   mplsTunnelARHopAddrType
            SYNTAX  INTEGER {
                       ipV4(1),
                       ipV6(2),
                       asNumber(3),
                       unnum(4)
                    }
            DESCRIPTION
                 "The value 'unnum (4)' is used to indicate an unnumbered
                  interface identifier and
                  TIMETRA-MPLS-MIB::vRtrMplsTunnelARHopUnnumIfID should be
                  configured."

        VARIATION   mplsTunnelARHopIpv6Addr
            ACCESS  not-implemented
            DESCRIPTION
                 "mplsTunnelARHopIpv6Addr is not implemented on Nokia SROS in
                  release 14.0.

                  IPv6 MPLS is not supported."

        VARIATION   mplsTunnelARHopIpv6PrefixLen
            ACCESS  not-implemented
            DESCRIPTION
                 "mplsTunnelARHopIpv6PrefixLen is not implemented on Nokia SROS
                  in release 14.0.

                  IPv6 MPLS is not supported."

        VARIATION   mplsTunnelAdminStatus
            SYNTAX  INTEGER {
                       up                   (1), -- ready to pass packets
                       down                 (2)
                    -- testing              (3)
                    }
            DESCRIPTION
                 "Write access using value 'testing (3)' is not supported."

        VARIATION   mplsTunnelEntry
            CREATION-REQUIRES {
                       mplsTunnelRowStatus,
                       mplsTunnelName
                    }
            DESCRIPTION
                 "mplsTunnelName must be set for row creation to succeed. The
                  value of these objects cannot be changed after the row entry
                  has been created: mplsTunnelDescr, mplsTunnelIsIf,
                  mplsTunnelSignallingProto, mplsTunnelSetupPrio,
                  mplsTunnelHoldingPrio, mplsTunnelOwner,
                  mplsTunnelLocalProtectInUse, mplsTunnelResourcePointer,
                  mplsTunnelSessionAttributes, mplsTunnelInstancePriority."

        VARIATION   mplsTunnelHoldingPrio
            ACCESS  read-only
            DESCRIPTION
                 "mplsTunnelHoldingPrio is implemented as read-only on Nokia
                  SROS in release 14.0."

        VARIATION   mplsTunnelHopAsNumber
            ACCESS  not-implemented
            DESCRIPTION
                 "mplsTunnelHopAsNumber is not implemented on Nokia SROS in
                  release 14.0."

        VARIATION   mplsTunnelHopIpv6Addr
            ACCESS  not-implemented
            DESCRIPTION
                 "mplsTunnelHopIpv6Addr is not implemented on Nokia SROS in
                  release 14.0.

                  IPv6 MPLS is not supported."

        VARIATION   mplsTunnelHopIpv6PrefixLen
            ACCESS  not-implemented
            DESCRIPTION
                 "mplsTunnelHopIpv6PrefixLen is not implemented on Nokia SROS in
                  release 14.0.

                  IPv6 MPLS is not supported."

        VARIATION   mplsTunnelHopLspId
            ACCESS  not-implemented
            DESCRIPTION
                 "mplsTunnelHopLspId is not implemented on Nokia SROS in release
                  14.0."

        VARIATION   mplsTunnelHopTableIndex
            ACCESS  read-only
            DESCRIPTION
                 "mplsTunnelHopTableIndex is implemented as read-only. The value
                  of mplsTunnelHopTableIndex is the same as mplsTunnelIndex."

        VARIATION   mplsTunnelInstancePriority
            ACCESS  read-only
            DESCRIPTION
                 "mplsTunnelInstancePriority is implemented as read-only on
                  Nokia SROS in release 14.0."

        VARIATION   mplsTunnelIsIf
            ACCESS  read-only
            DESCRIPTION
                 "mplsTunnelIsIf is implemented as read-only on Nokia SROS in
                  release 14.0."

        VARIATION   mplsTunnelLocalProtectInUse
            ACCESS  read-only
            DESCRIPTION
                 "mplsTunnelLocalProtectInUse is implemented as read-only on
                  Nokia SROS in release 14.0."

        VARIATION   mplsTunnelName
            SYNTAX  DisplayString (SIZE(0..32))
            DESCRIPTION
                 "The maximum length supported for the mplsTunnelName is 32
                  characters."

        VARIATION   mplsTunnelOwner
            ACCESS  read-only
            DESCRIPTION
                 "mplsTunnelOwner is implemented as read-only on Nokia SROS in
                  release 14.0."

        VARIATION   mplsTunnelResourceIndexNext
            ACCESS  not-implemented
            DESCRIPTION
                 "mplsTunnelResourceIndexNext is not implemented on Nokia SROS
                  in release 14.0."

        VARIATION   mplsTunnelResourcePointer
            ACCESS  read-only
            DESCRIPTION
                 "mplsTunnelResourceTable is not implemented and
                  mplsTunnelResourcePointer always returns the null identifier
                  value { ccitt 0 }.

                  mplsTunnelResourcePointer is not implemented on Nokia SROS in
                  release 14.0."

        VARIATION   mplsTunnelResourceTable
            ACCESS  not-implemented
            DESCRIPTION
                 "mplsTunnelResourceTable is not implemented on Nokia SROS in
                  release 14.0."

        VARIATION   mplsTunnelRowStatus
            SYNTAX  RowStatus {
                       active               (1),
                    -- notInService         (2)
                    -- notReady             (3)
                       createAndGo          (4),
                    -- createAndWait        (5)
                       destroy              (6)
                    }
            DESCRIPTION
                 "mplsTunnelRowStatus supports only 'active (1)', 'createAndGo
                  (4)', and 'destroy (6)'."

        VARIATION   mplsTunnelSessionAttributes
            ACCESS  read-only
            DESCRIPTION
                 "mplsTunnelSessionAttributes is implemented as read-only on
                  Nokia SROS in release 14.0."

        VARIATION   mplsTunnelSetupPrio
            ACCESS  read-only
            DESCRIPTION
                 "mplsTunnelSetupPrio is implemented as read-only on Nokia SROS
                  in release 14.0."

        VARIATION   mplsTunnelSignallingProto
            ACCESS  read-only
            DESCRIPTION
                 "mplsTunnelSignallingProto is implemented as read-only on Nokia
                  SROS in release 14.0."

        VARIATION   mplsTunnelTrapEnable
            ACCESS  not-implemented
            DESCRIPTION
                 "Control of MPLS traps is managed using the tmnxEventTable in
                  the TIMETRA-LOG-MIB."

        VARIATION   mplsTunnelXCPointer
            ACCESS  not-implemented
            DESCRIPTION
                 "mplsTunnelXCPointer is not implemented on Nokia SROS in
                  release 14.0.

                  mplsTunnelXCPointer is implemented as read-only on Nokia SROS
                  in release 14.0."

    SUPPORTS        TIMETRA-MPLS-MIB
        INCLUDES {
           tmnxMplsAutoBwUnderflowGroup,
           tmnxMplsBfdOnLspV13v0Group,
           tmnxMplsBgpLabelRetentionGroup,
           tmnxMplsBypassOptGroup,
           tmnxMplsClassBasedFwdV13v0Group,
           tmnxMplsEntropyLabel14v0Group,
           tmnxMplsFRAdminGroup,
           tmnxMplsGenV12v0Group,
           tmnxMplsGlobalV11v0R4Group,
           tmnxMplsGlobalV13v0Group,
           tmnxMplsGlobalV7v0Group,
           tmnxMplsGlobalV8v0Group,
           tmnxMplsGlobalV9v0Group,
           tmnxMplsIfGroup,
           tmnxMplsIfSrlgV14v0Group,
           tmnxMplsIfV6v0Group,
           tmnxMplsIgpOverloadNotify,
           tmnxMplsLSPPathV12v0Group,
           tmnxMplsLSPV12v0Group,
           tmnxMplsLabelRangeGroup,
           tmnxMplsLabelSegRouteV13v0Group,
           tmnxMplsLabelStaticRgeV13v0Group,
           tmnxMplsLoadBalanceWtV13v0Group,
           tmnxMplsLspAutoBWFcWtGroup,
           tmnxMplsLspAutoBWV8v0Group,
           tmnxMplsLspPathV6v0Group,
           tmnxMplsLspPathV7v0Group,
           tmnxMplsLspPathV8v0Group,
           tmnxMplsLspPathV9v0R4Group,
           tmnxMplsLspStatsV7v0Group,
           tmnxMplsLspTempInStatsGroup,
           tmnxMplsLspTemplEL14v4Group,
           tmnxMplsLspTemplateGroup,
           tmnxMplsLspTemplateV8v0Group,
           tmnxMplsLspV6v0Group,
           tmnxMplsLspV7v0Group,
           tmnxMplsLspV8v0Group,
           tmnxMplsLspV9v0R4Group,
           tmnxMplsNotifV9v0R4Group,
           tmnxMplsNotificationR2r1Group,
           tmnxMplsNotificationV7v0Group,
           tmnxMplsNotificationV8v0Group,
           tmnxMplsNotifyObjsIgpOverload,
           tmnxMplsNotifyObjsV8v0Group,
           tmnxMplsNotifyV10v0Group,
           tmnxMplsP2mpInstanceGroup,
           tmnxMplsP2mpS2lGroup,
           tmnxMplsSRLfaOvrhd14v4Group,
           tmnxMplsSegRouting14v0Group,
           tmnxMplsSrlgV7v0Group,
           tmnxMplsTpGroup,
           tmnxMplsTunnelARHopGroup,
           tmnxMplsTunnelCHopGroup,
           tmnxMplsXCGroup
        }

        VARIATION   vRtrMplsGeneralOptimizeTimer
            ACCESS  read-only
            DESCRIPTION
                 "vRtrMplsGeneralOptimizeTimer is implemented as read-only on
                  Nokia SROS in release 14.0."

        VARIATION   vRtrMplsLspFRBandwidth
            ACCESS  read-only
            DESCRIPTION
                 "vRtrMplsLspFRBandwidth is implemented as read-only on Nokia
                  SROS in release 14.0."

        VARIATION   vRtrMplsLspFRObject
            ACCESS  read-only
            DESCRIPTION
                 "vRtrMplsLspFRObject is implemented as read-only on Nokia SROS
                  in release 14.0."

        VARIATION   vRtrMplsLspHoldPriority
            ACCESS  read-only
            DESCRIPTION
                 "vRtrMplsLspHoldPriority is implemented as read-only on Nokia
                  SROS in release 14.0."

        VARIATION   vRtrMplsLspOctets
            ACCESS  not-implemented
            DESCRIPTION
                 "vRtrMplsLspOctets is not implemented on Nokia SROS in release
                  14.0."

        VARIATION   vRtrMplsLspOptimizeTimer
            ACCESS  read-only
            DESCRIPTION
                 "vRtrMplsLspOptimizeTimer is implemented as read-only on Nokia
                  SROS in release 14.0."

        VARIATION   vRtrMplsLspPackets
            ACCESS  not-implemented
            DESCRIPTION
                 "vRtrMplsLspPackets is not implemented on Nokia SROS in release
                  14.0."

        VARIATION   vRtrMplsLspPathOptimizeTimer
            ACCESS  read-only
            DESCRIPTION
                 "vRtrMplsLspPathOptimizeTimer is implemented as read-only on
                  Nokia SROS in release 14.0."

        VARIATION   vRtrMplsLspPathRowStatus
            SYNTAX  RowStatus {
                       active               (1),
                    -- notInService         (2)
                    -- notReady             (3)
                       createAndGo          (4),
                    -- createAndWait        (5)
                       destroy              (6)
                    }
            DESCRIPTION
                 "vRtrMplsLspPathRowStatus supports only 'active (1)',
                  'createAndGo (4)', and 'destroy (6)'."

        VARIATION   vRtrMplsLspPathTableSpinlock
            ACCESS  not-implemented
            DESCRIPTION
                 "The vRtrMplsLspPathTableSpinlock was intended to be used for
                  control of changes to inherited attributes. There are no
                  inherited attributes in the base version of MPLS on Nokia
                  SROS."

        VARIATION   vRtrMplsLspRecord
            ACCESS  read-only
            DESCRIPTION
                 "vRtrMplsLspRecord is implemented as read-only on Nokia SROS in
                  release 14.0."

        VARIATION   vRtrMplsLspRowStatus
            SYNTAX  RowStatus {
                       active               (1),
                    -- notInService         (2)
                    -- notReady             (3)
                       createAndGo          (4),
                    -- createAndWait        (5)
                       destroy              (6)
                    }
            DESCRIPTION
                 "vRtrMplsLspRowStatus supports only 'active (1)', 'createAndGo
                  (4)', and 'destroy (6)'."

        VARIATION   vRtrMplsLspSetupPriority
            ACCESS  read-only
            DESCRIPTION
                 "vRtrMplsLspSetupPriority is implemented as read-only on Nokia
                  SROS in release 14.0."

        VARIATION   vRtrMplsLspTemplateFRMethod
            SYNTAX  INTEGER {
                    -- oneToOneBackup(1)
                       facilityBackup(2)
                    }
            DESCRIPTION
                 "For LSP templates of type P2MP, oneToOneBackup is not
                  supported."

        VARIATION   vRtrMplsLspTemplateFromAddr
            SYNTAX  InetAddress (SIZE (0|4))
            DESCRIPTION
                 "The vRtrMplsLspTemplateFromAddr supports only InetAddressType
                  values 'unknown (0)' and 'ipv4 (1)'."

        VARIATION   vRtrMplsLspTemplateFromAddrType
            SYNTAX  InetAddressType {
                       unknown              (0),
                       ipv4                 (1)
                    -- ipv6                 (2)
                    -- ipv4z                (3)
                    -- ipv6z                (4)
                    -- dns                  (16)
                    }
            DESCRIPTION
                 "vRtrMplsLspTemplateFromAddrType supports only the
                  InetAddressType values 'unknown (0)' and 'ipv4 (1)'."

        VARIATION   vRtrMplsLspTemplateRowStatus
            SYNTAX  RowStatus {
                       active               (1),
                    -- notInService         (2)
                    -- notReady             (3)
                       createAndGo          (4),
                    -- createAndWait        (5)
                       destroy              (6)
                    }
            DESCRIPTION
                 "vRtrMplsLspTemplateRowStatus supports only 'active (1)',
                  'createAndGo (4)', and 'destroy (6)'."

        VARIATION   vRtrMplsP2mpInstRowStatus
            SYNTAX  RowStatus {
                       active               (1),
                    -- notInService         (2)
                    -- notReady             (3)
                       createAndGo          (4),
                    -- createAndWait        (5)
                       destroy              (6)
                    }
            DESCRIPTION
                 "vRtrMplsP2mpInstRowStatus supports only 'active (1)',
                  'createAndGo (4)', and 'destroy (6)'."

        VARIATION   vRtrMplsS2lSubLspRowStatus
            SYNTAX  RowStatus {
                       active               (1),
                    -- notInService         (2)
                    -- notReady             (3)
                       createAndGo          (4),
                    -- createAndWait        (5)
                       destroy              (6)
                    }
            DESCRIPTION
                 "vRtrMplsS2lSubLspRowStatus supports only 'active (1)',
                  'createAndGo (4)', and 'destroy (6)'."

        VARIATION   vRtrMplsSrlgDBIfRowStatus
            SYNTAX  RowStatus {
                       active               (1),
                    -- notInService         (2)
                    -- notReady             (3)
                       createAndGo          (4),
                    -- createAndWait        (5)
                       destroy              (6)
                    }
            DESCRIPTION
                 "vRtrMplsSrlgDBIfRowStatus supports only 'active (1)',
                  'createAndGo (4)', and 'destroy (6)'."

        VARIATION   vRtrMplsSrlgDBRtrIdRowStatus
            SYNTAX  RowStatus {
                       active               (1),
                    -- notInService         (2)
                    -- notReady             (3)
                       createAndGo          (4),
                    -- createAndWait        (5)
                       destroy              (6)
                    }
            DESCRIPTION
                 "vRtrMplsSrlgDBRtrIdRowStatus supports only 'active (1)',
                  'createAndGo (4)', and 'destroy (6)'."

    SUPPORTS        TIMETRA-MPLS-TP-MIB
        INCLUDES {
           vRtrMplsTpInterfaceGroup,
           vRtrMplsTpInterfaceV14v0Group,
           vRtrMplsTpLspPathGroup,
           vRtrMplsTpLspPathMepGroup,
           vRtrMplsTpLspPathMepV12v0Group,
           vRtrMplsTpLspPathMepV14v0Group,
           vRtrMplsTpLsrCfgGroup,
           vRtrMplsTpLsrMipGroup,
           vRtrMplsTpLsrPathIdGroup,
           vRtrMplsTpNotificationGroup,
           vRtrMplsTpNotifyObjsGroup,
           vRtrMplsTpOamTemplateGroup,
           vRtrMplsTpProtectionTemplGroup,
           vRtrMplsTpSystemGroup,
           vRtrMplsTpTimeStampGroup,
           vRtrMplsTpTunnelCommandGroup,
           vRtrMplsTpTunnelTableGroup
        }

        VARIATION   vRtrMplsTpLspPathMepRowStatus
            SYNTAX  RowStatus {
                       active               (1),
                    -- notInService         (2)
                    -- notReady             (3)
                       createAndGo          (4),
                    -- createAndWait        (5)
                       destroy              (6)
                    }
            DESCRIPTION
                 "vRtrMplsTpLspPathMepRowStatus supports only 'active (1)',
                  'createAndGo (4)', and 'destroy (6)'."

        VARIATION   vRtrMplsTpLspPathRowStatus
            SYNTAX  RowStatus {
                       active               (1),
                    -- notInService         (2)
                    -- notReady             (3)
                       createAndGo          (4),
                    -- createAndWait        (5)
                       destroy              (6)
                    }
            DESCRIPTION
                 "vRtrMplsTpLspPathRowStatus supports only 'active (1)',
                  'createAndGo (4)', and 'destroy (6)'."

        VARIATION   vRtrMplsTpLsrPathIdRowStatus
            SYNTAX  RowStatus {
                       active               (1),
                    -- notInService         (2)
                    -- notReady             (3)
                       createAndGo          (4),
                    -- createAndWait        (5)
                       destroy              (6)
                    }
            DESCRIPTION
                 "vRtrMplsTpLsrPathIdRowStatus supports only 'active (1)',
                  'createAndGo (4)', and 'destroy (6)'."

        VARIATION   vRtrMplsTpLsrRowStatus
            SYNTAX  RowStatus {
                       active               (1),
                    -- notInService         (2)
                    -- notReady             (3)
                       createAndGo          (4),
                    -- createAndWait        (5)
                       destroy              (6)
                    }
            DESCRIPTION
                 "vRtrMplsTpLsrRowStatus supports only 'active (1)',
                  'createAndGo (4)', and 'destroy (6)'."

        VARIATION   vRtrMplsTpOamTmplRowStatus
            SYNTAX  RowStatus {
                       active               (1),
                    -- notInService         (2)
                    -- notReady             (3)
                       createAndGo          (4),
                    -- createAndWait        (5)
                       destroy              (6)
                    }
            DESCRIPTION
                 "vRtrMplsTpOamTmplRowStatus supports only 'active (1)',
                  'createAndGo (4)', and 'destroy (6)'."

        VARIATION   vRtrMplsTpPtcTmplRowStatus
            SYNTAX  RowStatus {
                       active               (1),
                    -- notInService         (2)
                    -- notReady             (3)
                       createAndGo          (4),
                    -- createAndWait        (5)
                       destroy              (6)
                    }
            DESCRIPTION
                 "vRtrMplsTpPtcTmplRowStatus supports only 'active (1)',
                  'createAndGo (4)', and 'destroy (6)'."

        VARIATION   vRtrMplsTpRowStatus
            SYNTAX  RowStatus {
                       active               (1),
                    -- notInService         (2)
                    -- notReady             (3)
                       createAndGo          (4),
                    -- createAndWait        (5)
                       destroy              (6)
                    }
            DESCRIPTION
                 "vRtrMplsTpRowStatus supports only 'active (1)', 'createAndGo
                  (4)', and 'destroy (6)'."

    ::= { tmnxSROSAgentV14v0  26 }

--
-- SROS MSDP CAPABILITIES
--
tmnxSROSMsdpV14v0                 AGENT-CAPABILITIES
    PRODUCT-RELEASE "Nokia SROS"
    STATUS          current
    DESCRIPTION
         "Implementation of MSDP protocol capabilities for Nokia SROS systems
          release 14.0."

    SUPPORTS        MSDP-MIB
        INCLUDES {
           msdpMIBEncapsulationGroup,
           msdpMIBGlobalsGroup,
           msdpMIBMeshGroupGroup,
           msdpMIBNotificationGroup,
           msdpMIBPeerGroup2,
           msdpMIBRPGroup,
           msdpMIBSACacheGroup
        }

        VARIATION   msdpCacheLifetime
            ACCESS  read-only
            DESCRIPTION
                 "msdpCacheLifetime is implemented as read-only on Nokia SROS in
                  release 14.0."

        VARIATION   msdpEnabled
            ACCESS  read-only
            DESCRIPTION
                 "msdpEnabled is implemented as read-only on Nokia SROS in
                  release 14.0."

        VARIATION   msdpMeshGroupStatus
            ACCESS  read-only
            DESCRIPTION
                 "msdpMeshGroupStatus is implemented as read-only on Nokia SROS
                  in release 14.0."

        VARIATION   msdpPeerConnectRetryInterval
            ACCESS  read-only
            DESCRIPTION
                 "msdpPeerConnectRetryInterval is implemented as read-only on
                  Nokia SROS in release 14.0."

        VARIATION   msdpPeerDataTtl
            ACCESS  read-only
            DESCRIPTION
                 "msdpPeerDataTtl is implemented as read-only on Nokia SROS in
                  release 14.0."

        VARIATION   msdpPeerEncapsulationType
            ACCESS  read-only
            DESCRIPTION
                 "msdpPeerEncapsulationType is implemented as read-only on Nokia
                  SROS in release 14.0."

        VARIATION   msdpPeerHoldTimeConfigured
            ACCESS  read-only
            DESCRIPTION
                 "msdpPeerHoldTimeConfigured is implemented as read-only on
                  Nokia SROS in release 14.0."

        VARIATION   msdpPeerKeepAliveConfigured
            ACCESS  read-only
            DESCRIPTION
                 "msdpPeerKeepAliveConfigured is implemented as read-only on
                  Nokia SROS in release 14.0."

        VARIATION   msdpPeerLocalAddress
            ACCESS  read-only
            DESCRIPTION
                 "msdpPeerLocalAddress is implemented as read-only on Nokia SROS
                  in release 14.0."

        VARIATION   msdpPeerStatus
            ACCESS  read-only
            DESCRIPTION
                 "msdpPeerStatus is implemented as read-only on Nokia SROS in
                  release 14.0."

        VARIATION   msdpRPAddress
            ACCESS  read-only
            DESCRIPTION
                 "msdpRPAddress is implemented as read-only on Nokia SROS in
                  release 14.0."

        VARIATION   msdpSACacheStatus
            ACCESS  read-only
            DESCRIPTION
                 "msdpSACacheStatus is implemented as read-only on Nokia SROS in
                  release 14.0."

    SUPPORTS        TIMETRA-MSDP-NG-MIB
        INCLUDES {
           tmnxMsdpNgGeneralGroup,
           tmnxMsdpNgNotificationGroup,
           tmnxMsdpNgPeerGroup,
           tmnxMsdpNgPeerGroupGroup,
           tmnxMsdpNgSAGroup,
           tmnxMsdpNgSARejGroup,
           tmnxMsdpNgSourceGroup
        }

    ::= { tmnxSROSAgentV14v0  53 }

--
-- SROS M_CAST_CAC CAPABILITIES
--
tmnxSROSMCastCacV14v0             AGENT-CAPABILITIES
    PRODUCT-RELEASE "Nokia SROS"
    STATUS          current
    DESCRIPTION
         "Implementation of the Multi-cast CAC (connection access control)
          feature on Nokia SROS systems release 14.0."

    SUPPORTS        TIMETRA-MCAST-CAC-MIB
        INCLUDES {
           tmnxMcacOperV5v0Group,
           tmnxMcacPolicyUserV5v0Group,
           tmnxMcacStatV12v0Group,
           tmnxMcacStatV5v0Group,
           tmnxMcacV12v0Group,
           tmnxMcacV14v0Group,
           tmnxMcacV5v0Group
        }

        VARIATION   tmnxMcacBdlChlEndAddr
            SYNTAX  InetAddress (SIZE (4))
            DESCRIPTION
                 "tmnxMcacBdlChlEndAddr only supports the InetAddressType value
                  'ipv4 (1)'."

        VARIATION   tmnxMcacBdlChlEndAddrType
            SYNTAX  InetAddressType {
                    -- unknown              (0)
                       ipv4                 (1)
                    -- ipv6                 (2)
                    -- ipv4z                (3)
                    -- ipv6z                (4)
                    -- dns                  (16)
                    }
            DESCRIPTION
                 "tmnxMcacBdlChlEndAddrType supports only the InetAddressType
                  value 'ipv4 (1)'."

        VARIATION   tmnxMcacBdlChlStartAddr
            SYNTAX  InetAddress (SIZE (4))
            DESCRIPTION
                 "tmnxMcacBdlChlStartAddr only supports the InetAddressType
                  value 'ipv4 (1)'."

        VARIATION   tmnxMcacBdlChlStartAddrType
            SYNTAX  InetAddressType {
                    -- unknown              (0)
                       ipv4                 (1)
                    -- ipv6                 (2)
                    -- ipv4z                (3)
                    -- ipv6z                (4)
                    -- dns                  (16)
                    }
            DESCRIPTION
                 "tmnxMcacBdlChlStartAddrType supports only the InetAddressType
                  value 'ipv4 (1)'."

        VARIATION   tmnxMcacIfPolicyAdminState
            SYNTAX  INTEGER {
                    -- noop                 (1)
                       inService            (2),
                       outOfService         (3)
                    }
            DESCRIPTION
                 "tmnxMcacIfPolicyAdminState supports only the values 'inService
                  (2)' and 'outOfService (3)'."

    ::= { tmnxSROSAgentV14v0  52 }

--
-- SROS NAT CAPABILITIES
--
tmnxSROSNatV14v0                  AGENT-CAPABILITIES
    PRODUCT-RELEASE "Nokia SROS"
    STATUS          current
    DESCRIPTION
         "Implementation of the NAT (Network Address Translation) feature on
          Nokia SROS systems release 14.0."

    SUPPORTS        TIMETRA-NAT-MIB
        INCLUDES {
           tmnxNatAccV11v0Group,
           tmnxNatActiveActiveRedGroup,
           tmnxNatDestGroup,
           tmnxNatDestinationNatGroup,
           tmnxNatDeterministicGroup,
           tmnxNatFragmentIpGroup,
           tmnxNatFwd2Group,
           tmnxNatFwdCfgGroup,
           tmnxNatIsa2Group,
           tmnxNatIsaStatGroup,
           tmnxNatIsaStatV10v0Group,
           tmnxNatIsaStatV11v0Group,
           tmnxNatIsaV12v0Group,
           tmnxNatL2AwV14v0Group,
           tmnxNatLsnSubIdentV12v0Group,
           tmnxNatLsnV12v0Group,
           tmnxNatMappingGroup,
           tmnxNatMultiPlcyGroup,
           tmnxNatNoLsnSubBlksFreeGroup,
           tmnxNatNotifyV14v0Group,
           tmnxNatPcp2Group,
           tmnxNatPcpGroup,
           tmnxNatPlV11v0Group,
           tmnxNatPlV13v0Group,
           tmnxNatPlcyGroup,
           tmnxNatPlcyStatGroup,
           tmnxNatPlcyV10v0Group,
           tmnxNatPlcyV14v0Group,
           tmnxNatPlcyV9v0Group,
           tmnxNatPlcyXmppEnhGroup,
           tmnxNatQryGroup,
           tmnxNatRedGroup,
           tmnxNatUpnpV14v0Group,
           tmnxNatVrtrGroup,
           tmnxNatVrtrIPFilterGroup,
           tmnxNatVrtrIPFilterV12v0Group,
           tmnxNatVrtrIPFilterV14v0Group,
           tmnxNatVrtrIPv6FilterV13v0Group,
           tmnxNatVrtrV9v0Group,
           tmnxNatWlanGwGroup,
           tmnxNatWlanGwV14v0Group
        }

        VARIATION   tmnxNat64InAdminState
            SYNTAX  INTEGER {
                    -- noop                 (1)
                       inService            (2),
                       outOfService         (3)
                    }
            DESCRIPTION
                 "tmnxNat64InAdminState supports only the values 'inService (2)'
                  and 'outOfService (3)'."

        VARIATION   tmnxNat64RowStatus
            SYNTAX  RowStatus {
                       active               (1),
                    -- notInService         (2)
                    -- notReady             (3)
                       createAndGo          (4),
                    -- createAndWait        (5)
                       destroy              (6)
                    }
            DESCRIPTION
                 "tmnxNat64RowStatus supports only 'active (1)', 'createAndGo
                  (4)', and 'destroy (6)'."

        VARIATION   tmnxNatClsfrN3RowStatus
            SYNTAX  RowStatus {
                       active               (1),
                    -- notInService         (2)
                    -- notReady             (3)
                       createAndGo          (4),
                    -- createAndWait        (5)
                       destroy              (6)
                    }
            DESCRIPTION
                 "tmnxNatClsfrN3RowStatus supports only 'active (1)',
                  'createAndGo (4)', and 'destroy (6)'."

        VARIATION   tmnxNatClsfrRowStatus
            SYNTAX  RowStatus {
                       active               (1),
                    -- notInService         (2)
                    -- notReady             (3)
                       createAndGo          (4),
                    -- createAndWait        (5)
                       destroy              (6)
                    }
            DESCRIPTION
                 "tmnxNatClsfrRowStatus supports only 'active (1)', 'createAndGo
                  (4)', and 'destroy (6)'."

        VARIATION   tmnxNatDestRowStatus
            SYNTAX  RowStatus {
                       active               (1),
                    -- notInService         (2)
                    -- notReady             (3)
                       createAndGo          (4),
                    -- createAndWait        (5)
                       destroy              (6)
                    }
            DESCRIPTION
                 "tmnxNatDestRowStatus supports only 'active (1)', 'createAndGo
                  (4)', and 'destroy (6)'."

        VARIATION   tmnxNatDetMapRowStatus
            SYNTAX  RowStatus {
                       active               (1),
                    -- notInService         (2)
                    -- notReady             (3)
                       createAndGo          (4),
                    -- createAndWait        (5)
                       destroy              (6)
                    }
            DESCRIPTION
                 "tmnxNatDetMapRowStatus supports only 'active (1)',
                  'createAndGo (4)', and 'destroy (6)'."

        VARIATION   tmnxNatDetPlcyAdminState
            SYNTAX  INTEGER {
                    -- noop                 (1)
                       inService            (2),
                       outOfService         (3)
                    }
            DESCRIPTION
                 "tmnxNatDetPlcyAdminState supports only the values 'inService
                  (2)' and 'outOfService (3)'."

        VARIATION   tmnxNatDetPlcyRowStatus
            SYNTAX  RowStatus {
                       active               (1),
                    -- notInService         (2)
                    -- notReady             (3)
                       createAndGo          (4),
                    -- createAndWait        (5)
                       destroy              (6)
                    }
            DESCRIPTION
                 "tmnxNatDetPlcyRowStatus supports only 'active (1)',
                  'createAndGo (4)', and 'destroy (6)'."

        VARIATION   tmnxNatDsliteAddrRowStatus
            SYNTAX  RowStatus {
                       active               (1),
                    -- notInService         (2)
                    -- notReady             (3)
                       createAndGo          (4),
                    -- createAndWait        (5)
                       destroy              (6)
                    }
            DESCRIPTION
                 "tmnxNatDsliteAddrRowStatus supports only 'active (1)',
                  'createAndGo (4)', and 'destroy (6)'."

        VARIATION   tmnxNatFwdActionProtocol
            SYNTAX  Unsigned32 (6|17)
            DESCRIPTION
                 "The only values supported are six (TCP) and seventeen (UDP)."

        VARIATION   tmnxNatIsaGrpAdminState
            SYNTAX  INTEGER {
                    -- noop                 (1)
                       inService            (2),
                       outOfService         (3)
                    }
            DESCRIPTION
                 "tmnxNatIsaGrpAdminState supports only the values 'inService
                  (2)' and 'outOfService (3)'."

        VARIATION   tmnxNatIsaGrpRowStatus
            SYNTAX  RowStatus {
                       active               (1),
                    -- notInService         (2)
                    -- notReady             (3)
                       createAndGo          (4),
                    -- createAndWait        (5)
                       destroy              (6)
                    }
            DESCRIPTION
                 "tmnxNatIsaGrpRowStatus supports only 'active (1)',
                  'createAndGo (4)', and 'destroy (6)'."

        VARIATION   tmnxNatIsaMdaRowStatus
            SYNTAX  RowStatus {
                       active               (1),
                    -- notInService         (2)
                    -- notReady             (3)
                       createAndGo          (4),
                    -- createAndWait        (5)
                       destroy              (6)
                    }
            DESCRIPTION
                 "tmnxNatIsaMdaRowStatus supports only 'active (1)',
                  'createAndGo (4)', and 'destroy (6)'."

        VARIATION   tmnxNatL2AwAddrRowStatus
            SYNTAX  RowStatus {
                       active               (1),
                    -- notInService         (2)
                    -- notReady             (3)
                       createAndGo          (4),
                    -- createAndWait        (5)
                       destroy              (6)
                    }
            DESCRIPTION
                 "tmnxNatL2AwAddrRowStatus supports only 'active (1)',
                  'createAndGo (4)', and 'destroy (6)'."

        VARIATION   tmnxNatMapDomAdminState
            SYNTAX  INTEGER {
                    -- noop                 (1)
                       inService            (2),
                       outOfService         (3)
                    }
            DESCRIPTION
                 "tmnxNatMapDomAdminState supports only the values 'inService
                  (2)' and 'outOfService (3)'."

        VARIATION   tmnxNatMapDomRowStatus
            SYNTAX  RowStatus {
                       active               (1),
                    -- notInService         (2)
                    -- notReady             (3)
                       createAndGo          (4),
                    -- createAndWait        (5)
                       destroy              (6)
                    }
            DESCRIPTION
                 "tmnxNatMapDomRowStatus supports only 'active (1)',
                  'createAndGo (4)', and 'destroy (6)'."

        VARIATION   tmnxNatMapRuleAdminState
            SYNTAX  INTEGER {
                    -- noop                 (1)
                       inService            (2),
                       outOfService         (3)
                    }
            DESCRIPTION
                 "tmnxNatMapRuleAdminState supports only the values 'inService
                  (2)' and 'outOfService (3)'."

        VARIATION   tmnxNatMapRuleRowStatus
            SYNTAX  RowStatus {
                       active               (1),
                    -- notInService         (2)
                    -- notReady             (3)
                       createAndGo          (4),
                    -- createAndWait        (5)
                       destroy              (6)
                    }
            DESCRIPTION
                 "tmnxNatMapRuleRowStatus supports only 'active (1)',
                  'createAndGo (4)', and 'destroy (6)'."

        VARIATION   tmnxNatMapVrtrDomRowStatus
            SYNTAX  RowStatus {
                       active               (1),
                    -- notInService         (2)
                    -- notReady             (3)
                       createAndGo          (4),
                    -- createAndWait        (5)
                       destroy              (6)
                    }
            DESCRIPTION
                 "tmnxNatMapVrtrDomRowStatus supports only 'active (1)',
                  'createAndGo (4)', and 'destroy (6)'."

        VARIATION   tmnxNatPcpPlcyRowStatus
            SYNTAX  RowStatus {
                       active               (1),
                    -- notInService         (2)
                    -- notReady             (3)
                       createAndGo          (4),
                    -- createAndWait        (5)
                       destroy              (6)
                    }
            DESCRIPTION
                 "tmnxNatPcpPlcyRowStatus supports only 'active (1)',
                  'createAndGo (4)', and 'destroy (6)'."

        VARIATION   tmnxNatPcpSrvAdminState
            SYNTAX  INTEGER {
                    -- noop                 (1)
                       inService            (2),
                       outOfService         (3)
                    }
            DESCRIPTION
                 "tmnxNatPcpSrvAdminState supports only the values 'inService
                  (2)' and 'outOfService (3)'."

        VARIATION   tmnxNatPcpSrvIfRowStatus
            SYNTAX  RowStatus {
                       active               (1),
                    -- notInService         (2)
                    -- notReady             (3)
                       createAndGo          (4),
                    -- createAndWait        (5)
                       destroy              (6)
                    }
            DESCRIPTION
                 "tmnxNatPcpSrvIfRowStatus supports only 'active (1)',
                  'createAndGo (4)', and 'destroy (6)'."

        VARIATION   tmnxNatPcpSrvRowStatus
            SYNTAX  RowStatus {
                       active               (1),
                    -- notInService         (2)
                    -- notReady             (3)
                       createAndGo          (4),
                    -- createAndWait        (5)
                       destroy              (6)
                    }
            DESCRIPTION
                 "tmnxNatPcpSrvRowStatus supports only 'active (1)',
                  'createAndGo (4)', and 'destroy (6)'."

        VARIATION   tmnxNatPlAdminState
            SYNTAX  INTEGER {
                    -- noop                 (1)
                       inService            (2),
                       outOfService         (3)
                    }
            DESCRIPTION
                 "tmnxNatPlAdminState supports only the values 'inService (2)'
                  and 'outOfService (3)'."

        VARIATION   tmnxNatPlLsnRedExpPrefix
            SYNTAX  InetAddress (SIZE(0|4))
            DESCRIPTION
                 "Only empty or IPv4 addresses are allowed."

        VARIATION   tmnxNatPlLsnRedExpPrefixType
            SYNTAX  InetAddressType {
                       unknown              (0),
                       ipv4                 (1)
                    -- ipv6                 (2)
                    -- ipv4z                (3)
                    -- ipv6z                (4)
                    -- dns                  (16)
                    }
            DESCRIPTION
                 "tmnxNatPlLsnRedExpPrefixType supports only the InetAddressType
                  values 'unknown (0)' and 'ipv4 (1)'."

        VARIATION   tmnxNatPlLsnRedMonPrefix
            SYNTAX  InetAddress (SIZE(0|4))
            DESCRIPTION
                 "Only empty or IPv4 addresses are allowed."

        VARIATION   tmnxNatPlLsnRedMonPrefixType
            SYNTAX  InetAddressType {
                       unknown              (0),
                       ipv4                 (1)
                    -- ipv6                 (2)
                    -- ipv4z                (3)
                    -- ipv6z                (4)
                    -- dns                  (16)
                    }
            DESCRIPTION
                 "tmnxNatPlLsnRedMonPrefixType supports only the InetAddressType
                  values 'unknown (0)' and 'ipv4 (1)'."

        VARIATION   tmnxNatPlPortResvAllowPrivileged
            SYNTAX  INTEGER {
                    -- true                 (1)
                       false(2)
                    }
            DESCRIPTION
                 "The only allowed value for this object is 'false (2)'."

        VARIATION   tmnxNatPlRangeRowStatus
            SYNTAX  RowStatus {
                       active               (1),
                    -- notInService         (2)
                    -- notReady             (3)
                       createAndGo          (4),
                    -- createAndWait        (5)
                       destroy              (6)
                    }
            DESCRIPTION
                 "tmnxNatPlRangeRowStatus supports only 'active (1)',
                  'createAndGo (4)', and 'destroy (6)'."

        VARIATION   tmnxNatPlRowStatus
            SYNTAX  RowStatus {
                       active               (1),
                    -- notInService         (2)
                    -- notReady             (3)
                       createAndGo          (4),
                    -- createAndWait        (5)
                       destroy              (6)
                    }
            DESCRIPTION
                 "tmnxNatPlRowStatus supports only 'active (1)', 'createAndGo
                  (4)', and 'destroy (6)'."

        VARIATION   tmnxNatPlcyFiltering
            SYNTAX  INTEGER {
                       endpointIndependent  (0),
                       addressAndPortDependent (2)
                    }
            DESCRIPTION
                 "The only allowed values for this object are
                  'endpointIndependent (0)' and 'addressAndPortDependent (2)'."

        VARIATION   tmnxNatPlcyRowStatus
            SYNTAX  RowStatus {
                       active               (1),
                    -- notInService         (2)
                    -- notReady             (3)
                       createAndGo          (4),
                    -- createAndWait        (5)
                       destroy              (6)
                    }
            DESCRIPTION
                 "tmnxNatPlcyRowStatus supports only 'active (1)', 'createAndGo
                  (4)', and 'destroy (6)'."

        VARIATION   tmnxNatSubIdAdminState
            SYNTAX  INTEGER {
                    -- noop                 (1)
                       inService            (2),
                       outOfService         (3)
                    }
            DESCRIPTION
                 "tmnxNatSubIdAdminState supports only the values 'inService
                  (2)' and 'outOfService (3)'."

        VARIATION   tmnxNatVrtrInDsliteAdminState
            SYNTAX  INTEGER {
                    -- noop                 (1)
                       inService            (2),
                       outOfService         (3)
                    }
            DESCRIPTION
                 "tmnxNatVrtrInDsliteAdminState supports only the values
                  'inService (2)' and 'outOfService (3)'."

        VARIATION   tmnxNatVrtrInRedPeerAddr
            SYNTAX  InetAddress (SIZE(0|4))
            DESCRIPTION
                 "Only empty or IPv4 addresses are allowed."

        VARIATION   tmnxNatVrtrInRedPeerAddrType
            SYNTAX  InetAddressType {
                       unknown              (0),
                       ipv4                 (1)
                    -- ipv6                 (2)
                    -- ipv4z                (3)
                    -- ipv6z                (4)
                    -- dns                  (16)
                    }
            DESCRIPTION
                 "tmnxNatVrtrInRedPeerAddrType supports only the InetAddressType
                  values 'unknown (0)' and 'ipv4 (1)'."

        VARIATION   tmnxNatVrtrInRedSteerRt
            SYNTAX  InetAddress (SIZE(0|4))
            DESCRIPTION
                 "Only empty or IPv4 addresses are allowed."

        VARIATION   tmnxNatVrtrInRedSteerRtType
            SYNTAX  InetAddressType {
                       unknown              (0),
                       ipv4                 (1)
                    -- ipv6                 (2)
                    -- ipv4z                (3)
                    -- ipv6z                (4)
                    -- dns                  (16)
                    }
            DESCRIPTION
                 "tmnxNatVrtrInRedSteerRtType supports only the InetAddressType
                  values 'unknown (0)' and 'ipv4 (1)'."

        VARIATION   tmnxNatVrtrRowStatus
            SYNTAX  RowStatus {
                       active               (1),
                    -- notInService         (2)
                    -- notReady             (3)
                       createAndGo          (4),
                    -- createAndWait        (5)
                       destroy              (6)
                    }
            DESCRIPTION
                 "tmnxNatVrtrRowStatus supports only 'active (1)', 'createAndGo
                  (4)', and 'destroy (6)'."

    ::= { tmnxSROSAgentV14v0  71 }

--
-- 7750c12 NAT CAPABILITIES
--
tmnx7750c12NatV14v0               AGENT-CAPABILITIES
    PRODUCT-RELEASE "Nokia SROS"
    STATUS          current
    DESCRIPTION
         "Implementation of the NAT (Network Address Translation) feature on
          Nokia 7750 c12 systems release 14.0."

--    SUPPORTS        TIMETRA-NAT-MIB
--        INCLUDES {
--        }

    ::= { tmnx7750c12AgentV14v0  71 }

--
-- 7750c4 NAT CAPABILITIES
--
tmnx7750c4NatV14v0                AGENT-CAPABILITIES
    PRODUCT-RELEASE "Nokia SROS"
    STATUS          current
    DESCRIPTION
         "Implementation of the NAT (Network Address Translation) feature on
          Nokia 7750 c4 systems release 14.0."

--    SUPPORTS        TIMETRA-NAT-MIB
--        INCLUDES {
--        }

    ::= { tmnx7750c4AgentV14v0  71 }

--
-- 7450 NAT CAPABILITIES
--
tmnx7450NatV14v0                  AGENT-CAPABILITIES
    PRODUCT-RELEASE "Nokia SROS"
    STATUS          current
    DESCRIPTION
         "Implementation of the NAT (Network Address Translation) feature on
          Nokia 7450 systems release 14.0."

--    SUPPORTS        TIMETRA-NAT-MIB
--        INCLUDES {
--        }

    ::= { tmnx7450AgentV14v0  71 }

--
-- 7950 NAT CAPABILITIES
--
tmnx7950NatV14v0                  AGENT-CAPABILITIES
    PRODUCT-RELEASE "Nokia SROS"
    STATUS          current
    DESCRIPTION
         "Implementation of the NAT (Network Address Translation) feature on
          Nokia 7950 systems release 14.0."

--    SUPPORTS        TIMETRA-NAT-MIB
--        INCLUDES {
--        }

    ::= { tmnx7950AgentV14v0  71 }

--
-- SROS NTP CAPABILITIES
--
tmnxSROSNtpV14v0                  AGENT-CAPABILITIES
    PRODUCT-RELEASE "Nokia SROS"
    STATUS          current
    DESCRIPTION
         "Implementation of NTP capabilities for Nokia SROS systems release
          14.0."

    SUPPORTS        TIMETRA-NTP-MIB
        INCLUDES {
           tmnxNtpAuthKeyGroup,
           tmnxNtpBroadcastGroup,
           tmnxNtpGlobalV8v0Group,
           tmnxNtpMulticastGroup,
           tmnxNtpNotificationV6v0Group,
           tmnxNtpPeersGroup,
           tmnxNtpServersGroup,
           tmnxNtpV8v0Group
        }

        VARIATION   tmnxNtpAuthKeyEntry
            CREATION-REQUIRES {
                       tmnxNtpAuthKeyType
                    }
            DESCRIPTION
                 "A value must be set for tmnxNtpAuthKeyType in order for
                  tmnxNtpAuthKeyEntryStatus to successfully transition to the
                  'active' state."

        VARIATION   tmnxNtpAuthKeyType
            SYNTAX  INTEGER {
                    -- des                  (1)
                       messageDigest        (2)
                    }
            DESCRIPTION
                 "The tmnxNtpAuthKeyType supports only 'messageDigest (2)'."

        VARIATION   tmnxNtpMaxFreqDftExceed
            ACCESS  not-implemented
            DESCRIPTION
                 "tmnxNtpMaxFreqDftExceed is not implemented on Nokia SROS in
                  release 14.0.

                  This notification was made obsolete in 4.0 R-12 release and
                  5.0 R-2 release."

        VARIATION   tmnxNtpMulticastAddress
            SYNTAX  InetAddress (SIZE (4))
            DESCRIPTION
                 "tmnxNtpMulticastAddress supports only InetAddressType 'ipv4'."

        VARIATION   tmnxNtpMulticastAddressType
            SYNTAX  InetAddressType {
                    -- unknown              (0)
                       ipv4                 (1)
                    -- ipv6                 (2)
                    -- ipv4z                (3)
                    -- ipv6z                (4)
                    -- dns                  (16)
                    }
            DESCRIPTION
                 "tmnxNtpMulticastAddressType supports only the InetAddressType
                  value 'ipv4 (1)'."

        VARIATION   tmnxNtpPeersAddrType
            SYNTAX  InetAddressType {
                    -- unknown              (0)
                       ipv4                 (1)
                    -- ipv6                 (2)
                    -- ipv4z                (3)
                    -- ipv6z                (4)
                    -- dns                  (16)
                    }
            DESCRIPTION
                 "tmnxNtpPeersAddrType supports only the InetAddressType value
                  'ipv4 (1)'."

        VARIATION   tmnxNtpPeersAddress
            SYNTAX  InetAddress (SIZE (4))
            DESCRIPTION
                 "tmnxNtpPeersAddress supports only InetAddressType 'ipv4'."

        VARIATION   tmnxNtpPeersPeerAddrType
            SYNTAX  InetAddressType {
                    -- unknown              (0)
                       ipv4                 (1)
                    -- ipv6                 (2)
                    -- ipv4z                (3)
                    -- ipv6z                (4)
                    -- dns                  (16)
                    }
            DESCRIPTION
                 "tmnxNtpPeersPeerAddrType supports only the InetAddressType
                  value 'ipv4 (1)'."

        VARIATION   tmnxNtpPeersPeerAddress
            SYNTAX  InetAddress (SIZE (4))
            DESCRIPTION
                 "tmnxNtpPeersPeerAddress supports only InetAddressType 'ipv4'."

        VARIATION   tmnxNtpServersAddrType
            SYNTAX  InetAddressType {
                    -- unknown              (0)
                       ipv4                 (1)
                    -- ipv6                 (2)
                    -- ipv4z                (3)
                    -- ipv6z                (4)
                    -- dns                  (16)
                    }
            DESCRIPTION
                 "tmnxNtpServersAddrType supports only the InetAddressType value
                  'ipv4 (1)'."

        VARIATION   tmnxNtpServersAddress
            SYNTAX  InetAddress (SIZE (4))
            DESCRIPTION
                 "tmnxNtpServersAddress supports only InetAddressType 'ipv4'."

        VARIATION   tmnxNtpUtcOffsetExThreshold
            ACCESS  not-implemented
            DESCRIPTION
                 "tmnxNtpUtcOffsetExThreshold is not implemented on Nokia SROS
                  in release 14.0.

                  This notification was made obsolete in 4.0 R-12 release and
                  5.0 R-2 release."

        VARIATION   tmnxNtpUtcOffsetInThreshold
            ACCESS  not-implemented
            DESCRIPTION
                 "tmnxNtpUtcOffsetInThreshold is not implemented on Nokia SROS
                  in release 14.0.

                  This notification was made obsolete in 4.0 R-12 release and
                  5.0 R-2 release."

    ::= { tmnxSROSAgentV14v0  46 }

--
-- SROS OAM_PM CAPABILITIES
--
tmnxSROSOamPmV14v0                AGENT-CAPABILITIES
    PRODUCT-RELEASE "Nokia SROS"
    STATUS          current
    DESCRIPTION
         "Implementation of OAM Performance Monitoring capabilities for Nokia
          SROS systems release 14.0."

    SUPPORTS        TIMETRA-OAM-PM-MIB
        INCLUDES {
           tmnxOamPmV12v0ObjGroup,
           tmnxOamPmV13v0NotifGroup,
           tmnxOamPmV13v0NotifyObjsGroup,
           tmnxOamPmV13v0ObjGroup,
           tmnxOamPmV14v0NotifyObjsGroup,
           tmnxOamPmV14v0ObjGroup
        }

        VARIATION   tmnxOamPmCfgBinGroupRowStatus
            SYNTAX  RowStatus {
                       active               (1),
                    -- notInService         (2)
                    -- notReady             (3)
                       createAndGo          (4),
                    -- createAndWait        (5)
                       destroy              (6)
                    }
            DESCRIPTION
                 "tmnxOamPmCfgBinGroupRowStatus supports only 'active (1)',
                  'createAndGo (4)', and 'destroy (6)'."

        VARIATION   tmnxOamPmCfgDelayDmmRowStatus
            SYNTAX  RowStatus {
                       active               (1),
                    -- notInService         (2)
                    -- notReady             (3)
                       createAndGo          (4),
                    -- createAndWait        (5)
                       destroy              (6)
                    }
            DESCRIPTION
                 "tmnxOamPmCfgDelayDmmRowStatus supports only 'active (1)',
                  'createAndGo (4)', and 'destroy (6)'."

        VARIATION   tmnxOamPmCfgLossLmmRowStatus
            SYNTAX  RowStatus {
                       active               (1),
                    -- notInService         (2)
                    -- notReady             (3)
                       createAndGo          (4),
                    -- createAndWait        (5)
                       destroy              (6)
                    }
            DESCRIPTION
                 "tmnxOamPmCfgLossLmmRowStatus supports only 'active (1)',
                  'createAndGo (4)', and 'destroy (6)'."

        VARIATION   tmnxOamPmCfgLossSlmRowStatus
            SYNTAX  RowStatus {
                       active               (1),
                    -- notInService         (2)
                    -- notReady             (3)
                       createAndGo          (4),
                    -- createAndWait        (5)
                       destroy              (6)
                    }
            DESCRIPTION
                 "tmnxOamPmCfgLossSlmRowStatus supports only 'active (1)',
                  'createAndGo (4)', and 'destroy (6)'."

        VARIATION   tmnxOamPmCfgMeasIntvlRowStatus
            SYNTAX  RowStatus {
                       active               (1),
                    -- notInService         (2)
                    -- notReady             (3)
                       createAndGo          (4),
                    -- createAndWait        (5)
                       destroy              (6)
                    }
            DESCRIPTION
                 "tmnxOamPmCfgMeasIntvlRowStatus supports only 'active (1)',
                  'createAndGo (4)', and 'destroy (6)'."

        VARIATION   tmnxOamPmCfgSessIpDstAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpDstAddressType supports only the
                  InetAddressType values 'unknown (0)', 'ipv4 (1)', and 'ipv6
                  (2)'."

        VARIATION   tmnxOamPmCfgSessIpNhAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpNhAddressType supports only the
                  InetAddressType values 'unknown (0)', 'ipv4 (1)', and 'ipv6
                  (2)'."

        VARIATION   tmnxOamPmCfgSessIpSrcAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpSrcAddressType supports only the
                  InetAddressType values 'unknown (0)', 'ipv4 (1)', and 'ipv6
                  (2)'."

        VARIATION   tmnxOamPmCfgSessRowStatus
            SYNTAX  RowStatus {
                       active               (1),
                    -- notInService         (2)
                    -- notReady             (3)
                       createAndGo          (4),
                    -- createAndWait        (5)
                       destroy              (6)
                    }
            DESCRIPTION
                 "tmnxOamPmCfgSessRowStatus supports only 'active (1)',
                  'createAndGo (4)', and 'destroy (6)'."

        VARIATION   tmnxOamPmCfgTwampLtRowStatus
            SYNTAX  RowStatus {
                       active               (1),
                    -- notInService         (2)
                    -- notReady             (3)
                       createAndGo          (4),
                    -- createAndWait        (5)
                       destroy              (6)
                    }
            DESCRIPTION
                 "tmnxOamPmCfgTwampLtRowStatus supports only 'active (1)',
                  'createAndGo (4)', and 'destroy (6)'."

        VARIATION   tmnxOamPmCfgTwlRflPfxRowStatus
            SYNTAX  RowStatus {
                       active               (1),
                    -- notInService         (2)
                    -- notReady             (3)
                       createAndGo          (4),
                    -- createAndWait        (5)
                       destroy              (6)
                    }
            DESCRIPTION
                 "tmnxOamPmCfgTwlRflPfxRowStatus supports only 'active (1)',
                  'createAndGo (4)', and 'destroy (6)'."

        VARIATION   tmnxOamPmCfgTwlRflRowStatus
            SYNTAX  RowStatus {
                       active               (1),
                    -- notInService         (2)
                    -- notReady             (3)
                       createAndGo          (4),
                    -- createAndWait        (5)
                       destroy              (6)
                    }
            DESCRIPTION
                 "tmnxOamPmCfgTwlRflRowStatus supports only 'active (1)',
                  'createAndGo (4)', and 'destroy (6)'."

        VARIATION   tmnxOamPmObjs
            DESCRIPTION
                 "The tmnxOamPmObjs objects are not supported on systems
                  equipped with CPM-1 or CPM-2."

    ::= { tmnxSROSAgentV14v0  28 }

--
-- 7750SR-1 OAM_PM CAPABILITIES
--
tmnx7750SR1OamPmV14v0             AGENT-CAPABILITIES
    PRODUCT-RELEASE "Nokia SROS"
    STATUS          current
    DESCRIPTION
         "Implementation of OAM Performance Monitoring capabilities for Nokia
          7750 SR-1 systems release 14.0."

    SUPPORTS        TIMETRA-OAM-PM-MIB
        INCLUDES {
           tmnxOamPmV12v0ObjGroup,
           tmnxOamPmV13v0NotifGroup,
           tmnxOamPmV13v0NotifyObjsGroup,
           tmnxOamPmV13v0ObjGroup,
           tmnxOamPmV14v0NotifyObjsGroup,
           tmnxOamPmV14v0ObjGroup
        }

        VARIATION   tmnxOamPmCfgBinGroupRowStatus
            SYNTAX  RowStatus {
                       active               (1),
                    -- notInService         (2)
                    -- notReady             (3)
                       createAndGo          (4),
                    -- createAndWait        (5)
                       destroy              (6)
                    }
            DESCRIPTION
                 "tmnxOamPmCfgBinGroupRowStatus supports only 'active (1)',
                  'createAndGo (4)', and 'destroy (6)'."

        VARIATION   tmnxOamPmCfgDelayDmmRowStatus
            SYNTAX  RowStatus {
                       active               (1),
                    -- notInService         (2)
                    -- notReady             (3)
                       createAndGo          (4),
                    -- createAndWait        (5)
                       destroy              (6)
                    }
            DESCRIPTION
                 "tmnxOamPmCfgDelayDmmRowStatus supports only 'active (1)',
                  'createAndGo (4)', and 'destroy (6)'."

        VARIATION   tmnxOamPmCfgLossLmmRowStatus
            SYNTAX  RowStatus {
                       active               (1),
                    -- notInService         (2)
                    -- notReady             (3)
                       createAndGo          (4),
                    -- createAndWait        (5)
                       destroy              (6)
                    }
            DESCRIPTION
                 "tmnxOamPmCfgLossLmmRowStatus supports only 'active (1)',
                  'createAndGo (4)', and 'destroy (6)'."

        VARIATION   tmnxOamPmCfgLossSlmRowStatus
            SYNTAX  RowStatus {
                       active               (1),
                    -- notInService         (2)
                    -- notReady             (3)
                       createAndGo          (4),
                    -- createAndWait        (5)
                       destroy              (6)
                    }
            DESCRIPTION
                 "tmnxOamPmCfgLossSlmRowStatus supports only 'active (1)',
                  'createAndGo (4)', and 'destroy (6)'."

        VARIATION   tmnxOamPmCfgMeasIntvlRowStatus
            SYNTAX  RowStatus {
                       active               (1),
                    -- notInService         (2)
                    -- notReady             (3)
                       createAndGo          (4),
                    -- createAndWait        (5)
                       destroy              (6)
                    }
            DESCRIPTION
                 "tmnxOamPmCfgMeasIntvlRowStatus supports only 'active (1)',
                  'createAndGo (4)', and 'destroy (6)'."

        VARIATION   tmnxOamPmCfgSessIpDstAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpDstAddressType supports only the
                  InetAddressType values 'unknown (0)', 'ipv4 (1)', and 'ipv6
                  (2)'."

        VARIATION   tmnxOamPmCfgSessIpNhAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpNhAddressType supports only the
                  InetAddressType values 'unknown (0)', 'ipv4 (1)', and 'ipv6
                  (2)'."

        VARIATION   tmnxOamPmCfgSessIpSrcAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpSrcAddressType supports only the
                  InetAddressType values 'unknown (0)', 'ipv4 (1)', and 'ipv6
                  (2)'."

        VARIATION   tmnxOamPmCfgSessRowStatus
            SYNTAX  RowStatus {
                       active               (1),
                    -- notInService         (2)
                    -- notReady             (3)
                       createAndGo          (4),
                    -- createAndWait        (5)
                       destroy              (6)
                    }
            DESCRIPTION
                 "tmnxOamPmCfgSessRowStatus supports only 'active (1)',
                  'createAndGo (4)', and 'destroy (6)'."

        VARIATION   tmnxOamPmCfgTwampLtRowStatus
            SYNTAX  RowStatus {
                       active               (1),
                    -- notInService         (2)
                    -- notReady             (3)
                       createAndGo          (4),
                    -- createAndWait        (5)
                       destroy              (6)
                    }
            DESCRIPTION
                 "tmnxOamPmCfgTwampLtRowStatus supports only 'active (1)',
                  'createAndGo (4)', and 'destroy (6)'."

        VARIATION   tmnxOamPmCfgTwlRflPfxRowStatus
            SYNTAX  RowStatus {
                       active               (1),
                    -- notInService         (2)
                    -- notReady             (3)
                       createAndGo          (4),
                    -- createAndWait        (5)
                       destroy              (6)
                    }
            DESCRIPTION
                 "tmnxOamPmCfgTwlRflPfxRowStatus supports only 'active (1)',
                  'createAndGo (4)', and 'destroy (6)'."

        VARIATION   tmnxOamPmCfgTwlRflRowStatus
            SYNTAX  RowStatus {
                       active               (1),
                    -- notInService         (2)
                    -- notReady             (3)
                       createAndGo          (4),
                    -- createAndWait        (5)
                       destroy              (6)
                    }
            DESCRIPTION
                 "tmnxOamPmCfgTwlRflRowStatus supports only 'active (1)',
                  'createAndGo (4)', and 'destroy (6)'."

        VARIATION   tmnxOamPmObjs
            ACCESS  not-implemented
            DESCRIPTION
                 "tmnxOamPmObjs is not implemented on Nokia 7750 SR-1 in release
                  14.0."

    ::= { tmnx7750SR1AgentV14v0  28 }

--
-- 7450ESS-1 OAM_PM CAPABILITIES
--
tmnx7450ESS1OamPmV14v0            AGENT-CAPABILITIES
    PRODUCT-RELEASE "Nokia SROS"
    STATUS          current
    DESCRIPTION
         "Implementation of OAM Performance Monitoring capabilities for Nokia
          7450 ESS-1 systems release 14.0."

    SUPPORTS        TIMETRA-OAM-PM-MIB
        INCLUDES {
           tmnxOamPmV12v0ObjGroup,
           tmnxOamPmV13v0NotifGroup,
           tmnxOamPmV13v0NotifyObjsGroup,
           tmnxOamPmV13v0ObjGroup,
           tmnxOamPmV14v0NotifyObjsGroup,
           tmnxOamPmV14v0ObjGroup
        }

        VARIATION   tmnxOamPmCfgBinGroupRowStatus
            SYNTAX  RowStatus {
                       active               (1),
                    -- notInService         (2)
                    -- notReady             (3)
                       createAndGo          (4),
                    -- createAndWait        (5)
                       destroy              (6)
                    }
            DESCRIPTION
                 "tmnxOamPmCfgBinGroupRowStatus supports only 'active (1)',
                  'createAndGo (4)', and 'destroy (6)'."

        VARIATION   tmnxOamPmCfgDelayDmmRowStatus
            SYNTAX  RowStatus {
                       active               (1),
                    -- notInService         (2)
                    -- notReady             (3)
                       createAndGo          (4),
                    -- createAndWait        (5)
                       destroy              (6)
                    }
            DESCRIPTION
                 "tmnxOamPmCfgDelayDmmRowStatus supports only 'active (1)',
                  'createAndGo (4)', and 'destroy (6)'."

        VARIATION   tmnxOamPmCfgLossLmmRowStatus
            SYNTAX  RowStatus {
                       active               (1),
                    -- notInService         (2)
                    -- notReady             (3)
                       createAndGo          (4),
                    -- createAndWait        (5)
                       destroy              (6)
                    }
            DESCRIPTION
                 "tmnxOamPmCfgLossLmmRowStatus supports only 'active (1)',
                  'createAndGo (4)', and 'destroy (6)'."

        VARIATION   tmnxOamPmCfgLossSlmRowStatus
            SYNTAX  RowStatus {
                       active               (1),
                    -- notInService         (2)
                    -- notReady             (3)
                       createAndGo          (4),
                    -- createAndWait        (5)
                       destroy              (6)
                    }
            DESCRIPTION
                 "tmnxOamPmCfgLossSlmRowStatus supports only 'active (1)',
                  'createAndGo (4)', and 'destroy (6)'."

        VARIATION   tmnxOamPmCfgMeasIntvlRowStatus
            SYNTAX  RowStatus {
                       active               (1),
                    -- notInService         (2)
                    -- notReady             (3)
                       createAndGo          (4),
                    -- createAndWait        (5)
                       destroy              (6)
                    }
            DESCRIPTION
                 "tmnxOamPmCfgMeasIntvlRowStatus supports only 'active (1)',
                  'createAndGo (4)', and 'destroy (6)'."

        VARIATION   tmnxOamPmCfgSessIpDstAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpDstAddressType supports only the
                  InetAddressType values 'unknown (0)', 'ipv4 (1)', and 'ipv6
                  (2)'."

        VARIATION   tmnxOamPmCfgSessIpNhAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpNhAddressType supports only the
                  InetAddressType values 'unknown (0)', 'ipv4 (1)', and 'ipv6
                  (2)'."

        VARIATION   tmnxOamPmCfgSessIpSrcAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpSrcAddressType supports only the
                  InetAddressType values 'unknown (0)', 'ipv4 (1)', and 'ipv6
                  (2)'."

        VARIATION   tmnxOamPmCfgSessRowStatus
            SYNTAX  RowStatus {
                       active               (1),
                    -- notInService         (2)
                    -- notReady             (3)
                       createAndGo          (4),
                    -- createAndWait        (5)
                       destroy              (6)
                    }
            DESCRIPTION
                 "tmnxOamPmCfgSessRowStatus supports only 'active (1)',
                  'createAndGo (4)', and 'destroy (6)'."

        VARIATION   tmnxOamPmCfgTwampLtRowStatus
            SYNTAX  RowStatus {
                       active               (1),
                    -- notInService         (2)
                    -- notReady             (3)
                       createAndGo          (4),
                    -- createAndWait        (5)
                       destroy              (6)
                    }
            DESCRIPTION
                 "tmnxOamPmCfgTwampLtRowStatus supports only 'active (1)',
                  'createAndGo (4)', and 'destroy (6)'."

        VARIATION   tmnxOamPmCfgTwlRflPfxRowStatus
            SYNTAX  RowStatus {
                       active               (1),
                    -- notInService         (2)
                    -- notReady             (3)
                       createAndGo          (4),
                    -- createAndWait        (5)
                       destroy              (6)
                    }
            DESCRIPTION
                 "tmnxOamPmCfgTwlRflPfxRowStatus supports only 'active (1)',
                  'createAndGo (4)', and 'destroy (6)'."

        VARIATION   tmnxOamPmCfgTwlRflRowStatus
            SYNTAX  RowStatus {
                       active               (1),
                    -- notInService         (2)
                    -- notReady             (3)
                       createAndGo          (4),
                    -- createAndWait        (5)
                       destroy              (6)
                    }
            DESCRIPTION
                 "tmnxOamPmCfgTwlRflRowStatus supports only 'active (1)',
                  'createAndGo (4)', and 'destroy (6)'."

        VARIATION   tmnxOamPmObjs
            ACCESS  not-implemented
            DESCRIPTION
                 "tmnxOamPmObjs is not implemented on Nokia 7450 ESS-1 in
                  release 14.0."

    ::= { tmnx7450ESS1AgentV14v0  28 }

--
-- 7450ESS-6 OAM_PM CAPABILITIES
--
tmnx7450ESS6OamPmV14v0            AGENT-CAPABILITIES
    PRODUCT-RELEASE "Nokia SROS"
    STATUS          current
    DESCRIPTION
         "Implementation of OAM Performance Monitoring capabilities for Nokia
          7450 ESS-6 systems release 14.0."

    SUPPORTS        TIMETRA-OAM-PM-MIB
        INCLUDES {
           tmnxOamPmV12v0ObjGroup,
           tmnxOamPmV13v0NotifGroup,
           tmnxOamPmV13v0NotifyObjsGroup,
           tmnxOamPmV13v0ObjGroup,
           tmnxOamPmV14v0NotifyObjsGroup,
           tmnxOamPmV14v0ObjGroup
        }

        VARIATION   tmnxOamPmCfgBinGroupRowStatus
            SYNTAX  RowStatus {
                       active               (1),
                    -- notInService         (2)
                    -- notReady             (3)
                       createAndGo          (4),
                    -- createAndWait        (5)
                       destroy              (6)
                    }
            DESCRIPTION
                 "tmnxOamPmCfgBinGroupRowStatus supports only 'active (1)',
                  'createAndGo (4)', and 'destroy (6)'."

        VARIATION   tmnxOamPmCfgDelayDmmRowStatus
            SYNTAX  RowStatus {
                       active               (1),
                    -- notInService         (2)
                    -- notReady             (3)
                       createAndGo          (4),
                    -- createAndWait        (5)
                       destroy              (6)
                    }
            DESCRIPTION
                 "tmnxOamPmCfgDelayDmmRowStatus supports only 'active (1)',
                  'createAndGo (4)', and 'destroy (6)'."

        VARIATION   tmnxOamPmCfgLossLmmRowStatus
            SYNTAX  RowStatus {
                       active               (1),
                    -- notInService         (2)
                    -- notReady             (3)
                       createAndGo          (4),
                    -- createAndWait        (5)
                       destroy              (6)
                    }
            DESCRIPTION
                 "tmnxOamPmCfgLossLmmRowStatus supports only 'active (1)',
                  'createAndGo (4)', and 'destroy (6)'."

        VARIATION   tmnxOamPmCfgLossSlmRowStatus
            SYNTAX  RowStatus {
                       active               (1),
                    -- notInService         (2)
                    -- notReady             (3)
                       createAndGo          (4),
                    -- createAndWait        (5)
                       destroy              (6)
                    }
            DESCRIPTION
                 "tmnxOamPmCfgLossSlmRowStatus supports only 'active (1)',
                  'createAndGo (4)', and 'destroy (6)'."

        VARIATION   tmnxOamPmCfgMeasIntvlRowStatus
            SYNTAX  RowStatus {
                       active               (1),
                    -- notInService         (2)
                    -- notReady             (3)
                       createAndGo          (4),
                    -- createAndWait        (5)
                       destroy              (6)
                    }
            DESCRIPTION
                 "tmnxOamPmCfgMeasIntvlRowStatus supports only 'active (1)',
                  'createAndGo (4)', and 'destroy (6)'."

        VARIATION   tmnxOamPmCfgSessIpDstAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpDstAddressType supports only the
                  InetAddressType values 'unknown (0)', 'ipv4 (1)', and 'ipv6
                  (2)'."

        VARIATION   tmnxOamPmCfgSessIpNhAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpNhAddressType supports only the
                  InetAddressType values 'unknown (0)', 'ipv4 (1)', and 'ipv6
                  (2)'."

        VARIATION   tmnxOamPmCfgSessIpSrcAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpSrcAddressType supports only the
                  InetAddressType values 'unknown (0)', 'ipv4 (1)', and 'ipv6
                  (2)'."

        VARIATION   tmnxOamPmCfgSessRowStatus
            SYNTAX  RowStatus {
                       active               (1),
                    -- notInService         (2)
                    -- notReady             (3)
                       createAndGo          (4),
                    -- createAndWait        (5)
                       destroy              (6)
                    }
            DESCRIPTION
                 "tmnxOamPmCfgSessRowStatus supports only 'active (1)',
                  'createAndGo (4)', and 'destroy (6)'."

        VARIATION   tmnxOamPmCfgTwampLtRowStatus
            SYNTAX  RowStatus {
                       active               (1),
                    -- notInService         (2)
                    -- notReady             (3)
                       createAndGo          (4),
                    -- createAndWait        (5)
                       destroy              (6)
                    }
            DESCRIPTION
                 "tmnxOamPmCfgTwampLtRowStatus supports only 'active (1)',
                  'createAndGo (4)', and 'destroy (6)'."

        VARIATION   tmnxOamPmCfgTwlRflPfxRowStatus
            SYNTAX  RowStatus {
                       active               (1),
                    -- notInService         (2)
                    -- notReady             (3)
                       createAndGo          (4),
                    -- createAndWait        (5)
                       destroy              (6)
                    }
            DESCRIPTION
                 "tmnxOamPmCfgTwlRflPfxRowStatus supports only 'active (1)',
                  'createAndGo (4)', and 'destroy (6)'."

        VARIATION   tmnxOamPmCfgTwlRflRowStatus
            SYNTAX  RowStatus {
                       active               (1),
                    -- notInService         (2)
                    -- notReady             (3)
                       createAndGo          (4),
                    -- createAndWait        (5)
                       destroy              (6)
                    }
            DESCRIPTION
                 "tmnxOamPmCfgTwlRflRowStatus supports only 'active (1)',
                  'createAndGo (4)', and 'destroy (6)'."

        VARIATION   tmnxOamPmObjs
            ACCESS  not-implemented
            DESCRIPTION
                 "tmnxOamPmObjs is not implemented on Nokia 7450 ESS-6 in
                  release 14.0."

    ::= { tmnx7450ESS6AgentV14v0  28 }

--
-- 7710 OAM_PM CAPABILITIES
--
tmnx7710OamPmV14v0                AGENT-CAPABILITIES
    PRODUCT-RELEASE "Nokia SROS"
    STATUS          current
    DESCRIPTION
         "Implementation of OAM Performance Monitoring capabilities for Nokia
          7710 systems release 14.0."

    SUPPORTS        TIMETRA-OAM-PM-MIB
        INCLUDES {
           tmnxOamPmV12v0ObjGroup,
           tmnxOamPmV13v0NotifGroup,
           tmnxOamPmV13v0NotifyObjsGroup,
           tmnxOamPmV13v0ObjGroup,
           tmnxOamPmV14v0NotifyObjsGroup,
           tmnxOamPmV14v0ObjGroup
        }

        VARIATION   tmnxOamPmCfgBinGroupRowStatus
            SYNTAX  RowStatus {
                       active               (1),
                    -- notInService         (2)
                    -- notReady             (3)
                       createAndGo          (4),
                    -- createAndWait        (5)
                       destroy              (6)
                    }
            DESCRIPTION
                 "tmnxOamPmCfgBinGroupRowStatus supports only 'active (1)',
                  'createAndGo (4)', and 'destroy (6)'."

        VARIATION   tmnxOamPmCfgDelayDmmRowStatus
            SYNTAX  RowStatus {
                       active               (1),
                    -- notInService         (2)
                    -- notReady             (3)
                       createAndGo          (4),
                    -- createAndWait        (5)
                       destroy              (6)
                    }
            DESCRIPTION
                 "tmnxOamPmCfgDelayDmmRowStatus supports only 'active (1)',
                  'createAndGo (4)', and 'destroy (6)'."

        VARIATION   tmnxOamPmCfgLossLmmRowStatus
            SYNTAX  RowStatus {
                       active               (1),
                    -- notInService         (2)
                    -- notReady             (3)
                       createAndGo          (4),
                    -- createAndWait        (5)
                       destroy              (6)
                    }
            DESCRIPTION
                 "tmnxOamPmCfgLossLmmRowStatus supports only 'active (1)',
                  'createAndGo (4)', and 'destroy (6)'."

        VARIATION   tmnxOamPmCfgLossSlmRowStatus
            SYNTAX  RowStatus {
                       active               (1),
                    -- notInService         (2)
                    -- notReady             (3)
                       createAndGo          (4),
                    -- createAndWait        (5)
                       destroy              (6)
                    }
            DESCRIPTION
                 "tmnxOamPmCfgLossSlmRowStatus supports only 'active (1)',
                  'createAndGo (4)', and 'destroy (6)'."

        VARIATION   tmnxOamPmCfgMeasIntvlRowStatus
            SYNTAX  RowStatus {
                       active               (1),
                    -- notInService         (2)
                    -- notReady             (3)
                       createAndGo          (4),
                    -- createAndWait        (5)
                       destroy              (6)
                    }
            DESCRIPTION
                 "tmnxOamPmCfgMeasIntvlRowStatus supports only 'active (1)',
                  'createAndGo (4)', and 'destroy (6)'."

        VARIATION   tmnxOamPmCfgSessIpDstAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpDstAddressType supports only the
                  InetAddressType values 'unknown (0)', 'ipv4 (1)', and 'ipv6
                  (2)'."

        VARIATION   tmnxOamPmCfgSessIpNhAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpNhAddressType supports only the
                  InetAddressType values 'unknown (0)', 'ipv4 (1)', and 'ipv6
                  (2)'."

        VARIATION   tmnxOamPmCfgSessIpSrcAddressType
            SYNTAX  InetAddressType {
                       unknown              (0),
                       ipv4                 (1),
                       ipv6                 (2)
                    -- ipv4z                (3)
                    -- ipv6z                (4)
                    -- dns                  (16)
                    }
            DESCRIPTION
                 "tmnxOamPmCfgSessIpSrcAddressType supports only the
                  InetAddressType values 'unknown (0)', 'ipv4 (1)', and 'ipv6
                  (2)'."

        VARIATION   tmnxOamPmCfgSessRowStatus
            SYNTAX  RowStatus {
                       active               (1),
                    -- notInService         (2)
                    -- notReady             (3)
                       createAndGo          (4),
                    -- createAndWait        (5)
                       destroy              (6)
                    }
            DESCRIPTION
                 "tmnxOamPmCfgSessRowStatus supports only 'active (1)',
                  'createAndGo (4)', and 'destroy (6)'."

        VARIATION   tmnxOamPmCfgTwampLtRowStatus
            SYNTAX  RowStatus {
                       active               (1),
                    -- notInService         (2)
                    -- notReady             (3)
                       createAndGo          (4),
                    -- createAndWait        (5)
                       destroy              (6)
                    }
            DESCRIPTION
                 "tmnxOamPmCfgTwampLtRowStatus supports only 'active (1)',
                  'createAndGo (4)', and 'destroy (6)'."

        VARIATION   tmnxOamPmCfgTwlRflPfxRowStatus
            SYNTAX  RowStatus {
                       active               (1),
                    -- notInService         (2)
                    -- notReady             (3)
                       createAndGo          (4),
                    -- createAndWait        (5)
                       destroy              (6)
                    }
            DESCRIPTION
                 "tmnxOamPmCfgTwlRflPfxRowStatus supports only 'active (1)',
                  'createAndGo (4)', and 'destroy (6)'."

        VARIATION   tmnxOamPmCfgTwlRflRowStatus
            SYNTAX  RowStatus {
                       active               (1),
                    -- notInService         (2)
                    -- notReady             (3)
                       createAndGo          (4),
                    -- createAndWait        (5)
                       destroy              (6)
                    }
            DESCRIPTION
                 "tmnxOamPmCfgTwlRflRowStatus supports only 'active (1)',
                  'createAndGo (4)', and 'destroy (6)'."

        VARIATION   tmnxOamPmObjs
            ACCESS  not-implemented
            DESCRIPTION
                 "tmnxOamPmObjs is not implemented on Nokia 7710 in release
                  14.0."

    ::= { tmnx7710AgentV14v0  28 }

--
-- SROS OAM_TEST CAPABILITIES
--
tmnxSROSOamTestV14v0              AGENT-CAPABILITIES
    PRODUCT-RELEASE "Nokia SROS"
    STATUS          current
    DESCRIPTION
         "Implementation of OAM test capabilities for Nokia SROS systems release
          14.0."

    SUPPORTS        TIMETRA-OAM-TEST-MIB
        INCLUDES {
           tmnxOamAncpTestV5v0Group,
-- EXCLUDE tmnxOamAtmPingR2r1Group
           tmnxOamCpePingV4v0Group,
           tmnxOamEthCfmPingV8v0Group,
           tmnxOamEthCfmTrV8v0Group,
           tmnxOamGeneralV10v0Group,
           tmnxOamGeneralV11v0Group,
           tmnxOamGeneralV14v0Group,
           tmnxOamGeneralV8v0Group,
           tmnxOamIcmpPingGroup,
           tmnxOamLTtraceV9v0Group,
           tmnxOamLspPingV11v0Group,
           tmnxOamLspTrV6v0Group,
           tmnxOamMRInfoV4v0Group,
           tmnxOamMacPingCtlV11v0Group,
           tmnxOamMacPingHistoryV11v0Group,
           tmnxOamMacTrV3v0Group,
           tmnxOamMcastTrV4v0Group,
           tmnxOamMfibPingV6v0Group,
           tmnxOamMobilePingGroup,
           tmnxOamP2mpLspPingGroup,
           tmnxOamP2mpLspPingV10v0Group,
           tmnxOamP2mpLspPingV8v0Group,
           tmnxOamP2mpLspTraceGroup,
           tmnxOamPingCtlV10v0Group,
           tmnxOamPingGeneralV10v0Group,
           tmnxOamPingNotificationV7v0Group,
           tmnxOamPingV11v0Group,
           tmnxOamPingV12v0Group,
           tmnxOamPingV13v0Group,
           tmnxOamPingV14v0Group,
           tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrGeneralV8v0Group,
           tmnxOamTrHopsV4v0Group,
           tmnxOamTrNotificationV5v0Group,
           tmnxOamTrNotificationV8v0Group,
           tmnxOamTrV11v0Group,
           tmnxOamTrV12v0Group,
           tmnxOamTrV13v0Group,
           tmnxOamVccvPingV11v0Group,
           tmnxOamVccvPingV5v0Group,
           tmnxOamVccvPingV9v0Group,
           tmnxOamVccvTrV11v0Group,
           tmnxOamVccvTrV6v0Group,
           tmnxOamVccvTrV9v0Group,
           tmnxOamVprnPingV4v0Group,
           tmnxOamVprnTrV6v0Group
        }

        VARIATION   tmnxOamCpePingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamCpePingCtlSrcAddrType supports only the InetAddressType
                  values 'unknown (0)' and 'ipv4 (1)'."

        VARIATION   tmnxOamLTtraceAutoRowStatus
            SYNTAX  RowStatus {
                       active               (1),
                    -- notInService         (2)
                    -- notReady             (3)
                       createAndGo          (4),
                    -- createAndWait        (5)
                       destroy              (6)
                    }
            DESCRIPTION
                 "tmnxOamLTtraceAutoRowStatus supports only 'active (1)',
                  'createAndGo (4)', and 'destroy (6)'."

        VARIATION   tmnxOamLTtraceCtlLdpPrefixLen
            SYNTAX  InetAddressPrefixLength (32)
            DESCRIPTION
                 "tmnxOamLTtraceCtlLdpPrefixLen supports prefix length 32 only."

        VARIATION   tmnxOamLTtraceCtlLdpPrefixType
            SYNTAX  InetAddressType {
                       unknown              (0),
                       ipv4                 (1)
                    -- ipv6                 (2)
                    -- ipv4z                (3)
                    -- ipv6z                (4)
                    -- dns                  (16)
                    }
            DESCRIPTION
                 "tmnxOamLTtraceCtlLdpPrefixType supports only the
                  InetAddressType values 'unknown (0)' and 'ipv4 (1)'."

        VARIATION   tmnxOamLspPingCtlLdpPrefixLen
            SYNTAX  InetAddressPrefixLength (32 | 128)
            DESCRIPTION
                 "tmnxOamLspPingCtlLdpPrefixLen supports prefix lengths 32 and
                  128 only."

        VARIATION   tmnxOamLspTrCtlLdpPrefixLen
            SYNTAX  InetAddressPrefixLength (32 | 128)
            DESCRIPTION
                 "tmnxOamLspTrCtlLdpPrefixLen supports prefix lengths 32 and 128
                  only."

        VARIATION   tmnxOamMcastTrCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlDestAddrType supports only the
                  InetAddressType values 'unknown (0)' and 'ipv4 (1)'."

        VARIATION   tmnxOamMcastTrCtlGrpAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlGrpAddrType supports only the InetAddressType
                  values 'unknown (0)' and 'ipv4 (1)'."

        VARIATION   tmnxOamMcastTrCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlSrcAddrType supports only the InetAddressType
                  values 'unknown (0)' and 'ipv4 (1)'."

        VARIATION   tmnxOamMfibPingCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlDestAddrType supports only the
                  InetAddressType values 'unknown (0)' and 'ipv4 (1)'."

        VARIATION   tmnxOamMfibPingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlSrcAddrType supports only the
                  InetAddressType values 'unknown (0)' and 'ipv4 (1)'."

        VARIATION   tmnxOamP2mpLspPingCtlIpAddrType
            SYNTAX  InetAddressType {
                    -- unknown              (0)
                       ipv4                 (1)
                    -- ipv6                 (2)
                    -- ipv4z                (3)
                    -- ipv6z                (4)
                    -- dns                  (16)
                    }
            DESCRIPTION
                 "tmnxOamP2mpLspPingCtlIpAddrType supports only the
                  InetAddressType value 'ipv4 (1)'."

        VARIATION   tmnxOamP2mpLspPingCtlIpRowStatus
            SYNTAX  RowStatus {
                       active               (1),
                    -- notInService         (2)
                    -- notReady             (3)
                       createAndGo          (4),
                    -- createAndWait        (5)
                       destroy              (6)
                    }
            DESCRIPTION
                 "tmnxOamP2mpLspPingCtlIpRowStatus supports only 'active (1)',
                  'createAndGo (4)', and 'destroy (6)'."

        VARIATION   tmnxOamP2mpLspTrCtlLeafIpAddrType
            SYNTAX  InetAddressType {
                       unknown              (0),
                       ipv4                 (1)
                    -- ipv6                 (2)
                    -- ipv4z                (3)
                    -- ipv6z                (4)
                    -- dns                  (16)
                    }
            DESCRIPTION
                 "tmnxOamP2mpLspTrCtlLeafIpAddrType supports only the
                  InetAddressType values 'unknown (0)' and 'ipv4 (1)'."

        VARIATION   tmnxOamPingCtlRowStatus
            SYNTAX  RowStatus {
                       active               (1),
                    -- notInService         (2)
                    -- notReady             (3)
                       createAndGo          (4),
                    -- createAndWait        (5)
                       destroy              (6)
                    }
            DESCRIPTION
                 "tmnxOamPingCtlRowStatus supports only 'active (1)',
                  'createAndGo (4)', and 'destroy (6)'."

        VARIATION   tmnxOamPingCtlSAA
            ACCESS  read-only
            DESCRIPTION
                 "tmnxOamPingCtlSAA is implemented as read-only on Nokia SROS in
                  release 14.0."

        VARIATION   tmnxOamPingCtlTestMode
            SYNTAX  INTEGER {
                       sdpPing              (1),
                       mtuPing              (2),
                       svcPing              (3),
                    -- macQuery             (4) - obsolete
                       macPing              (5),
                       macPopulate          (6),
                       macPurge             (7),
                       lspPing              (8),
                       vprnPing             (9),
                       atmPing              (10),
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21) - not supported
                    }
            DESCRIPTION
                 "The value 'mobGtpPing (21)' is not supported on Nokia SROS."

        VARIATION   tmnxOamPingCtlTgtAddrType
            SYNTAX  INTEGER {
                       unknown              (0),
                       ipv4                 (1),
                       ipv6                 (2),
                    -- ipv4z                (3)
                       ipv6z                (4),
                       dns                  (16)
                    }
            DESCRIPTION
                 "tmnxOamPingCtlTgtAddrType does not support the InetAddressType
                  'ipv4z(3)'."

        VARIATION   tmnxOamSaaCtlRowStatus
            SYNTAX  RowStatus {
                       active               (1),
                    -- notInService         (2)
                    -- notReady             (3)
                       createAndGo          (4),
                    -- createAndWait        (5)
                       destroy              (6)
                    }
            DESCRIPTION
                 "tmnxOamSaaCtlRowStatus supports only 'active (1)',
                  'createAndGo (4)', and 'destroy (6)'."

        VARIATION   tmnxOamSaaTRowStatus
            SYNTAX  RowStatus {
                       active               (1),
                    -- notInService         (2)
                    -- notReady             (3)
                       createAndGo          (4),
                    -- createAndWait        (5)
                       destroy              (6)
                    }
            DESCRIPTION
                 "tmnxOamSaaTRowStatus supports only 'active (1)', 'createAndGo
                  (4)', and 'destroy (6)'."

        VARIATION   tmnxOamSaaTThreshold
            DESCRIPTION
                 "The value of tmnxOamSaaTThreshold must be a multiple of 1000
                  when specifying a tmnxOamSaaTType with units of microseconds."

        VARIATION   tmnxOamTrCtlRowStatus
            SYNTAX  RowStatus {
                       active               (1),
                    -- notInService         (2)
                    -- notReady             (3)
                       createAndGo          (4),
                    -- createAndWait        (5)
                       destroy              (6)
                    }
            DESCRIPTION
                 "tmnxOamTrCtlRowStatus supports only 'active (1)', 'createAndGo
                  (4)', and 'destroy (6)'."

        VARIATION   tmnxOamTrCtlSAA
            ACCESS  read-only
            DESCRIPTION
                 "tmnxOamTrCtlSAA is implemented as read-only on Nokia SROS in
                  release 14.0."

        VARIATION   tmnxOamTrCtlTgtAddrType
            SYNTAX  INTEGER {
                       unknown              (0),
                       ipv4                 (1),
                       ipv6                 (2),
                    -- ipv4z                (3)
                    -- ipv6z                (4)
                       dns                  (16)
                    }
            DESCRIPTION
                 "tmnxOamTrCtlTgtAddrType does not support InetAddressType code
                  points 'ipv4z(3)' and 'ipv6z(4)'."

        VARIATION   tmnxOamTrCtlTrapGeneration
            SYNTAX  BITS {
                    -- pathChange(0)
                       testFailure(1),
                       testCompletion(2)
                    }
            DESCRIPTION
                 "The pathChange bit is not supported."

        VARIATION   tmnxOamTrPathChange
            ACCESS  not-implemented
            DESCRIPTION
                 "tmnxOamTrPathChange notification is not supported."

        VARIATION   tmnxOamVccvPgTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlDstAddrT supports only the
                  InetAddressType values 'unknown (0)' and 'ipv4 (1)'."

        VARIATION   tmnxOamVccvPgTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlSrcAddrT supports only the
                  InetAddressType values 'unknown (0)' and 'ipv4 (1)'."

        VARIATION   tmnxOamVccvTrTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlDstAddrT supports only the
                  InetAddressType values 'unknown (0)' and 'ipv4 (1)'."

        VARIATION   tmnxOamVccvTrTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlSrcAddrT supports only the
                  InetAddressType values 'unknown (0)' and 'ipv4 (1)'."

        VARIATION   tmnxOamVxlanPingCtlInIpDstAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpDstAddrT supports only the
                  InetAddressType value 'ipv4 (1)'."

        VARIATION   tmnxOamVxlanPingCtlInIpSrcAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpSrcAddrT supports only the
                  InetAddressType value 'ipv4 (1)'."

    ::= { tmnxSROSAgentV14v0  27 }

--
-- 7750SR-1 OAM_TEST CAPABILITIES
--
tmnx7750SR1OamTestV14v0           AGENT-CAPABILITIES
    PRODUCT-RELEASE "Nokia SROS"
    STATUS          current
    DESCRIPTION
         "Implementation of OAM test capabilities for Nokia 7750 SR-1 systems
          release 14.0."

    SUPPORTS        TIMETRA-OAM-TEST-MIB
        INCLUDES {
           tmnxOamAncpTestV5v0Group,
-- EXCLUDE tmnxOamAtmPingR2r1Group
           tmnxOamCpePingV4v0Group,
           tmnxOamEthCfmPingV8v0Group,
           tmnxOamEthCfmTrV8v0Group,
           tmnxOamGeneralV10v0Group,
           tmnxOamGeneralV11v0Group,
           tmnxOamGeneralV14v0Group,
           tmnxOamGeneralV8v0Group,
           tmnxOamIcmpPingGroup,
           tmnxOamLTtraceV9v0Group,
           tmnxOamLspPingV11v0Group,
           tmnxOamLspTrV6v0Group,
           tmnxOamMRInfoV4v0Group,
           tmnxOamMacPingCtlV11v0Group,
           tmnxOamMacPingHistoryV11v0Group,
           tmnxOamMacTrV3v0Group,
           tmnxOamMcastTrV4v0Group,
           tmnxOamMfibPingV6v0Group,
           tmnxOamMobilePingGroup,
           tmnxOamP2mpLspPingGroup,
           tmnxOamP2mpLspPingV10v0Group,
           tmnxOamP2mpLspPingV8v0Group,
           tmnxOamP2mpLspTraceGroup,
           tmnxOamPingCtlV10v0Group,
           tmnxOamPingGeneralV10v0Group,
           tmnxOamPingNotificationV7v0Group,
           tmnxOamPingV11v0Group,
           tmnxOamPingV12v0Group,
           tmnxOamPingV13v0Group,
           tmnxOamPingV14v0Group,
           tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrGeneralV8v0Group,
           tmnxOamTrHopsV4v0Group,
           tmnxOamTrNotificationV5v0Group,
           tmnxOamTrNotificationV8v0Group,
           tmnxOamTrV11v0Group,
           tmnxOamTrV12v0Group,
           tmnxOamTrV13v0Group,
           tmnxOamVccvPingV11v0Group,
           tmnxOamVccvPingV5v0Group,
           tmnxOamVccvPingV9v0Group,
           tmnxOamVccvTrV11v0Group,
           tmnxOamVccvTrV6v0Group,
           tmnxOamVccvTrV9v0Group,
           tmnxOamVprnPingV4v0Group,
           tmnxOamVprnTrV6v0Group
        }

        VARIATION   tmnxOamCpePingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamCpePingCtlSrcAddrType supports only the InetAddressType
                  values 'unknown (0)' and 'ipv4 (1)'."

        VARIATION   tmnxOamIcmpTrLabelStackBottom
            ACCESS  not-implemented
            DESCRIPTION
                 "tmnxOamIcmpTrLabelStackBottom is not implemented on Nokia 7750
                  SR-1 in release 14.0."

        VARIATION   tmnxOamIcmpTrLabelStackExperimnt
            ACCESS  not-implemented
            DESCRIPTION
                 "tmnxOamIcmpTrLabelStackExperimnt is not implemented on Nokia
                  7750 SR-1 in release 14.0."

        VARIATION   tmnxOamIcmpTrLabelStackLabel
            ACCESS  not-implemented
            DESCRIPTION
                 "tmnxOamIcmpTrLabelStackLabel is not implemented on Nokia 7750
                  SR-1 in release 14.0."

        VARIATION   tmnxOamIcmpTrLabelStackTtl
            ACCESS  not-implemented
            DESCRIPTION
                 "tmnxOamIcmpTrLabelStackTtl is not implemented on Nokia 7750
                  SR-1 in release 14.0."

        VARIATION   tmnxOamLTtraceAutoRowStatus
            SYNTAX  RowStatus {
                       active               (1),
                    -- notInService         (2)
                    -- notReady             (3)
                       createAndGo          (4),
                    -- createAndWait        (5)
                       destroy              (6)
                    }
            DESCRIPTION
                 "tmnxOamLTtraceAutoRowStatus supports only 'active (1)',
                  'createAndGo (4)', and 'destroy (6)'."

        VARIATION   tmnxOamLTtraceCtlLdpPrefixLen
            SYNTAX  InetAddressPrefixLength (32)
            DESCRIPTION
                 "tmnxOamLTtraceCtlLdpPrefixLen supports prefix length 32 only."

        VARIATION   tmnxOamLTtraceCtlLdpPrefixType
            SYNTAX  InetAddressType {
                       unknown              (0),
                       ipv4                 (1)
                    -- ipv6                 (2)
                    -- ipv4z                (3)
                    -- ipv6z                (4)
                    -- dns                  (16)
                    }
            DESCRIPTION
                 "tmnxOamLTtraceCtlLdpPrefixType supports only the
                  InetAddressType values 'unknown (0)' and 'ipv4 (1)'."

        VARIATION   tmnxOamLspPingCtlAssocChannel
            ACCESS  not-implemented
            DESCRIPTION
                 "tmnxOamLspPingCtlAssocChannel is not implemented on Nokia 7750
                  SR-1 in release 14.0."

        VARIATION   tmnxOamLspPingCtlLdpPrefixLen
            SYNTAX  InetAddressPrefixLength (32 | 128)
            DESCRIPTION
                 "tmnxOamLspPingCtlLdpPrefixLen supports prefix lengths 32 and
                  128 only."

        VARIATION   tmnxOamLspPingCtlMplsTpGlobalId
            ACCESS  not-implemented
            DESCRIPTION
                 "tmnxOamLspPingCtlMplsTpGlobalId is not implemented on Nokia
                  7750 SR-1 in release 14.0."

        VARIATION   tmnxOamLspPingCtlMplsTpNodeId
            ACCESS  not-implemented
            DESCRIPTION
                 "tmnxOamLspPingCtlMplsTpNodeId is not implemented on Nokia 7750
                  SR-1 in release 14.0."

        VARIATION   tmnxOamLspPingCtlMplsTpPathType
            ACCESS  not-implemented
            DESCRIPTION
                 "tmnxOamLspPingCtlMplsTpPathType is not implemented on Nokia
                  7750 SR-1 in release 14.0."

        VARIATION   tmnxOamLspPingCtlTestSubMode
            SYNTAX  INTEGER {
                       unspecified(1),
                    -- tpStatic(2)
                       bgpLabeledPrefix(3)
                    }
            DESCRIPTION
                 "'tpStatic(2)' is not supported on Nokia 7750 SR-1."

        VARIATION   tmnxOamLspTrCtlAssocChannel
            ACCESS  not-implemented
            DESCRIPTION
                 "tmnxOamLspTrCtlAssocChannel is not implemented on Nokia 7750
                  SR-1 in release 14.0."

        VARIATION   tmnxOamLspTrCtlLdpPrefixLen
            SYNTAX  InetAddressPrefixLength (32 | 128)
            DESCRIPTION
                 "tmnxOamLspTrCtlLdpPrefixLen supports prefix lengths 32 and 128
                  only."

        VARIATION   tmnxOamLspTrCtlMplsTpPathType
            ACCESS  not-implemented
            DESCRIPTION
                 "tmnxOamLspTrCtlMplsTpPathType is not implemented on Nokia 7750
                  SR-1 in release 14.0."

        VARIATION   tmnxOamLspTrCtlTestSubMode
            SYNTAX  INTEGER {
                       unspecified(1),
                    -- tpStatic(2)
                       bgpLabeledPrefix(3)
                    }
            DESCRIPTION
                 "'tpStatic(2)' is not supported on Nokia 7750 SR-1."

        VARIATION   tmnxOamMcastTrCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlDestAddrType supports only the
                  InetAddressType values 'unknown (0)' and 'ipv4 (1)'."

        VARIATION   tmnxOamMcastTrCtlGrpAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlGrpAddrType supports only the InetAddressType
                  values 'unknown (0)' and 'ipv4 (1)'."

        VARIATION   tmnxOamMcastTrCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlSrcAddrType supports only the InetAddressType
                  values 'unknown (0)' and 'ipv4 (1)'."

        VARIATION   tmnxOamMfibPingCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlDestAddrType supports only the
                  InetAddressType values 'unknown (0)' and 'ipv4 (1)'."

        VARIATION   tmnxOamMfibPingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlSrcAddrType supports only the
                  InetAddressType values 'unknown (0)' and 'ipv4 (1)'."

        VARIATION   tmnxOamP2mpLspPingCtlIpAddrType
            SYNTAX  InetAddressType {
                    -- unknown              (0)
                       ipv4                 (1)
                    -- ipv6                 (2)
                    -- ipv4z                (3)
                    -- ipv6z                (4)
                    -- dns                  (16)
                    }
            DESCRIPTION
                 "tmnxOamP2mpLspPingCtlIpAddrType supports only the
                  InetAddressType value 'ipv4 (1)'."

        VARIATION   tmnxOamP2mpLspPingCtlIpRowStatus
            SYNTAX  RowStatus {
                       active               (1),
                    -- notInService         (2)
                    -- notReady             (3)
                       createAndGo          (4),
                    -- createAndWait        (5)
                       destroy              (6)
                    }
            DESCRIPTION
                 "tmnxOamP2mpLspPingCtlIpRowStatus supports only 'active (1)',
                  'createAndGo (4)', and 'destroy (6)'."

        VARIATION   tmnxOamP2mpLspTrCtlLeafIpAddrType
            SYNTAX  InetAddressType {
                       unknown              (0),
                       ipv4                 (1)
                    -- ipv6                 (2)
                    -- ipv4z                (3)
                    -- ipv6z                (4)
                    -- dns                  (16)
                    }
            DESCRIPTION
                 "tmnxOamP2mpLspTrCtlLeafIpAddrType supports only the
                  InetAddressType values 'unknown (0)' and 'ipv4 (1)'."

        VARIATION   tmnxOamPingCtlRowStatus
            SYNTAX  RowStatus {
                       active               (1),
                    -- notInService         (2)
                    -- notReady             (3)
                       createAndGo          (4),
                    -- createAndWait        (5)
                       destroy              (6)
                    }
            DESCRIPTION
                 "tmnxOamPingCtlRowStatus supports only 'active (1)',
                  'createAndGo (4)', and 'destroy (6)'."

        VARIATION   tmnxOamPingCtlSAA
            ACCESS  read-only
            DESCRIPTION
                 "tmnxOamPingCtlSAA is implemented as read-only on Nokia 7750
                  SR-1 in release 14.0."

        VARIATION   tmnxOamPingCtlTestMode
            SYNTAX  INTEGER {
                       sdpPing              (1),
                       mtuPing              (2),
                       svcPing              (3),
                    -- macQuery             (4) - obsolete
                       macPing              (5),
                       macPopulate          (6),
                       macPurge             (7),
                       lspPing              (8),
                       vprnPing             (9),
                       atmPing              (10),
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21) - not supported
                    }
            DESCRIPTION
                 "The value 'mobGtpPing (21)' is not supported on Nokia 7750
                  SR-1."

        VARIATION   tmnxOamPingCtlTgtAddrType
            SYNTAX  INTEGER {
                       unknown              (0),
                       ipv4                 (1),
                       ipv6                 (2),
                    -- ipv4z                (3)
                       ipv6z                (4),
                       dns                  (16)
                    }
            DESCRIPTION
                 "tmnxOamPingCtlTgtAddrType does not support the InetAddressType
                  'ipv4z(3)'."

        VARIATION   tmnxOamPingHistorySrcGlobalId
            ACCESS  not-implemented
            DESCRIPTION
                 "tmnxOamPingHistorySrcGlobalId is not implemented on Nokia 7750
                  SR-1 in release 14.0."

        VARIATION   tmnxOamPingHistorySrcNodeId
            ACCESS  not-implemented
            DESCRIPTION
                 "tmnxOamPingHistorySrcNodeId is not implemented on Nokia 7750
                  SR-1 in release 14.0."

        VARIATION   tmnxOamSaaCtlRowStatus
            SYNTAX  RowStatus {
                       active               (1),
                    -- notInService         (2)
                    -- notReady             (3)
                       createAndGo          (4),
                    -- createAndWait        (5)
                       destroy              (6)
                    }
            DESCRIPTION
                 "tmnxOamSaaCtlRowStatus supports only 'active (1)',
                  'createAndGo (4)', and 'destroy (6)'."

        VARIATION   tmnxOamSaaTRowStatus
            SYNTAX  RowStatus {
                       active               (1),
                    -- notInService         (2)
                    -- notReady             (3)
                       createAndGo          (4),
                    -- createAndWait        (5)
                       destroy              (6)
                    }
            DESCRIPTION
                 "tmnxOamSaaTRowStatus supports only 'active (1)', 'createAndGo
                  (4)', and 'destroy (6)'."

        VARIATION   tmnxOamSaaTThreshold
            DESCRIPTION
                 "The value of tmnxOamSaaTThreshold must be a multiple of 1000
                  when specifying a tmnxOamSaaTType with units of microseconds."

        VARIATION   tmnxOamTrCtlRowStatus
            SYNTAX  RowStatus {
                       active               (1),
                    -- notInService         (2)
                    -- notReady             (3)
                       createAndGo          (4),
                    -- createAndWait        (5)
                       destroy              (6)
                    }
            DESCRIPTION
                 "tmnxOamTrCtlRowStatus supports only 'active (1)', 'createAndGo
                  (4)', and 'destroy (6)'."

        VARIATION   tmnxOamTrCtlSAA
            ACCESS  read-only
            DESCRIPTION
                 "tmnxOamTrCtlSAA is implemented as read-only on Nokia 7750 SR-1
                  in release 14.0."

        VARIATION   tmnxOamTrCtlTgtAddrType
            SYNTAX  INTEGER {
                       unknown              (0),
                       ipv4                 (1),
                       ipv6                 (2),
                    -- ipv4z                (3)
                    -- ipv6z                (4)
                       dns                  (16)
                    }
            DESCRIPTION
                 "tmnxOamTrCtlTgtAddrType does not support InetAddressType code
                  points 'ipv4z(3)' and 'ipv6z(4)'."

        VARIATION   tmnxOamTrCtlTrapGeneration
            SYNTAX  BITS {
                    -- pathChange(0)
                       testFailure(1),
                       testCompletion(2)
                    }
            DESCRIPTION
                 "The pathChange bit is not supported."

        VARIATION   tmnxOamTrPathChange
            ACCESS  not-implemented
            DESCRIPTION
                 "tmnxOamTrPathChange notification is not supported."

        VARIATION   tmnxOamTrProbeHistorySrcGlobalId
            ACCESS  not-implemented
            DESCRIPTION
                 "tmnxOamTrProbeHistorySrcGlobalId is not implemented on Nokia
                  7750 SR-1 in release 14.0."

        VARIATION   tmnxOamTrProbeHistorySrcNodeId
            ACCESS  not-implemented
            DESCRIPTION
                 "tmnxOamTrProbeHistorySrcNodeId is not implemented on Nokia
                  7750 SR-1 in release 14.0."

        VARIATION   tmnxOamVccvPgTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlDstAddrT supports only the
                  InetAddressType values 'unknown (0)' and 'ipv4 (1)'."

        VARIATION   tmnxOamVccvPgTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlSrcAddrT supports only the
                  InetAddressType values 'unknown (0)' and 'ipv4 (1)'."

        VARIATION   tmnxOamVccvPingCtlAssocChannel
            ACCESS  not-implemented
            DESCRIPTION
                 "tmnxOamVccvPingCtlAssocChannel is not implemented on Nokia
                  7750 SR-1 in release 14.0."

        VARIATION   tmnxOamVccvPingCtlMplsTpGlobalId
            ACCESS  not-implemented
            DESCRIPTION
                 "tmnxOamVccvPingCtlMplsTpGlobalId is not implemented on Nokia
                  7750 SR-1 in release 14.0."

        VARIATION   tmnxOamVccvPingCtlMplsTpNodeId
            ACCESS  not-implemented
            DESCRIPTION
                 "tmnxOamVccvPingCtlMplsTpNodeId is not implemented on Nokia
                  7750 SR-1 in release 14.0."

        VARIATION   tmnxOamVccvPingCtlTestSubMode
            SYNTAX  INTEGER {
                       unspecified(1)
                    -- tpStatic(2)
                    }
            DESCRIPTION
                 "'tpStatic(2)' is not supported on Nokia 7750 SR-1."

        VARIATION   tmnxOamVccvTrCtlAssocChannel
            ACCESS  not-implemented
            DESCRIPTION
                 "tmnxOamVccvTrCtlAssocChannel is not implemented on Nokia 7750
                  SR-1 in release 14.0."

        VARIATION   tmnxOamVccvTrCtlTestSubMode
            SYNTAX  INTEGER {
                       unspecified(1)
                    -- tpStatic(2)
                    }
            DESCRIPTION
                 "'tpStatic(2)' is not supported on Nokia 7750 SR-1."

        VARIATION   tmnxOamVccvTrNextTpAgi
            ACCESS  not-implemented
            DESCRIPTION
                 "tmnxOamVccvTrNextTpAgi is not implemented on Nokia 7750 SR-1
                  in release 14.0."

        VARIATION   tmnxOamVccvTrNextTpSaiiAcId
            ACCESS  not-implemented
            DESCRIPTION
                 "tmnxOamVccvTrNextTpSaiiAcId is not implemented on Nokia 7750
                  SR-1 in release 14.0."

        VARIATION   tmnxOamVccvTrNextTpSaiiGlobalId
            ACCESS  not-implemented
            DESCRIPTION
                 "tmnxOamVccvTrNextTpSaiiGlobalId is not implemented on Nokia
                  7750 SR-1 in release 14.0."

        VARIATION   tmnxOamVccvTrNextTpSaiiNodeId
            ACCESS  not-implemented
            DESCRIPTION
                 "tmnxOamVccvTrNextTpSaiiNodeId is not implemented on Nokia 7750
                  SR-1 in release 14.0."

        VARIATION   tmnxOamVccvTrNextTpTaiiAcId
            ACCESS  not-implemented
            DESCRIPTION
                 "tmnxOamVccvTrNextTpTaiiAcId is not implemented on Nokia 7750
                  SR-1 in release 14.0."

        VARIATION   tmnxOamVccvTrNextTpTaiiGlobalId
            ACCESS  not-implemented
            DESCRIPTION
                 "tmnxOamVccvTrNextTpTaiiGlobalId is not implemented on Nokia
                  7750 SR-1 in release 14.0."

        VARIATION   tmnxOamVccvTrNextTpTaiiNodeId
            ACCESS  not-implemented
            DESCRIPTION
                 "tmnxOamVccvTrNextTpTaiiNodeId is not implemented on Nokia 7750
                  SR-1 in release 14.0."

        VARIATION   tmnxOamVccvTrTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlDstAddrT supports only the
                  InetAddressType values 'unknown (0)' and 'ipv4 (1)'."

        VARIATION   tmnxOamVccvTrTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlSrcAddrT supports only the
                  InetAddressType values 'unknown (0)' and 'ipv4 (1)'."

        VARIATION   tmnxOamVxlanPingCtlInIpDstAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpDstAddrT supports only the
                  InetAddressType value 'ipv4 (1)'."

        VARIATION   tmnxOamVxlanPingCtlInIpSrcAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpSrcAddrT supports only the
                  InetAddressType value 'ipv4 (1)'."

    ::= { tmnx7750SR1AgentV14v0  27 }

--
-- 7450ESS-1 OAM_TEST CAPABILITIES
--
tmnx7450ESS1OamTestV14v0          AGENT-CAPABILITIES
    PRODUCT-RELEASE "Nokia SROS"
    STATUS          current
    DESCRIPTION
         "Implementation of OAM test capabilities for Nokia 7450 ESS-1 systems
          release 14.0."

    SUPPORTS        TIMETRA-OAM-TEST-MIB
        INCLUDES {
           tmnxOamAncpTestV5v0Group,
-- EXCLUDE tmnxOamAtmPingR2r1Group
           tmnxOamCpePingV4v0Group,
           tmnxOamEthCfmPingV8v0Group,
           tmnxOamEthCfmTrV8v0Group,
           tmnxOamGeneralV10v0Group,
           tmnxOamGeneralV11v0Group,
           tmnxOamGeneralV14v0Group,
           tmnxOamGeneralV8v0Group,
           tmnxOamIcmpPingGroup,
           tmnxOamLTtraceV9v0Group,
           tmnxOamLspPingV11v0Group,
           tmnxOamLspTrV6v0Group,
           tmnxOamMRInfoV4v0Group,
           tmnxOamMacPingCtlV11v0Group,
           tmnxOamMacPingHistoryV11v0Group,
           tmnxOamMacTrV3v0Group,
           tmnxOamMcastTrV4v0Group,
           tmnxOamMfibPingV6v0Group,
           tmnxOamMobilePingGroup,
           tmnxOamP2mpLspPingGroup,
           tmnxOamP2mpLspPingV10v0Group,
           tmnxOamP2mpLspPingV8v0Group,
           tmnxOamP2mpLspTraceGroup,
           tmnxOamPingCtlV10v0Group,
           tmnxOamPingGeneralV10v0Group,
           tmnxOamPingNotificationV7v0Group,
           tmnxOamPingV11v0Group,
           tmnxOamPingV12v0Group,
           tmnxOamPingV13v0Group,
           tmnxOamPingV14v0Group,
           tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrGeneralV8v0Group,
           tmnxOamTrHopsV4v0Group,
           tmnxOamTrNotificationV5v0Group,
           tmnxOamTrNotificationV8v0Group,
           tmnxOamTrV11v0Group,
           tmnxOamTrV12v0Group,
           tmnxOamTrV13v0Group,
           tmnxOamVccvPingV11v0Group,
           tmnxOamVccvPingV5v0Group,
           tmnxOamVccvPingV9v0Group,
           tmnxOamVccvTrV11v0Group,
           tmnxOamVccvTrV6v0Group,
           tmnxOamVccvTrV9v0Group,
           tmnxOamVprnPingV4v0Group,
           tmnxOamVprnTrV6v0Group
        }

        VARIATION   tmnxOamCpePingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamCpePingCtlSrcAddrType supports only the InetAddressType
                  values 'unknown (0)' and 'ipv4 (1)'."

        VARIATION   tmnxOamIcmpTrLabelStackBottom
            ACCESS  not-implemented
            DESCRIPTION
                 "tmnxOamIcmpTrLabelStackBottom is not implemented on Nokia 7450
                  ESS-1 in release 14.0."

        VARIATION   tmnxOamIcmpTrLabelStackExperimnt
            ACCESS  not-implemented
            DESCRIPTION
                 "tmnxOamIcmpTrLabelStackExperimnt is not implemented on Nokia
                  7450 ESS-1 in release 14.0."

        VARIATION   tmnxOamIcmpTrLabelStackLabel
            ACCESS  not-implemented
            DESCRIPTION
                 "tmnxOamIcmpTrLabelStackLabel is not implemented on Nokia 7450
                  ESS-1 in release 14.0."

        VARIATION   tmnxOamIcmpTrLabelStackTtl
            ACCESS  not-implemented
            DESCRIPTION
                 "tmnxOamIcmpTrLabelStackTtl is not implemented on Nokia 7450
                  ESS-1 in release 14.0."

        VARIATION   tmnxOamLTtraceAutoRowStatus
            SYNTAX  RowStatus {
                       active               (1),
                    -- notInService         (2)
                    -- notReady             (3)
                       createAndGo          (4),
                    -- createAndWait        (5)
                       destroy              (6)
                    }
            DESCRIPTION
                 "tmnxOamLTtraceAutoRowStatus supports only 'active (1)',
                  'createAndGo (4)', and 'destroy (6)'."

        VARIATION   tmnxOamLTtraceCtlLdpPrefixLen
            SYNTAX  InetAddressPrefixLength (32)
            DESCRIPTION
                 "tmnxOamLTtraceCtlLdpPrefixLen supports prefix length 32 only."

        VARIATION   tmnxOamLTtraceCtlLdpPrefixType
            SYNTAX  InetAddressType {
                       unknown              (0),
                       ipv4                 (1)
                    -- ipv6                 (2)
                    -- ipv4z                (3)
                    -- ipv6z                (4)
                    -- dns                  (16)
                    }
            DESCRIPTION
                 "tmnxOamLTtraceCtlLdpPrefixType supports only the
                  InetAddressType values 'unknown (0)' and 'ipv4 (1)'."

        VARIATION   tmnxOamLspPingCtlAssocChannel
            ACCESS  not-implemented
            DESCRIPTION
                 "tmnxOamLspPingCtlAssocChannel is not implemented on Nokia 7450
                  ESS-1 in release 14.0."

        VARIATION   tmnxOamLspPingCtlLdpPrefixLen
            SYNTAX  InetAddressPrefixLength (32 | 128)
            DESCRIPTION
                 "tmnxOamLspPingCtlLdpPrefixLen supports prefix lengths 32 and
                  128 only."

        VARIATION   tmnxOamLspPingCtlMplsTpGlobalId
            ACCESS  not-implemented
            DESCRIPTION
                 "tmnxOamLspPingCtlMplsTpGlobalId is not implemented on Nokia
                  7450 ESS-1 in release 14.0."

        VARIATION   tmnxOamLspPingCtlMplsTpNodeId
            ACCESS  not-implemented
            DESCRIPTION
                 "tmnxOamLspPingCtlMplsTpNodeId is not implemented on Nokia 7450
                  ESS-1 in release 14.0."

        VARIATION   tmnxOamLspPingCtlMplsTpPathType
            ACCESS  not-implemented
            DESCRIPTION
                 "tmnxOamLspPingCtlMplsTpPathType is not implemented on Nokia
                  7450 ESS-1 in release 14.0."

        VARIATION   tmnxOamLspPingCtlTestSubMode
            SYNTAX  INTEGER {
                       unspecified(1),
                    -- tpStatic(2)
                       bgpLabeledPrefix(3)
                    }
            DESCRIPTION
                 "'tpStatic(2)' is not supported on Nokia 7450 ESS-1."

        VARIATION   tmnxOamLspTrCtlAssocChannel
            ACCESS  not-implemented
            DESCRIPTION
                 "tmnxOamLspTrCtlAssocChannel is not implemented on Nokia 7450
                  ESS-1 in release 14.0."

        VARIATION   tmnxOamLspTrCtlLdpPrefixLen
            SYNTAX  InetAddressPrefixLength (32 | 128)
            DESCRIPTION
                 "tmnxOamLspTrCtlLdpPrefixLen supports prefix lengths 32 and 128
                  only."

        VARIATION   tmnxOamLspTrCtlMplsTpPathType
            ACCESS  not-implemented
            DESCRIPTION
                 "tmnxOamLspTrCtlMplsTpPathType is not implemented on Nokia 7450
                  ESS-1 in release 14.0."

        VARIATION   tmnxOamLspTrCtlTestSubMode
            SYNTAX  INTEGER {
                       unspecified(1),
                    -- tpStatic(2)
                       bgpLabeledPrefix(3)
                    }
            DESCRIPTION
                 "'tpStatic(2)' is not supported on Nokia 7450 ESS-1."

        VARIATION   tmnxOamMcastTrCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlDestAddrType supports only the
                  InetAddressType values 'unknown (0)' and 'ipv4 (1)'."

        VARIATION   tmnxOamMcastTrCtlGrpAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlGrpAddrType supports only the InetAddressType
                  values 'unknown (0)' and 'ipv4 (1)'."

        VARIATION   tmnxOamMcastTrCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlSrcAddrType supports only the InetAddressType
                  values 'unknown (0)' and 'ipv4 (1)'."

        VARIATION   tmnxOamMfibPingCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlDestAddrType supports only the
                  InetAddressType values 'unknown (0)' and 'ipv4 (1)'."

        VARIATION   tmnxOamMfibPingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlSrcAddrType supports only the
                  InetAddressType values 'unknown (0)' and 'ipv4 (1)'."

        VARIATION   tmnxOamP2mpLspPingCtlIpAddrType
            SYNTAX  InetAddressType {
                    -- unknown              (0)
                       ipv4                 (1)
                    -- ipv6                 (2)
                    -- ipv4z                (3)
                    -- ipv6z                (4)
                    -- dns                  (16)
                    }
            DESCRIPTION
                 "tmnxOamP2mpLspPingCtlIpAddrType supports only the
                  InetAddressType value 'ipv4 (1)'."

        VARIATION   tmnxOamP2mpLspPingCtlIpRowStatus
            SYNTAX  RowStatus {
                       active               (1),
                    -- notInService         (2)
                    -- notReady             (3)
                       createAndGo          (4),
                    -- createAndWait        (5)
                       destroy              (6)
                    }
            DESCRIPTION
                 "tmnxOamP2mpLspPingCtlIpRowStatus supports only 'active (1)',
                  'createAndGo (4)', and 'destroy (6)'."

        VARIATION   tmnxOamP2mpLspTrCtlLeafIpAddrType
            SYNTAX  InetAddressType {
                       unknown              (0),
                       ipv4                 (1)
                    -- ipv6                 (2)
                    -- ipv4z                (3)
                    -- ipv6z                (4)
                    -- dns                  (16)
                    }
            DESCRIPTION
                 "tmnxOamP2mpLspTrCtlLeafIpAddrType supports only the
                  InetAddressType values 'unknown (0)' and 'ipv4 (1)'."

        VARIATION   tmnxOamPingCtlRowStatus
            SYNTAX  RowStatus {
                       active               (1),
                    -- notInService         (2)
                    -- notReady             (3)
                       createAndGo          (4),
                    -- createAndWait        (5)
                       destroy              (6)
                    }
            DESCRIPTION
                 "tmnxOamPingCtlRowStatus supports only 'active (1)',
                  'createAndGo (4)', and 'destroy (6)'."

        VARIATION   tmnxOamPingCtlSAA
            ACCESS  read-only
            DESCRIPTION
                 "tmnxOamPingCtlSAA is implemented as read-only on Nokia 7450
                  ESS-1 in release 14.0."

        VARIATION   tmnxOamPingCtlTestMode
            SYNTAX  INTEGER {
                       sdpPing              (1),
                       mtuPing              (2),
                       svcPing              (3),
                    -- macQuery             (4) - obsolete
                       macPing              (5),
                       macPopulate          (6),
                       macPurge             (7),
                       lspPing              (8),
                       vprnPing             (9),
                       atmPing              (10),
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21) - not supported
                    }
            DESCRIPTION
                 "The value 'mobGtpPing (21)' is not supported on Nokia 7450
                  ESS-1."

        VARIATION   tmnxOamPingCtlTgtAddrType
            SYNTAX  INTEGER {
                       unknown              (0),
                       ipv4                 (1),
                       ipv6                 (2),
                    -- ipv4z                (3)
                       ipv6z                (4),
                       dns                  (16)
                    }
            DESCRIPTION
                 "tmnxOamPingCtlTgtAddrType does not support the InetAddressType
                  'ipv4z(3)'."

        VARIATION   tmnxOamPingHistorySrcGlobalId
            ACCESS  not-implemented
            DESCRIPTION
                 "tmnxOamPingHistorySrcGlobalId is not implemented on Nokia 7450
                  ESS-1 in release 14.0."

        VARIATION   tmnxOamPingHistorySrcNodeId
            ACCESS  not-implemented
            DESCRIPTION
                 "tmnxOamPingHistorySrcNodeId is not implemented on Nokia 7450
                  ESS-1 in release 14.0."

        VARIATION   tmnxOamSaaCtlRowStatus
            SYNTAX  RowStatus {
                       active               (1),
                    -- notInService         (2)
                    -- notReady             (3)
                       createAndGo          (4),
                    -- createAndWait        (5)
                       destroy              (6)
                    }
            DESCRIPTION
                 "tmnxOamSaaCtlRowStatus supports only 'active (1)',
                  'createAndGo (4)', and 'destroy (6)'."

        VARIATION   tmnxOamSaaTRowStatus
            SYNTAX  RowStatus {
                       active               (1),
                    -- notInService         (2)
                    -- notReady             (3)
                       createAndGo          (4),
                    -- createAndWait        (5)
                       destroy              (6)
                    }
            DESCRIPTION
                 "tmnxOamSaaTRowStatus supports only 'active (1)', 'createAndGo
                  (4)', and 'destroy (6)'."

        VARIATION   tmnxOamSaaTThreshold
            DESCRIPTION
                 "The value of tmnxOamSaaTThreshold must be a multiple of 1000
                  when specifying a tmnxOamSaaTType with units of microseconds."

        VARIATION   tmnxOamTrCtlRowStatus
            SYNTAX  RowStatus {
                       active               (1),
                    -- notInService         (2)
                    -- notReady             (3)
                       createAndGo          (4),
                    -- createAndWait        (5)
                       destroy              (6)
                    }
            DESCRIPTION
                 "tmnxOamTrCtlRowStatus supports only 'active (1)', 'createAndGo
                  (4)', and 'destroy (6)'."

        VARIATION   tmnxOamTrCtlSAA
            ACCESS  read-only
            DESCRIPTION
                 "tmnxOamTrCtlSAA is implemented as read-only on Nokia 7450
                  ESS-1 in release 14.0."

        VARIATION   tmnxOamTrCtlTgtAddrType
            SYNTAX  INTEGER {
                       unknown              (0),
                       ipv4                 (1),
                       ipv6                 (2),
                    -- ipv4z                (3)
                    -- ipv6z                (4)
                       dns                  (16)
                    }
            DESCRIPTION
                 "tmnxOamTrCtlTgtAddrType does not support InetAddressType code
                  points 'ipv4z(3)' and 'ipv6z(4)'."

        VARIATION   tmnxOamTrCtlTrapGeneration
            SYNTAX  BITS {
                    -- pathChange(0)
                       testFailure(1),
                       testCompletion(2)
                    }
            DESCRIPTION
                 "The pathChange bit is not supported."

        VARIATION   tmnxOamTrPathChange
            ACCESS  not-implemented
            DESCRIPTION
                 "tmnxOamTrPathChange notification is not supported."

        VARIATION   tmnxOamTrProbeHistorySrcGlobalId
            ACCESS  not-implemented
            DESCRIPTION
                 "tmnxOamTrProbeHistorySrcGlobalId is not implemented on Nokia
                  7450 ESS-1 in release 14.0."

        VARIATION   tmnxOamTrProbeHistorySrcNodeId
            ACCESS  not-implemented
            DESCRIPTION
                 "tmnxOamTrProbeHistorySrcNodeId is not implemented on Nokia
                  7450 ESS-1 in release 14.0."

        VARIATION   tmnxOamVccvPgTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlDstAddrT supports only the
                  InetAddressType values 'unknown (0)' and 'ipv4 (1)'."

        VARIATION   tmnxOamVccvPgTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlSrcAddrT supports only the
                  InetAddressType values 'unknown (0)' and 'ipv4 (1)'."

        VARIATION   tmnxOamVccvPingCtlAssocChannel
            ACCESS  not-implemented
            DESCRIPTION
                 "tmnxOamVccvPingCtlAssocChannel is not implemented on Nokia
                  7450 ESS-1 in release 14.0."

        VARIATION   tmnxOamVccvPingCtlMplsTpGlobalId
            ACCESS  not-implemented
            DESCRIPTION
                 "tmnxOamVccvPingCtlMplsTpGlobalId is not implemented on Nokia
                  7450 ESS-1 in release 14.0."

        VARIATION   tmnxOamVccvPingCtlMplsTpNodeId
            ACCESS  not-implemented
            DESCRIPTION
                 "tmnxOamVccvPingCtlMplsTpNodeId is not implemented on Nokia
                  7450 ESS-1 in release 14.0."

        VARIATION   tmnxOamVccvPingCtlTestSubMode
            SYNTAX  INTEGER {
                       unspecified(1)
                    -- tpStatic(2)
                    }
            DESCRIPTION
                 "'tpStatic(2)' is not supported on Nokia 7450 ESS-1."

        VARIATION   tmnxOamVccvTrCtlAssocChannel
            ACCESS  not-implemented
            DESCRIPTION
                 "tmnxOamVccvTrCtlAssocChannel is not implemented on Nokia 7450
                  ESS-1 in release 14.0."

        VARIATION   tmnxOamVccvTrCtlTestSubMode
            SYNTAX  INTEGER {
                       unspecified(1)
                    -- tpStatic(2)
                    }
            DESCRIPTION
                 "'tpStatic(2)' is not supported on Nokia 7450 ESS-1."

        VARIATION   tmnxOamVccvTrNextTpAgi
            ACCESS  not-implemented
            DESCRIPTION
                 "tmnxOamVccvTrNextTpAgi is not implemented on Nokia 7450 ESS-1
                  in release 14.0."

        VARIATION   tmnxOamVccvTrNextTpSaiiAcId
            ACCESS  not-implemented
            DESCRIPTION
                 "tmnxOamVccvTrNextTpSaiiAcId is not implemented on Nokia 7450
                  ESS-1 in release 14.0."

        VARIATION   tmnxOamVccvTrNextTpSaiiGlobalId
            ACCESS  not-implemented
            DESCRIPTION
                 "tmnxOamVccvTrNextTpSaiiGlobalId is not implemented on Nokia
                  7450 ESS-1 in release 14.0."

        VARIATION   tmnxOamVccvTrNextTpSaiiNodeId
            ACCESS  not-implemented
            DESCRIPTION
                 "tmnxOamVccvTrNextTpSaiiNodeId is not implemented on Nokia 7450
                  ESS-1 in release 14.0."

        VARIATION   tmnxOamVccvTrNextTpTaiiAcId
            ACCESS  not-implemented
            DESCRIPTION
                 "tmnxOamVccvTrNextTpTaiiAcId is not implemented on Nokia 7450
                  ESS-1 in release 14.0."

        VARIATION   tmnxOamVccvTrNextTpTaiiGlobalId
            ACCESS  not-implemented
            DESCRIPTION
                 "tmnxOamVccvTrNextTpTaiiGlobalId is not implemented on Nokia
                  7450 ESS-1 in release 14.0."

        VARIATION   tmnxOamVccvTrNextTpTaiiNodeId
            ACCESS  not-implemented
            DESCRIPTION
                 "tmnxOamVccvTrNextTpTaiiNodeId is not implemented on Nokia 7450
                  ESS-1 in release 14.0."

        VARIATION   tmnxOamVccvTrTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlDstAddrT supports only the
                  InetAddressType values 'unknown (0)' and 'ipv4 (1)'."

        VARIATION   tmnxOamVccvTrTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlSrcAddrT supports only the
                  InetAddressType values 'unknown (0)' and 'ipv4 (1)'."

        VARIATION   tmnxOamVxlanPingCtlInIpDstAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpDstAddrT supports only the
                  InetAddressType value 'ipv4 (1)'."

        VARIATION   tmnxOamVxlanPingCtlInIpSrcAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpSrcAddrT supports only the
                  InetAddressType value 'ipv4 (1)'."

    ::= { tmnx7450ESS1AgentV14v0  27 }

--
-- 7450ESS-6 OAM_TEST CAPABILITIES
--
tmnx7450ESS6OamTestV14v0          AGENT-CAPABILITIES
    PRODUCT-RELEASE "Nokia SROS"
    STATUS          current
    DESCRIPTION
         "Implementation of OAM test capabilities for Nokia 7450 ESS-6 systems
          release 14.0."

    SUPPORTS        TIMETRA-OAM-TEST-MIB
        INCLUDES {
           tmnxOamAncpTestV5v0Group,
-- EXCLUDE tmnxOamAtmPingR2r1Group
           tmnxOamCpePingV4v0Group,
           tmnxOamEthCfmPingV8v0Group,
           tmnxOamEthCfmTrV8v0Group,
           tmnxOamGeneralV10v0Group,
           tmnxOamGeneralV11v0Group,
           tmnxOamGeneralV14v0Group,
           tmnxOamGeneralV8v0Group,
           tmnxOamIcmpPingGroup,
           tmnxOamLTtraceV9v0Group,
           tmnxOamLspPingV11v0Group,
           tmnxOamLspTrV6v0Group,
           tmnxOamMRInfoV4v0Group,
           tmnxOamMacPingCtlV11v0Group,
           tmnxOamMacPingHistoryV11v0Group,
           tmnxOamMacTrV3v0Group,
           tmnxOamMcastTrV4v0Group,
           tmnxOamMfibPingV6v0Group,
           tmnxOamMobilePingGroup,
           tmnxOamP2mpLspPingGroup,
           tmnxOamP2mpLspPingV10v0Group,
           tmnxOamP2mpLspPingV8v0Group,
           tmnxOamP2mpLspTraceGroup,
           tmnxOamPingCtlV10v0Group,
           tmnxOamPingGeneralV10v0Group,
           tmnxOamPingNotificationV7v0Group,
           tmnxOamPingV11v0Group,
           tmnxOamPingV12v0Group,
           tmnxOamPingV13v0Group,
           tmnxOamPingV14v0Group,
           tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrGeneralV8v0Group,
           tmnxOamTrHopsV4v0Group,
           tmnxOamTrNotificationV5v0Group,
           tmnxOamTrNotificationV8v0Group,
           tmnxOamTrV11v0Group,
           tmnxOamTrV12v0Group,
           tmnxOamTrV13v0Group,
           tmnxOamVccvPingV11v0Group,
           tmnxOamVccvPingV5v0Group,
           tmnxOamVccvPingV9v0Group,
           tmnxOamVccvTrV11v0Group,
           tmnxOamVccvTrV6v0Group,
           tmnxOamVccvTrV9v0Group,
           tmnxOamVprnPingV4v0Group,
           tmnxOamVprnTrV6v0Group
        }

        VARIATION   tmnxOamCpePingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamCpePingCtlSrcAddrType supports only the InetAddressType
                  values 'unknown (0)' and 'ipv4 (1)'."

        VARIATION   tmnxOamLTtraceAutoRowStatus
            SYNTAX  RowStatus {
                       active               (1),
                    -- notInService         (2)
                    -- notReady             (3)
                       createAndGo          (4),
                    -- createAndWait        (5)
                       destroy              (6)
                    }
            DESCRIPTION
                 "tmnxOamLTtraceAutoRowStatus supports only 'active (1)',
                  'createAndGo (4)', and 'destroy (6)'."

        VARIATION   tmnxOamLTtraceCtlLdpPrefixLen
            SYNTAX  InetAddressPrefixLength (32)
            DESCRIPTION
                 "tmnxOamLTtraceCtlLdpPrefixLen supports prefix length 32 only."

        VARIATION   tmnxOamLTtraceCtlLdpPrefixType
            SYNTAX  InetAddressType {
                       unknown              (0),
                       ipv4                 (1)
                    -- ipv6                 (2)
                    -- ipv4z                (3)
                    -- ipv6z                (4)
                    -- dns                  (16)
                    }
            DESCRIPTION
                 "tmnxOamLTtraceCtlLdpPrefixType supports only the
                  InetAddressType values 'unknown (0)' and 'ipv4 (1)'."

        VARIATION   tmnxOamLspPingCtlAssocChannel
            ACCESS  not-implemented
            DESCRIPTION
                 "tmnxOamLspPingCtlAssocChannel is not implemented on Nokia 7450
                  ESS-6 in release 14.0."

        VARIATION   tmnxOamLspPingCtlLdpPrefixLen
            SYNTAX  InetAddressPrefixLength (32 | 128)
            DESCRIPTION
                 "tmnxOamLspPingCtlLdpPrefixLen supports prefix lengths 32 and
                  128 only."

        VARIATION   tmnxOamLspPingCtlMplsTpGlobalId
            ACCESS  not-implemented
            DESCRIPTION
                 "tmnxOamLspPingCtlMplsTpGlobalId is not implemented on Nokia
                  7450 ESS-6 in release 14.0."

        VARIATION   tmnxOamLspPingCtlMplsTpNodeId
            ACCESS  not-implemented
            DESCRIPTION
                 "tmnxOamLspPingCtlMplsTpNodeId is not implemented on Nokia 7450
                  ESS-6 in release 14.0."

        VARIATION   tmnxOamLspPingCtlMplsTpPathType
            ACCESS  not-implemented
            DESCRIPTION
                 "tmnxOamLspPingCtlMplsTpPathType is not implemented on Nokia
                  7450 ESS-6 in release 14.0."

        VARIATION   tmnxOamLspPingCtlTestSubMode
            SYNTAX  INTEGER {
                       unspecified(1),
                    -- tpStatic(2)
                       bgpLabeledPrefix(3)
                    }
            DESCRIPTION
                 "'tpStatic(2)' is not supported on Nokia 7450 ESS-6."

        VARIATION   tmnxOamLspTrCtlAssocChannel
            ACCESS  not-implemented
            DESCRIPTION
                 "tmnxOamLspTrCtlAssocChannel is not implemented on Nokia 7450
                  ESS-6 in release 14.0."

        VARIATION   tmnxOamLspTrCtlLdpPrefixLen
            SYNTAX  InetAddressPrefixLength (32 | 128)
            DESCRIPTION
                 "tmnxOamLspTrCtlLdpPrefixLen supports prefix lengths 32 and 128
                  only."

        VARIATION   tmnxOamLspTrCtlMplsTpPathType
            ACCESS  not-implemented
            DESCRIPTION
                 "tmnxOamLspTrCtlMplsTpPathType is not implemented on Nokia 7450
                  ESS-6 in release 14.0."

        VARIATION   tmnxOamLspTrCtlTestSubMode
            SYNTAX  INTEGER {
                       unspecified(1),
                    -- tpStatic(2)
                       bgpLabeledPrefix(3)
                    }
            DESCRIPTION
                 "'tpStatic(2)' is not supported on Nokia 7450 ESS-6."

        VARIATION   tmnxOamMcastTrCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlDestAddrType supports only the
                  InetAddressType values 'unknown (0)' and 'ipv4 (1)'."

        VARIATION   tmnxOamMcastTrCtlGrpAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlGrpAddrType supports only the InetAddressType
                  values 'unknown (0)' and 'ipv4 (1)'."

        VARIATION   tmnxOamMcastTrCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlSrcAddrType supports only the InetAddressType
                  values 'unknown (0)' and 'ipv4 (1)'."

        VARIATION   tmnxOamMfibPingCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlDestAddrType supports only the
                  InetAddressType values 'unknown (0)' and 'ipv4 (1)'."

        VARIATION   tmnxOamMfibPingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlSrcAddrType supports only the
                  InetAddressType values 'unknown (0)' and 'ipv4 (1)'."

        VARIATION   tmnxOamP2mpLspPingCtlIpAddrType
            SYNTAX  InetAddressType {
                    -- unknown              (0)
                       ipv4                 (1)
                    -- ipv6                 (2)
                    -- ipv4z                (3)
                    -- ipv6z                (4)
                    -- dns                  (16)
                    }
            DESCRIPTION
                 "tmnxOamP2mpLspPingCtlIpAddrType supports only the
                  InetAddressType value 'ipv4 (1)'."

        VARIATION   tmnxOamP2mpLspPingCtlIpRowStatus
            SYNTAX  RowStatus {
                       active               (1),
                    -- notInService         (2)
                    -- notReady             (3)
                       createAndGo          (4),
                    -- createAndWait        (5)
                       destroy              (6)
                    }
            DESCRIPTION
                 "tmnxOamP2mpLspPingCtlIpRowStatus supports only 'active (1)',
                  'createAndGo (4)', and 'destroy (6)'."

        VARIATION   tmnxOamP2mpLspTrCtlLeafIpAddrType
            SYNTAX  InetAddressType {
                       unknown              (0),
                       ipv4                 (1)
                    -- ipv6                 (2)
                    -- ipv4z                (3)
                    -- ipv6z                (4)
                    -- dns                  (16)
                    }
            DESCRIPTION
                 "tmnxOamP2mpLspTrCtlLeafIpAddrType supports only the
                  InetAddressType values 'unknown (0)' and 'ipv4 (1)'."

        VARIATION   tmnxOamPingCtlRowStatus
            SYNTAX  RowStatus {
                       active               (1),
                    -- notInService         (2)
                    -- notReady             (3)
                       createAndGo          (4),
                    -- createAndWait        (5)
                       destroy              (6)
                    }
            DESCRIPTION
                 "tmnxOamPingCtlRowStatus supports only 'active (1)',
                  'createAndGo (4)', and 'destroy (6)'."

        VARIATION   tmnxOamPingCtlSAA
            ACCESS  read-only
            DESCRIPTION
                 "tmnxOamPingCtlSAA is implemented as read-only on Nokia 7450
                  ESS-6 in release 14.0."

        VARIATION   tmnxOamPingCtlTestMode
            SYNTAX  INTEGER {
                       sdpPing              (1),
                       mtuPing              (2),
                       svcPing              (3),
                    -- macQuery             (4) - obsolete
                       macPing              (5),
                       macPopulate          (6),
                       macPurge             (7),
                       lspPing              (8),
                       vprnPing             (9),
                       atmPing              (10),
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21) - not supported
                    }
            DESCRIPTION
                 "The value 'mobGtpPing (21)' is not supported on Nokia 7450
                  ESS-6."

        VARIATION   tmnxOamPingCtlTgtAddrType
            SYNTAX  INTEGER {
                       unknown              (0),
                       ipv4                 (1),
                       ipv6                 (2),
                    -- ipv4z                (3)
                       ipv6z                (4),
                       dns                  (16)
                    }
            DESCRIPTION
                 "tmnxOamPingCtlTgtAddrType does not support the InetAddressType
                  'ipv4z(3)'."

        VARIATION   tmnxOamPingHistorySrcGlobalId
            ACCESS  not-implemented
            DESCRIPTION
                 "tmnxOamPingHistorySrcGlobalId is not implemented on Nokia 7450
                  ESS-6 in release 14.0."

        VARIATION   tmnxOamPingHistorySrcNodeId
            ACCESS  not-implemented
            DESCRIPTION
                 "tmnxOamPingHistorySrcNodeId is not implemented on Nokia 7450
                  ESS-6 in release 14.0."

        VARIATION   tmnxOamSaaCtlRowStatus
            SYNTAX  RowStatus {
                       active               (1),
                    -- notInService         (2)
                    -- notReady             (3)
                       createAndGo          (4),
                    -- createAndWait        (5)
                       destroy              (6)
                    }
            DESCRIPTION
                 "tmnxOamSaaCtlRowStatus supports only 'active (1)',
                  'createAndGo (4)', and 'destroy (6)'."

        VARIATION   tmnxOamSaaTRowStatus
            SYNTAX  RowStatus {
                       active               (1),
                    -- notInService         (2)
                    -- notReady             (3)
                       createAndGo          (4),
                    -- createAndWait        (5)
                       destroy              (6)
                    }
            DESCRIPTION
                 "tmnxOamSaaTRowStatus supports only 'active (1)', 'createAndGo
                  (4)', and 'destroy (6)'."

        VARIATION   tmnxOamSaaTThreshold
            DESCRIPTION
                 "The value of tmnxOamSaaTThreshold must be a multiple of 1000
                  when specifying a tmnxOamSaaTType with units of microseconds."

        VARIATION   tmnxOamTrCtlRowStatus
            SYNTAX  RowStatus {
                       active               (1),
                    -- notInService         (2)
                    -- notReady             (3)
                       createAndGo          (4),
                    -- createAndWait        (5)
                       destroy              (6)
                    }
            DESCRIPTION
                 "tmnxOamTrCtlRowStatus supports only 'active (1)', 'createAndGo
                  (4)', and 'destroy (6)'."

        VARIATION   tmnxOamTrCtlSAA
            ACCESS  read-only
            DESCRIPTION
                 "tmnxOamTrCtlSAA is implemented as read-only on Nokia 7450
                  ESS-6 in release 14.0."

        VARIATION   tmnxOamTrCtlTgtAddrType
            SYNTAX  INTEGER {
                       unknown              (0),
                       ipv4                 (1),
                       ipv6                 (2),
                    -- ipv4z                (3)
                    -- ipv6z                (4)
                       dns                  (16)
                    }
            DESCRIPTION
                 "tmnxOamTrCtlTgtAddrType does not support InetAddressType code
                  points 'ipv4z(3)' and 'ipv6z(4)'."

        VARIATION   tmnxOamTrCtlTrapGeneration
            SYNTAX  BITS {
                    -- pathChange(0)
                       testFailure(1),
                       testCompletion(2)
                    }
            DESCRIPTION
                 "The pathChange bit is not supported."

        VARIATION   tmnxOamTrPathChange
            ACCESS  not-implemented
            DESCRIPTION
                 "tmnxOamTrPathChange notification is not supported."

        VARIATION   tmnxOamTrProbeHistorySrcGlobalId
            ACCESS  not-implemented
            DESCRIPTION
                 "tmnxOamTrProbeHistorySrcGlobalId is not implemented on Nokia
                  7450 ESS-6 in release 14.0."

        VARIATION   tmnxOamTrProbeHistorySrcNodeId
            ACCESS  not-implemented
            DESCRIPTION
                 "tmnxOamTrProbeHistorySrcNodeId is not implemented on Nokia
                  7450 ESS-6 in release 14.0."

        VARIATION   tmnxOamVccvPgTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlDstAddrT supports only the
                  InetAddressType values 'unknown (0)' and 'ipv4 (1)'."

        VARIATION   tmnxOamVccvPgTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlSrcAddrT supports only the
                  InetAddressType values 'unknown (0)' and 'ipv4 (1)'."

        VARIATION   tmnxOamVccvPingCtlAssocChannel
            ACCESS  not-implemented
            DESCRIPTION
                 "tmnxOamVccvPingCtlAssocChannel is not implemented on Nokia
                  7450 ESS-6 in release 14.0."

        VARIATION   tmnxOamVccvPingCtlMplsTpGlobalId
            ACCESS  not-implemented
            DESCRIPTION
                 "tmnxOamVccvPingCtlMplsTpGlobalId is not implemented on Nokia
                  7450 ESS-6 in release 14.0."

        VARIATION   tmnxOamVccvPingCtlMplsTpNodeId
            ACCESS  not-implemented
            DESCRIPTION
                 "tmnxOamVccvPingCtlMplsTpNodeId is not implemented on Nokia
                  7450 ESS-6 in release 14.0."

        VARIATION   tmnxOamVccvPingCtlTestSubMode
            SYNTAX  INTEGER {
                       unspecified(1)
                    -- tpStatic(2)
                    }
            DESCRIPTION
                 "'tpStatic(2)' is not supported on Nokia 7450 ESS-6."

        VARIATION   tmnxOamVccvTrCtlAssocChannel
            ACCESS  not-implemented
            DESCRIPTION
                 "tmnxOamVccvTrCtlAssocChannel is not implemented on Nokia 7450
                  ESS-6 in release 14.0."

        VARIATION   tmnxOamVccvTrCtlTestSubMode
            SYNTAX  INTEGER {
                       unspecified(1)
                    -- tpStatic(2)
                    }
            DESCRIPTION
                 "'tpStatic(2)' is not supported on Nokia 7450 ESS-6."

        VARIATION   tmnxOamVccvTrNextTpAgi
            ACCESS  not-implemented
            DESCRIPTION
                 "tmnxOamVccvTrNextTpAgi is not implemented on Nokia 7450 ESS-6
                  in release 14.0."

        VARIATION   tmnxOamVccvTrNextTpSaiiAcId
            ACCESS  not-implemented
            DESCRIPTION
                 "tmnxOamVccvTrNextTpSaiiAcId is not implemented on Nokia 7450
                  ESS-6 in release 14.0."

        VARIATION   tmnxOamVccvTrNextTpSaiiGlobalId
            ACCESS  not-implemented
            DESCRIPTION
                 "tmnxOamVccvTrNextTpSaiiGlobalId is not implemented on Nokia
                  7450 ESS-6 in release 14.0."

        VARIATION   tmnxOamVccvTrNextTpSaiiNodeId
            ACCESS  not-implemented
            DESCRIPTION
                 "tmnxOamVccvTrNextTpSaiiNodeId is not implemented on Nokia 7450
                  ESS-6 in release 14.0."

        VARIATION   tmnxOamVccvTrNextTpTaiiAcId
            ACCESS  not-implemented
            DESCRIPTION
                 "tmnxOamVccvTrNextTpTaiiAcId is not implemented on Nokia 7450
                  ESS-6 in release 14.0."

        VARIATION   tmnxOamVccvTrNextTpTaiiGlobalId
            ACCESS  not-implemented
            DESCRIPTION
                 "tmnxOamVccvTrNextTpTaiiGlobalId is not implemented on Nokia
                  7450 ESS-6 in release 14.0."

        VARIATION   tmnxOamVccvTrNextTpTaiiNodeId
            ACCESS  not-implemented
            DESCRIPTION
                 "tmnxOamVccvTrNextTpTaiiNodeId is not implemented on Nokia 7450
                  ESS-6 in release 14.0."

        VARIATION   tmnxOamVccvTrTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlDstAddrT supports only the
                  InetAddressType values 'unknown (0)' and 'ipv4 (1)'."

        VARIATION   tmnxOamVccvTrTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlSrcAddrT supports only the
                  InetAddressType values 'unknown (0)' and 'ipv4 (1)'."

        VARIATION   tmnxOamVxlanPingCtlInIpDstAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpDstAddrT supports only the
                  InetAddressType value 'ipv4 (1)'."

        VARIATION   tmnxOamVxlanPingCtlInIpSrcAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpSrcAddrT supports only the
                  InetAddressType value 'ipv4 (1)'."

    ::= { tmnx7450ESS6AgentV14v0  27 }

--
-- 7710 OAM_TEST CAPABILITIES
--
tmnx7710OamTestV14v0              AGENT-CAPABILITIES
    PRODUCT-RELEASE "Nokia SROS"
    STATUS          current
    DESCRIPTION
         "Implementation of OAM test capabilities for Nokia 7710 systems release
          14.0."

    SUPPORTS        TIMETRA-OAM-TEST-MIB
        INCLUDES {
           tmnxOamAncpTestV5v0Group,
-- EXCLUDE tmnxOamAtmPingR2r1Group
           tmnxOamCpePingV4v0Group,
           tmnxOamEthCfmPingV8v0Group,
           tmnxOamEthCfmTrV8v0Group,
           tmnxOamGeneralV10v0Group,
           tmnxOamGeneralV11v0Group,
           tmnxOamGeneralV14v0Group,
           tmnxOamGeneralV8v0Group,
           tmnxOamIcmpPingGroup,
           tmnxOamLTtraceV9v0Group,
           tmnxOamLspPingV11v0Group,
           tmnxOamLspTrV6v0Group,
           tmnxOamMRInfoV4v0Group,
           tmnxOamMacPingCtlV11v0Group,
           tmnxOamMacPingHistoryV11v0Group,
           tmnxOamMacTrV3v0Group,
           tmnxOamMcastTrV4v0Group,
           tmnxOamMfibPingV6v0Group,
           tmnxOamMobilePingGroup,
           tmnxOamP2mpLspPingGroup,
           tmnxOamP2mpLspPingV10v0Group,
           tmnxOamP2mpLspPingV8v0Group,
           tmnxOamP2mpLspTraceGroup,
           tmnxOamPingCtlV10v0Group,
           tmnxOamPingGeneralV10v0Group,
           tmnxOamPingNotificationV7v0Group,
           tmnxOamPingV11v0Group,
           tmnxOamPingV12v0Group,
           tmnxOamPingV13v0Group,
           tmnxOamPingV14v0Group,
           tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrGeneralV8v0Group,
           tmnxOamTrHopsV4v0Group,
           tmnxOamTrNotificationV5v0Group,
           tmnxOamTrNotificationV8v0Group,
           tmnxOamTrV11v0Group,
           tmnxOamTrV12v0Group,
           tmnxOamTrV13v0Group,
           tmnxOamVccvPingV11v0Group,
           tmnxOamVccvPingV5v0Group,
           tmnxOamVccvPingV9v0Group,
           tmnxOamVccvTrV11v0Group,
           tmnxOamVccvTrV6v0Group,
           tmnxOamVccvTrV9v0Group,
           tmnxOamVprnPingV4v0Group,
           tmnxOamVprnTrV6v0Group
        }

        VARIATION   tmnxOamCpePingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamCpePingCtlSrcAddrType supports only the InetAddressType
                  values 'unknown (0)' and 'ipv4 (1)'."

        VARIATION   tmnxOamIcmpTrLabelStackBottom
            ACCESS  not-implemented
            DESCRIPTION
                 "tmnxOamIcmpTrLabelStackBottom is not implemented on Nokia 7710
                  in release 14.0."

        VARIATION   tmnxOamIcmpTrLabelStackExperimnt
            ACCESS  not-implemented
            DESCRIPTION
                 "tmnxOamIcmpTrLabelStackExperimnt is not implemented on Nokia
                  7710 in release 14.0."

        VARIATION   tmnxOamIcmpTrLabelStackLabel
            ACCESS  not-implemented
            DESCRIPTION
                 "tmnxOamIcmpTrLabelStackLabel is not implemented on Nokia 7710
                  in release 14.0."

        VARIATION   tmnxOamIcmpTrLabelStackTtl
            ACCESS  not-implemented
            DESCRIPTION
                 "tmnxOamIcmpTrLabelStackTtl is not implemented on Nokia 7710 in
                  release 14.0."

        VARIATION   tmnxOamLTtraceAutoRowStatus
            SYNTAX  RowStatus {
                       active               (1),
                    -- notInService         (2)
                    -- notReady             (3)
                       createAndGo          (4),
                    -- createAndWait        (5)
                       destroy              (6)
                    }
            DESCRIPTION
                 "tmnxOamLTtraceAutoRowStatus supports only 'active (1)',
                  'createAndGo (4)', and 'destroy (6)'."

        VARIATION   tmnxOamLTtraceCtlLdpPrefixLen
            SYNTAX  InetAddressPrefixLength (32)
            DESCRIPTION
                 "tmnxOamLTtraceCtlLdpPrefixLen supports prefix length 32 only."

        VARIATION   tmnxOamLTtraceCtlLdpPrefixType
            SYNTAX  InetAddressType {
                       unknown              (0),
                       ipv4                 (1)
                    -- ipv6                 (2)
                    -- ipv4z                (3)
                    -- ipv6z                (4)
                    -- dns                  (16)
                    }
            DESCRIPTION
                 "tmnxOamLTtraceCtlLdpPrefixType supports only the
                  InetAddressType values 'unknown (0)' and 'ipv4 (1)'."

        VARIATION   tmnxOamLspPingCtlAssocChannel
            ACCESS  not-implemented
            DESCRIPTION
                 "tmnxOamLspPingCtlAssocChannel is not implemented on Nokia 7710
                  in release 14.0."

        VARIATION   tmnxOamLspPingCtlLdpPrefixLen
            SYNTAX  InetAddressPrefixLength (32 | 128)
            DESCRIPTION
                 "tmnxOamLspPingCtlLdpPrefixLen supports prefix lengths 32 and
                  128 only."

        VARIATION   tmnxOamLspPingCtlMplsTpGlobalId
            ACCESS  not-implemented
            DESCRIPTION
                 "tmnxOamLspPingCtlMplsTpGlobalId is not implemented on Nokia
                  7710 in release 14.0."

        VARIATION   tmnxOamLspPingCtlMplsTpNodeId
            ACCESS  not-implemented
            DESCRIPTION
                 "tmnxOamLspPingCtlMplsTpNodeId is not implemented on Nokia 7710
                  in release 14.0."

        VARIATION   tmnxOamLspPingCtlMplsTpPathType
            ACCESS  not-implemented
            DESCRIPTION
                 "tmnxOamLspPingCtlMplsTpPathType is not implemented on Nokia
                  7710 in release 14.0."

        VARIATION   tmnxOamLspPingCtlTestSubMode
            SYNTAX  INTEGER {
                       unspecified(1),
                    -- tpStatic(2)
                       bgpLabeledPrefix(3)
                    }
            DESCRIPTION
                 "'tpStatic(2)' is not supported on Nokia 7710."

        VARIATION   tmnxOamLspTrCtlAssocChannel
            ACCESS  not-implemented
            DESCRIPTION
                 "tmnxOamLspTrCtlAssocChannel is not implemented on Nokia 7710
                  in release 14.0."

        VARIATION   tmnxOamLspTrCtlLdpPrefixLen
            SYNTAX  InetAddressPrefixLength (32 | 128)
            DESCRIPTION
                 "tmnxOamLspTrCtlLdpPrefixLen supports prefix lengths 32 and 128
                  only."

        VARIATION   tmnxOamLspTrCtlMplsTpPathType
            ACCESS  not-implemented
            DESCRIPTION
                 "tmnxOamLspTrCtlMplsTpPathType is not implemented on Nokia 7710
                  in release 14.0."

        VARIATION   tmnxOamLspTrCtlTestSubMode
            SYNTAX  INTEGER {
                       unspecified(1),
                    -- tpStatic(2)
                       bgpLabeledPrefix(3)
                    }
            DESCRIPTION
                 "'tpStatic(2)' is not supported on Nokia 7710."

        VARIATION   tmnxOamMcastTrCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlDestAddrType supports only the
                  InetAddressType values 'unknown (0)' and 'ipv4 (1)'."

        VARIATION   tmnxOamMcastTrCtlGrpAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlGrpAddrType supports only the InetAddressType
                  values 'unknown (0)' and 'ipv4 (1)'."

        VARIATION   tmnxOamMcastTrCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlSrcAddrType supports only the InetAddressType
                  values 'unknown (0)' and 'ipv4 (1)'."

        VARIATION   tmnxOamMfibPingCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlDestAddrType supports only the
                  InetAddressType values 'unknown (0)' and 'ipv4 (1)'."

        VARIATION   tmnxOamMfibPingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlSrcAddrType supports only the
                  InetAddressType values 'unknown (0)' and 'ipv4 (1)'."

        VARIATION   tmnxOamP2mpLspPingCtlIpAddrType
            SYNTAX  InetAddressType {
                    -- unknown              (0)
                       ipv4                 (1)
                    -- ipv6                 (2)
                    -- ipv4z                (3)
                    -- ipv6z                (4)
                    -- dns                  (16)
                    }
            DESCRIPTION
                 "tmnxOamP2mpLspPingCtlIpAddrType supports only the
                  InetAddressType value 'ipv4 (1)'."

        VARIATION   tmnxOamP2mpLspPingCtlIpRowStatus
            SYNTAX  RowStatus {
                       active               (1),
                    -- notInService         (2)
                    -- notReady             (3)
                       createAndGo          (4),
                    -- createAndWait        (5)
                       destroy              (6)
                    }
            DESCRIPTION
                 "tmnxOamP2mpLspPingCtlIpRowStatus supports only 'active (1)',
                  'createAndGo (4)', and 'destroy (6)'."

        VARIATION   tmnxOamP2mpLspTrCtlLeafIpAddrType
            SYNTAX  InetAddressType {
                       unknown              (0),
                       ipv4                 (1)
                    -- ipv6                 (2)
                    -- ipv4z                (3)
                    -- ipv6z                (4)
                    -- dns                  (16)
                    }
            DESCRIPTION
                 "tmnxOamP2mpLspTrCtlLeafIpAddrType supports only the
                  InetAddressType values 'unknown (0)' and 'ipv4 (1)'."

        VARIATION   tmnxOamPingCtlRowStatus
            SYNTAX  RowStatus {
                       active               (1),
                    -- notInService         (2)
                    -- notReady             (3)
                       createAndGo          (4),
                    -- createAndWait        (5)
                       destroy              (6)
                    }
            DESCRIPTION
                 "tmnxOamPingCtlRowStatus supports only 'active (1)',
                  'createAndGo (4)', and 'destroy (6)'."

        VARIATION   tmnxOamPingCtlSAA
            ACCESS  read-only
            DESCRIPTION
                 "tmnxOamPingCtlSAA is implemented as read-only on Nokia 7710 in
                  release 14.0."

        VARIATION   tmnxOamPingCtlTestMode
            SYNTAX  INTEGER {
                       sdpPing              (1),
                       mtuPing              (2),
                       svcPing              (3),
                    -- macQuery             (4) - obsolete
                       macPing              (5),
                       macPopulate          (6),
                       macPurge             (7),
                       lspPing              (8),
                       vprnPing             (9),
                       atmPing              (10),
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21) - not supported
                    }
            DESCRIPTION
                 "The value 'mobGtpPing (21)' is not supported on Nokia 7710."

        VARIATION   tmnxOamPingCtlTgtAddrType
            SYNTAX  INTEGER {
                       unknown              (0),
                       ipv4                 (1),
                       ipv6                 (2),
                    -- ipv4z                (3)
                       ipv6z                (4),
                       dns                  (16)
                    }
            DESCRIPTION
                 "tmnxOamPingCtlTgtAddrType does not support the InetAddressType
                  'ipv4z(3)'."

        VARIATION   tmnxOamPingHistorySrcGlobalId
            ACCESS  not-implemented
            DESCRIPTION
                 "tmnxOamPingHistorySrcGlobalId is not implemented on Nokia 7710
                  in release 14.0."

        VARIATION   tmnxOamPingHistorySrcNodeId
            ACCESS  not-implemented
            DESCRIPTION
                 "tmnxOamPingHistorySrcNodeId is not implemented on Nokia 7710
                  in release 14.0."

        VARIATION   tmnxOamSaaCtlRowStatus
            SYNTAX  RowStatus {
                       active               (1),
                    -- notInService         (2)
                    -- notReady             (3)
                       createAndGo          (4),
                    -- createAndWait        (5)
                       destroy              (6)
                    }
            DESCRIPTION
                 "tmnxOamSaaCtlRowStatus supports only 'active (1)',
                  'createAndGo (4)', and 'destroy (6)'."

        VARIATION   tmnxOamSaaTRowStatus
            SYNTAX  RowStatus {
                       active               (1),
                    -- notInService         (2)
                    -- notReady             (3)
                       createAndGo          (4),
                    -- createAndWait        (5)
                       destroy              (6)
                    }
            DESCRIPTION
                 "tmnxOamSaaTRowStatus supports only 'active (1)', 'createAndGo
                  (4)', and 'destroy (6)'."

        VARIATION   tmnxOamSaaTThreshold
            DESCRIPTION
                 "The value of tmnxOamSaaTThreshold must be a multiple of 1000
                  when specifying a tmnxOamSaaTType with units of microseconds."

        VARIATION   tmnxOamTrCtlRowStatus
            SYNTAX  RowStatus {
                       active               (1),
                    -- notInService         (2)
                    -- notReady             (3)
                       createAndGo          (4),
                    -- createAndWait        (5)
                       destroy              (6)
                    }
            DESCRIPTION
                 "tmnxOamTrCtlRowStatus supports only 'active (1)', 'createAndGo
                  (4)', and 'destroy (6)'."

        VARIATION   tmnxOamTrCtlSAA
            ACCESS  read-only
            DESCRIPTION
                 "tmnxOamTrCtlSAA is implemented as read-only on Nokia 7710 in
                  release 14.0."

        VARIATION   tmnxOamTrCtlTgtAddrType
            SYNTAX  INTEGER {
                       unknown              (0),
                       ipv4                 (1),
                       ipv6                 (2),
                    -- ipv4z                (3)
                    -- ipv6z                (4)
                       dns                  (16)
                    }
            DESCRIPTION
                 "tmnxOamTrCtlTgtAddrType does not support InetAddressType code
                  points 'ipv4z(3)' and 'ipv6z(4)'."

        VARIATION   tmnxOamTrCtlTrapGeneration
            SYNTAX  BITS {
                    -- pathChange(0)
                       testFailure(1),
                       testCompletion(2)
                    }
            DESCRIPTION
                 "The pathChange bit is not supported."

        VARIATION   tmnxOamTrPathChange
            ACCESS  not-implemented
            DESCRIPTION
                 "tmnxOamTrPathChange notification is not supported."

        VARIATION   tmnxOamTrProbeHistorySrcGlobalId
            ACCESS  not-implemented
            DESCRIPTION
                 "tmnxOamTrProbeHistorySrcGlobalId is not implemented on Nokia
                  7710 in release 14.0."

        VARIATION   tmnxOamTrProbeHistorySrcNodeId
            ACCESS  not-implemented
            DESCRIPTION
                 "tmnxOamTrProbeHistorySrcNodeId is not implemented on Nokia
                  7710 in release 14.0."

        VARIATION   tmnxOamVccvPgTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlDstAddrT supports only the
                  InetAddressType values 'unknown (0)' and 'ipv4 (1)'."

        VARIATION   tmnxOamVccvPgTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlSrcAddrT supports only the
                  InetAddressType values 'unknown (0)' and 'ipv4 (1)'."

        VARIATION   tmnxOamVccvPingCtlAssocChannel
            ACCESS  not-implemented
            DESCRIPTION
                 "tmnxOamVccvPingCtlAssocChannel is not implemented on Nokia
                  7710 in release 14.0."

        VARIATION   tmnxOamVccvPingCtlMplsTpGlobalId
            ACCESS  not-implemented
            DESCRIPTION
                 "tmnxOamVccvPingCtlMplsTpGlobalId is not implemented on Nokia
                  7710 in release 14.0."

        VARIATION   tmnxOamVccvPingCtlMplsTpNodeId
            ACCESS  not-implemented
            DESCRIPTION
                 "tmnxOamVccvPingCtlMplsTpNodeId is not implemented on Nokia
                  7710 in release 14.0."

        VARIATION   tmnxOamVccvPingCtlTestSubMode
            SYNTAX  INTEGER {
                       unspecified(1)
                    -- tpStatic(2)
                    }
            DESCRIPTION
                 "'tpStatic(2)' is not supported on Nokia 7710."

        VARIATION   tmnxOamVccvTrCtlAssocChannel
            ACCESS  not-implemented
            DESCRIPTION
                 "tmnxOamVccvTrCtlAssocChannel is not implemented on Nokia 7710
                  in release 14.0."

        VARIATION   tmnxOamVccvTrCtlTestSubMode
            SYNTAX  INTEGER {
                       unspecified(1)
                    -- tpStatic(2)
                    }
            DESCRIPTION
                 "'tpStatic(2)' is not supported on Nokia 7710."

        VARIATION   tmnxOamVccvTrNextTpAgi
            ACCESS  not-implemented
            DESCRIPTION
                 "tmnxOamVccvTrNextTpAgi is not implemented on Nokia 7710 in
                  release 14.0."

        VARIATION   tmnxOamVccvTrNextTpSaiiAcId
            ACCESS  not-implemented
            DESCRIPTION
                 "tmnxOamVccvTrNextTpSaiiAcId is not implemented on Nokia 7710
                  in release 14.0."

        VARIATION   tmnxOamVccvTrNextTpSaiiGlobalId
            ACCESS  not-implemented
            DESCRIPTION
                 "tmnxOamVccvTrNextTpSaiiGlobalId is not implemented on Nokia
                  7710 in release 14.0."

        VARIATION   tmnxOamVccvTrNextTpSaiiNodeId
            ACCESS  not-implemented
            DESCRIPTION
                 "tmnxOamVccvTrNextTpSaiiNodeId is not implemented on Nokia 7710
                  in release 14.0."

        VARIATION   tmnxOamVccvTrNextTpTaiiAcId
            ACCESS  not-implemented
            DESCRIPTION
                 "tmnxOamVccvTrNextTpTaiiAcId is not implemented on Nokia 7710
                  in release 14.0."

        VARIATION   tmnxOamVccvTrNextTpTaiiGlobalId
            ACCESS  not-implemented
            DESCRIPTION
                 "tmnxOamVccvTrNextTpTaiiGlobalId is not implemented on Nokia
                  7710 in release 14.0."

        VARIATION   tmnxOamVccvTrNextTpTaiiNodeId
            ACCESS  not-implemented
            DESCRIPTION
                 "tmnxOamVccvTrNextTpTaiiNodeId is not implemented on Nokia 7710
                  in release 14.0."

        VARIATION   tmnxOamVccvTrTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlDstAddrT supports only the
                  InetAddressType values 'unknown (0)' and 'ipv4 (1)'."

        VARIATION   tmnxOamVccvTrTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlSrcAddrT supports only the
                  InetAddressType values 'unknown (0)' and 'ipv4 (1)'."

        VARIATION   tmnxOamVxlanPingCtlInIpDstAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpDstAddrT supports only the
                  InetAddressType value 'ipv4 (1)'."

        VARIATION   tmnxOamVxlanPingCtlInIpSrcAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpSrcAddrT supports only the
                  InetAddressType value 'ipv4 (1)'."

    ::= { tmnx7710AgentV14v0  27 }

--
-- 7950 OAM_TEST CAPABILITIES
--
tmnx7950OamTestV14v0              AGENT-CAPABILITIES
    PRODUCT-RELEASE "Nokia SROS"
    STATUS          current
    DESCRIPTION
         "Implementation of OAM test capabilities for Nokia 7950 systems release
          14.0."

    SUPPORTS        TIMETRA-OAM-TEST-MIB
        INCLUDES {
           tmnxOamAncpTestV5v0Group,
-- EXCLUDE tmnxOamAtmPingR2r1Group
           tmnxOamCpePingV4v0Group,
           tmnxOamEthCfmPingV8v0Group,
           tmnxOamEthCfmTrV8v0Group,
           tmnxOamGeneralV10v0Group,
           tmnxOamGeneralV11v0Group,
           tmnxOamGeneralV14v0Group,
           tmnxOamGeneralV8v0Group,
           tmnxOamIcmpPingGroup,
           tmnxOamLTtraceV9v0Group,
           tmnxOamLspPingV11v0Group,
           tmnxOamLspTrV6v0Group,
           tmnxOamMRInfoV4v0Group,
           tmnxOamMacPingCtlV11v0Group,
           tmnxOamMacPingHistoryV11v0Group,
           tmnxOamMacTrV3v0Group,
           tmnxOamMcastTrV4v0Group,
           tmnxOamMfibPingV6v0Group,
           tmnxOamMobilePingGroup,
           tmnxOamP2mpLspPingGroup,
           tmnxOamP2mpLspPingV10v0Group,
           tmnxOamP2mpLspPingV8v0Group,
           tmnxOamP2mpLspTraceGroup,
           tmnxOamPingCtlV10v0Group,
           tmnxOamPingGeneralV10v0Group,
           tmnxOamPingNotificationV7v0Group,
           tmnxOamPingV11v0Group,
           tmnxOamPingV12v0Group,
           tmnxOamPingV13v0Group,
           tmnxOamPingV14v0Group,
           tmnxOamSaaGeneralV10v0Group,
           tmnxOamSaaGeneralV7v0Group,
           tmnxOamSaaGeneralV8v0Group,
           tmnxOamSaaNotificationV3v0Group,
           tmnxOamSaaThresholdV3v0Group,
           tmnxOamTrGeneralV11v0Group,
           tmnxOamTrGeneralV7v0Group,
           tmnxOamTrGeneralV8v0Group,
           tmnxOamTrHopsV4v0Group,
           tmnxOamTrNotificationV5v0Group,
           tmnxOamTrNotificationV8v0Group,
           tmnxOamTrV11v0Group,
           tmnxOamTrV12v0Group,
           tmnxOamTrV13v0Group,
           tmnxOamVccvPingV11v0Group,
           tmnxOamVccvPingV5v0Group,
           tmnxOamVccvPingV9v0Group,
           tmnxOamVccvTrV11v0Group,
           tmnxOamVccvTrV6v0Group,
           tmnxOamVccvTrV9v0Group,
           tmnxOamVprnPingV4v0Group,
           tmnxOamVprnTrV6v0Group
        }

        VARIATION   tmnxOamCpePingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamCpePingCtlSrcAddrType supports only the InetAddressType
                  values 'unknown (0)' and 'ipv4 (1)'."

        VARIATION   tmnxOamLTtraceAutoRowStatus
            SYNTAX  RowStatus {
                       active               (1),
                    -- notInService         (2)
                    -- notReady             (3)
                       createAndGo          (4),
                    -- createAndWait        (5)
                       destroy              (6)
                    }
            DESCRIPTION
                 "tmnxOamLTtraceAutoRowStatus supports only 'active (1)',
                  'createAndGo (4)', and 'destroy (6)'."

        VARIATION   tmnxOamLTtraceCtlLdpPrefixLen
            SYNTAX  InetAddressPrefixLength (32)
            DESCRIPTION
                 "tmnxOamLTtraceCtlLdpPrefixLen supports prefix length 32 only."

        VARIATION   tmnxOamLTtraceCtlLdpPrefixType
            SYNTAX  InetAddressType {
                       unknown              (0),
                       ipv4                 (1)
                    -- ipv6                 (2)
                    -- ipv4z                (3)
                    -- ipv6z                (4)
                    -- dns                  (16)
                    }
            DESCRIPTION
                 "tmnxOamLTtraceCtlLdpPrefixType supports only the
                  InetAddressType values 'unknown (0)' and 'ipv4 (1)'."

        VARIATION   tmnxOamLspPingCtlAssocChannel
            ACCESS  not-implemented
            DESCRIPTION
                 "tmnxOamLspPingCtlAssocChannel is not implemented on Nokia 7950
                  in release 14.0."

        VARIATION   tmnxOamLspPingCtlLdpPrefixLen
            SYNTAX  InetAddressPrefixLength (32 | 128)
            DESCRIPTION
                 "tmnxOamLspPingCtlLdpPrefixLen supports prefix lengths 32 and
                  128 only."

        VARIATION   tmnxOamLspPingCtlMplsTpGlobalId
            ACCESS  not-implemented
            DESCRIPTION
                 "tmnxOamLspPingCtlMplsTpGlobalId is not implemented on Nokia
                  7950 in release 14.0."

        VARIATION   tmnxOamLspPingCtlMplsTpNodeId
            ACCESS  not-implemented
            DESCRIPTION
                 "tmnxOamLspPingCtlMplsTpNodeId is not implemented on Nokia 7950
                  in release 14.0."

        VARIATION   tmnxOamLspPingCtlMplsTpPathType
            ACCESS  not-implemented
            DESCRIPTION
                 "tmnxOamLspPingCtlMplsTpPathType is not implemented on Nokia
                  7950 in release 14.0."

        VARIATION   tmnxOamLspPingCtlTestSubMode
            SYNTAX  INTEGER {
                       unspecified(1),
                    -- tpStatic(2)
                       bgpLabeledPrefix(3)
                    }
            DESCRIPTION
                 "'tpStatic(2)' is not supported on Nokia 7950."

        VARIATION   tmnxOamLspTrCtlAssocChannel
            ACCESS  not-implemented
            DESCRIPTION
                 "tmnxOamLspTrCtlAssocChannel is not implemented on Nokia 7950
                  in release 14.0."

        VARIATION   tmnxOamLspTrCtlLdpPrefixLen
            SYNTAX  InetAddressPrefixLength (32 | 128)
            DESCRIPTION
                 "tmnxOamLspTrCtlLdpPrefixLen supports prefix lengths 32 and 128
                  only."

        VARIATION   tmnxOamLspTrCtlMplsTpPathType
            ACCESS  not-implemented
            DESCRIPTION
                 "tmnxOamLspTrCtlMplsTpPathType is not implemented on Nokia 7950
                  in release 14.0."

        VARIATION   tmnxOamLspTrCtlTestSubMode
            SYNTAX  INTEGER {
                       unspecified(1),
                    -- tpStatic(2)
                       bgpLabeledPrefix(3)
                    }
            DESCRIPTION
                 "'tpStatic(2)' is not supported on Nokia 7950."

        VARIATION   tmnxOamMcastTrCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlDestAddrType supports only the
                  InetAddressType values 'unknown (0)' and 'ipv4 (1)'."

        VARIATION   tmnxOamMcastTrCtlGrpAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlGrpAddrType supports only the InetAddressType
                  values 'unknown (0)' and 'ipv4 (1)'."

        VARIATION   tmnxOamMcastTrCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMcastTrCtlSrcAddrType supports only the InetAddressType
                  values 'unknown (0)' and 'ipv4 (1)'."

        VARIATION   tmnxOamMfibPingCtlDestAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlDestAddrType supports only the
                  InetAddressType values 'unknown (0)' and 'ipv4 (1)'."

        VARIATION   tmnxOamMfibPingCtlSrcAddrType
            SYNTAX  InetAddressType {
                       unknown              (0),
                       ipv4                 (1)
                    -- ipv6                 (2)
                    -- ipv4z                (3)
                    -- ipv6z                (4)
                    -- dns                  (16)
                    }
            DESCRIPTION
                 "tmnxOamMfibPingCtlSrcAddrType supports only the
                  InetAddressType values 'unknown (0)' and 'ipv4 (1)'."

        VARIATION   tmnxOamP2mpLspPingCtlIpAddrType
            SYNTAX  InetAddressType {
                    -- unknown              (0)
                       ipv4                 (1)
                    -- ipv6                 (2)
                    -- ipv4z                (3)
                    -- ipv6z                (4)
                    -- dns                  (16)
                    }
            DESCRIPTION
                 "tmnxOamP2mpLspPingCtlIpAddrType supports only the
                  InetAddressType value 'ipv4 (1)'."

        VARIATION   tmnxOamP2mpLspPingCtlIpRowStatus
            SYNTAX  RowStatus {
                       active               (1),
                    -- notInService         (2)
                    -- notReady             (3)
                       createAndGo          (4),
                    -- createAndWait        (5)
                       destroy              (6)
                    }
            DESCRIPTION
                 "tmnxOamP2mpLspPingCtlIpRowStatus supports only 'active (1)',
                  'createAndGo (4)', and 'destroy (6)'."

        VARIATION   tmnxOamP2mpLspTrCtlLeafIpAddrType
            SYNTAX  InetAddressType {
                       unknown              (0),
                       ipv4                 (1)
                    -- ipv6                 (2)
                    -- ipv4z                (3)
                    -- ipv6z                (4)
                    -- dns                  (16)
                    }
            DESCRIPTION
                 "tmnxOamP2mpLspTrCtlLeafIpAddrType supports only the
                  InetAddressType values 'unknown (0)' and 'ipv4 (1)'."

        VARIATION   tmnxOamPingCtlRowStatus
            SYNTAX  RowStatus {
                       active               (1),
                    -- notInService         (2)
                    -- notReady             (3)
                       createAndGo          (4),
                    -- createAndWait        (5)
                       destroy              (6)
                    }
            DESCRIPTION
                 "tmnxOamPingCtlRowStatus supports only 'active (1)',
                  'createAndGo (4)', and 'destroy (6)'."

        VARIATION   tmnxOamPingCtlSAA
            ACCESS  read-only
            DESCRIPTION
                 "tmnxOamPingCtlSAA is implemented as read-only on Nokia 7950 in
                  release 14.0."

        VARIATION   tmnxOamPingCtlTestMode
            SYNTAX  INTEGER {
                       sdpPing              (1),
                       mtuPing              (2),
                       svcPing              (3),
                    -- macQuery             (4) - obsolete
                       macPing              (5),
                       macPopulate          (6),
                       macPurge             (7),
                       lspPing              (8),
                       vprnPing             (9),
                    -- atmPing              (10)
                       mfibPing             (11),
                       cpePing              (12),
                       mrInfo               (13),
                       vccvPing             (14),
                       icmpPing             (15),
                       dnsPing              (16),
                       ancpLoopback         (17),
                       p2mpLspPing          (18),
                       ethCfmLoopback       (19),
                       ethCfmTwoWayDelay    (20)
                    -- mobGtpPing           (21) - not supported
                    }
            DESCRIPTION
                 "The values 'atmPing (10)' and 'mobGtpPing (21)' are not
                  supported on Nokia 7950."

        VARIATION   tmnxOamPingCtlTgtAddrType
            SYNTAX  INTEGER {
                       unknown              (0),
                       ipv4                 (1),
                       ipv6                 (2),
                    -- ipv4z                (3)
                       ipv6z                (4),
                       dns                  (16)
                    }
            DESCRIPTION
                 "tmnxOamPingCtlTgtAddrType does not support the InetAddressType
                  'ipv4z(3)'."

        VARIATION   tmnxOamPingHistorySrcGlobalId
            ACCESS  not-implemented
            DESCRIPTION
                 "tmnxOamPingHistorySrcGlobalId is not implemented on Nokia 7950
                  in release 14.0."

        VARIATION   tmnxOamPingHistorySrcNodeId
            ACCESS  not-implemented
            DESCRIPTION
                 "tmnxOamPingHistorySrcNodeId is not implemented on Nokia 7950
                  in release 14.0."

        VARIATION   tmnxOamSaaCtlRowStatus
            SYNTAX  RowStatus {
                       active               (1),
                    -- notInService         (2)
                    -- notReady             (3)
                       createAndGo          (4),
                    -- createAndWait        (5)
                       destroy              (6)
                    }
            DESCRIPTION
                 "tmnxOamSaaCtlRowStatus supports only 'active (1)',
                  'createAndGo (4)', and 'destroy (6)'."

        VARIATION   tmnxOamSaaTRowStatus
            SYNTAX  RowStatus {
                       active               (1),
                    -- notInService         (2)
                    -- notReady             (3)
                       createAndGo          (4),
                    -- createAndWait        (5)
                       destroy              (6)
                    }
            DESCRIPTION
                 "tmnxOamSaaTRowStatus supports only 'active (1)', 'createAndGo
                  (4)', and 'destroy (6)'."

        VARIATION   tmnxOamSaaTThreshold
            DESCRIPTION
                 "The value of tmnxOamSaaTThreshold must be a multiple of 1000
                  when specifying a tmnxOamSaaTType with units of microseconds."

        VARIATION   tmnxOamTrCtlRowStatus
            SYNTAX  RowStatus {
                       active               (1),
                    -- notInService         (2)
                    -- notReady             (3)
                       createAndGo          (4),
                    -- createAndWait        (5)
                       destroy              (6)
                    }
            DESCRIPTION
                 "tmnxOamTrCtlRowStatus supports only 'active (1)', 'createAndGo
                  (4)', and 'destroy (6)'."

        VARIATION   tmnxOamTrCtlSAA
            ACCESS  read-only
            DESCRIPTION
                 "tmnxOamTrCtlSAA is implemented as read-only on Nokia 7950 in
                  release 14.0."

        VARIATION   tmnxOamTrCtlTgtAddrType
            SYNTAX  INTEGER {
                       unknown              (0),
                       ipv4                 (1),
                       ipv6                 (2),
                    -- ipv4z                (3)
                    -- ipv6z                (4)
                       dns                  (16)
                    }
            DESCRIPTION
                 "tmnxOamTrCtlTgtAddrType does not support InetAddressType code
                  points 'ipv4z(3)' and 'ipv6z(4)'."

        VARIATION   tmnxOamTrCtlTrapGeneration
            SYNTAX  BITS {
                    -- pathChange(0)
                       testFailure(1),
                       testCompletion(2)
                    }
            DESCRIPTION
                 "The pathChange bit is not supported."

        VARIATION   tmnxOamTrPathChange
            ACCESS  not-implemented
            DESCRIPTION
                 "tmnxOamTrPathChange notification is not supported."

        VARIATION   tmnxOamTrProbeHistorySrcGlobalId
            ACCESS  not-implemented
            DESCRIPTION
                 "tmnxOamTrProbeHistorySrcGlobalId is not implemented on Nokia
                  7950 in release 14.0."

        VARIATION   tmnxOamTrProbeHistorySrcNodeId
            ACCESS  not-implemented
            DESCRIPTION
                 "tmnxOamTrProbeHistorySrcNodeId is not implemented on Nokia
                  7950 in release 14.0."

        VARIATION   tmnxOamVccvPgTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlDstAddrT supports only the
                  InetAddressType values 'unknown (0)' and 'ipv4 (1)'."

        VARIATION   tmnxOamVccvPgTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvPgTgFec128CtlSrcAddrT supports only the
                  InetAddressType values 'unknown (0)' and 'ipv4 (1)'."

        VARIATION   tmnxOamVccvPingCtlAssocChannel
            ACCESS  not-implemented
            DESCRIPTION
                 "tmnxOamVccvPingCtlAssocChannel is not implemented on Nokia
                  7950 in release 14.0."

        VARIATION   tmnxOamVccvPingCtlMplsTpGlobalId
            ACCESS  not-implemented
            DESCRIPTION
                 "tmnxOamVccvPingCtlMplsTpGlobalId is not implemented on Nokia
                  7950 in release 14.0."

        VARIATION   tmnxOamVccvPingCtlMplsTpNodeId
            ACCESS  not-implemented
            DESCRIPTION
                 "tmnxOamVccvPingCtlMplsTpNodeId is not implemented on Nokia
                  7950 in release 14.0."

        VARIATION   tmnxOamVccvPingCtlTestSubMode
            SYNTAX  INTEGER {
                       unspecified(1)
                    -- tpStatic(2)
                    }
            DESCRIPTION
                 "'tpStatic(2)' is not supported on Nokia 7950."

        VARIATION   tmnxOamVccvTrCtlAssocChannel
            ACCESS  not-implemented
            DESCRIPTION
                 "tmnxOamVccvTrCtlAssocChannel is not implemented on Nokia 7950
                  in release 14.0."

        VARIATION   tmnxOamVccvTrCtlTestSubMode
            SYNTAX  INTEGER {
                       unspecified(1)
                    -- tpStatic(2)
                    }
            DESCRIPTION
                 "'tpStatic(2)' is not supported on Nokia 7950."

        VARIATION   tmnxOamVccvTrNextTpAgi
            ACCESS  not-implemented
            DESCRIPTION
                 "tmnxOamVccvTrNextTpAgi is not implemented on Nokia 7950 in
                  release 14.0."

        VARIATION   tmnxOamVccvTrNextTpSaiiAcId
            ACCESS  not-implemented
            DESCRIPTION
                 "tmnxOamVccvTrNextTpSaiiAcId is not implemented on Nokia 7950
                  in release 14.0."

        VARIATION   tmnxOamVccvTrNextTpSaiiGlobalId
            ACCESS  not-implemented
            DESCRIPTION
                 "tmnxOamVccvTrNextTpSaiiGlobalId is not implemented on Nokia
                  7950 in release 14.0."

        VARIATION   tmnxOamVccvTrNextTpSaiiNodeId
            ACCESS  not-implemented
            DESCRIPTION
                 "tmnxOamVccvTrNextTpSaiiNodeId is not implemented on Nokia 7950
                  in release 14.0."

        VARIATION   tmnxOamVccvTrNextTpTaiiAcId
            ACCESS  not-implemented
            DESCRIPTION
                 "tmnxOamVccvTrNextTpTaiiAcId is not implemented on Nokia 7950
                  in release 14.0."

        VARIATION   tmnxOamVccvTrNextTpTaiiGlobalId
            ACCESS  not-implemented
            DESCRIPTION
                 "tmnxOamVccvTrNextTpTaiiGlobalId is not implemented on Nokia
                  7950 in release 14.0."

        VARIATION   tmnxOamVccvTrNextTpTaiiNodeId
            ACCESS  not-implemented
            DESCRIPTION
                 "tmnxOamVccvTrNextTpTaiiNodeId is not implemented on Nokia 7950
                  in release 14.0."

        VARIATION   tmnxOamVccvTrTgFec128CtlDstAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlDstAddrT supports only the
                  InetAddressType values 'unknown (0)' and 'ipv4 (1)'."

        VARIATION   tmnxOamVccvTrTgFec128CtlSrcAddrT
            SYNTAX  InetAddressType {
                       unknown              (0),
                       ipv4                 (1)
                    -- ipv6                 (2)
                    -- ipv4z                (3)
                    -- ipv6z                (4)
                    -- dns                  (16)
                    }
            DESCRIPTION
                 "tmnxOamVccvTrTgFec128CtlSrcAddrT supports only the
                  InetAddressType values 'unknown (0)' and 'ipv4 (1)'."

        VARIATION   tmnxOamVxlanPingCtlInIpDstAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpDstAddrT supports only the
                  InetAddressType value 'ipv4 (1)'."

        VARIATION   tmnxOamVxlanPingCtlInIpSrcAddrT
            SYNTAX  InetAddressType {
                    -- unknown              (0)
                       ipv4                 (1)
                    -- ipv6                 (2)
                    -- ipv4z                (3)
                    -- ipv6z                (4)
                    -- dns                  (16)
                    }
            DESCRIPTION
                 "tmnxOamVxlanPingCtlInIpSrcAddrT supports only the
                  InetAddressType value 'ipv4 (1)'."

    ::= { tmnx7950AgentV14v0  27 }

--
-- 7750SR-7 OES CAPABILITIES
--
tmnx7750SR7OesV14v0               AGENT-CAPABILITIES
    PRODUCT-RELEASE "Nokia SROS"
    STATUS          current
    DESCRIPTION
         "Implementation of OES capabilities for Nokia 7750 SR-7 systems release
          14.0."

    SUPPORTS        TIMETRA-OES-HARDWARE-MIB
        INCLUDES {
           tmnxOesHwGroupV14v0,
           tmnxOesHwNotificationGroupV14v0,
           tmnxOesHwNotifyObjsGroupV14v0
        }

    SUPPORTS        TIMETRA-OES-MIB
        INCLUDES {
           tmnxOesGroupV14v0,
           tmnxOesNotificationGroupV14v0,
           tmnxOesNotifyObjsGroupV14v0
        }

    ::= { tmnx7750SR7AgentV14v0  93 }

--
-- 7750SR-12 OES CAPABILITIES
--
tmnx7750SR12OesV14v0              AGENT-CAPABILITIES
    PRODUCT-RELEASE "Nokia SROS"
    STATUS          current
    DESCRIPTION
         "Implementation of OES capabilities for Nokia 7750 SR-12 systems
          release 14.0."

    SUPPORTS        TIMETRA-OES-HARDWARE-MIB
        INCLUDES {
           tmnxOesHwGroupV14v0,
           tmnxOesHwNotificationGroupV14v0,
           tmnxOesHwNotifyObjsGroupV14v0
        }

    SUPPORTS        TIMETRA-OES-MIB
        INCLUDES {
           tmnxOesGroupV14v0,
           tmnxOesNotificationGroupV14v0,
           tmnxOesNotifyObjsGroupV14v0
        }

    ::= { tmnx7750SR12AgentV14v0  93 }

--
-- 7750SR-12e OES CAPABILITIES
--
tmnx7750SR12eOesV14v0             AGENT-CAPABILITIES
    PRODUCT-RELEASE "Nokia SROS"
    STATUS          current
    DESCRIPTION
         "Implementation of OES capabilities for Nokia 7750 SR-12e systems
          release 14.0."

    SUPPORTS        TIMETRA-OES-HARDWARE-MIB
        INCLUDES {
           tmnxOesHwGroupV14v0,
           tmnxOesHwNotificationGroupV14v0,
           tmnxOesHwNotifyObjsGroupV14v0
        }

    SUPPORTS        TIMETRA-OES-MIB
        INCLUDES {
           tmnxOesGroupV14v0,
           tmnxOesNotificationGroupV14v0,
           tmnxOesNotifyObjsGroupV14v0
        }

    ::= { tmnx7750SR12eAgentV14v0  93 }

--
-- 7950 OES CAPABILITIES
--
tmnx7950OesV14v0                  AGENT-CAPABILITIES
    PRODUCT-RELEASE "Nokia SROS"
    STATUS          current
    DESCRIPTION
         "Implementation of OES capabilities for Nokia 7950 systems release
          14.0."

    SUPPORTS        TIMETRA-OES-HARDWARE-MIB
        INCLUDES {
           tmnxOesHwGroupV14v0,
           tmnxOesHwNotificationGroupV14v0,
           tmnxOesHwNotifyObjsGroupV14v0
        }

    SUPPORTS        TIMETRA-OES-MIB
        INCLUDES {
           tmnxOesGroupV14v0,
           tmnxOesNotificationGroupV14v0,
           tmnxOesNotifyObjsGroupV14v0
        }

    ::= { tmnx7950AgentV14v0  93 }

--
-- SROS OPEN_FLOW CAPABILITIES
--
tmnxSROSOpenFlowV14v0             AGENT-CAPABILITIES
    PRODUCT-RELEASE "Nokia SROS"
    STATUS          current
    DESCRIPTION
         "Implementation of Open Flow capabilities for Nokia SROS systems
          release 14.0."

    SUPPORTS        TIMETRA-OPEN-FLOW-MIB
        INCLUDES {
           tmnxOpenFlowAuxChannelGroup,
           tmnxOpenFlowConfigGroup,
           tmnxOpenFlowNotificationGroup,
           tmnxOpenFlowNotifyObjsGroup,
           tmnxOpenFlowV13v0Group
        }

        VARIATION   tmnxOFControllerAddress
            SYNTAX  InetAddress (SIZE (4))
            DESCRIPTION
                 "tmnxOFControllerAddress only supports InetAddressType 'ipv4
                  (1)'."

        VARIATION   tmnxOFControllerAddressType
            SYNTAX  InetAddressType {
                    -- unknown              (0)
                       ipv4                 (1)
                    -- ipv6                 (2)
                    -- ipv4z                (3)
                    -- ipv6z                (4)
                    -- dns                  (16)
                    }
            DESCRIPTION
                 "tmnxOFControllerAddressType supports only the InetAddressType
                  value 'ipv4 (1)'."

        VARIATION   tmnxOFSwitchAdminState
            SYNTAX  INTEGER {
                    -- noop                 (1)
                       inService            (2),
                       outOfService         (3)
                    }
            DESCRIPTION
                 "tmnxOFSwitchAdminState supports only the values 'inService
                  (2)' and 'outOfService (3)'."

    ::= { tmnxSROSAgentV14v0  89 }

--
-- SROS OSPF CAPABILITIES
--
tmnxSROSOspfV14v0                 AGENT-CAPABILITIES
    PRODUCT-RELEASE "Nokia SROS"
    STATUS          current
    DESCRIPTION
         "Implementation of OSPF protocol capabilities for Nokia SROS systems
          release 14.0."

    SUPPORTS        OSPF-MIB
        INCLUDES {
           ospfAreaAggregateGroup2,
           ospfAreaGroup2,
-- EXCLUDE ospfAreaLsaCountGroup
           ospfAsLsdbGroup,
           ospfBasicGroup2,
-- EXCLUDE ospfExtLsdbGroup
           ospfHostGroup2,
           ospfIfGroup2,
           ospfIfMetricGroup,
           ospfLocalLsdbGroup,
           ospfLsdbGroup,
           ospfNbrGroup2,
           ospfStubAreaGroup,
           ospfVirtIfGroup2,
           ospfVirtLocalLsdbGroup,
           ospfVirtNbrGroup2
        }

        VARIATION   ospfASBdrRtrStatus
            ACCESS  read-only
            DESCRIPTION
                 "ospfASBdrRtrStatus is implemented as read-only on Nokia SROS
                  in release 14.0."

        VARIATION   ospfAddressLessIf
            ACCESS  read-only
            DESCRIPTION
                 "ospfAddressLessIf is implemented as read-only on Nokia SROS in
                  release 14.0."

        VARIATION   ospfAdminStat
            ACCESS  read-only
            DESCRIPTION
                 "ospfAdminStat is implemented as read-only on Nokia SROS in
                  release 14.0."

        VARIATION   ospfAreaAggregateAreaID
            ACCESS  read-only
            DESCRIPTION
                 "ospfAreaAggregateAreaID is implemented as read-only on Nokia
                  SROS in release 14.0."

        VARIATION   ospfAreaAggregateEffect
            ACCESS  read-only
            DESCRIPTION
                 "ospfAreaAggregateEffect is implemented as read-only on Nokia
                  SROS in release 14.0."

        VARIATION   ospfAreaAggregateExtRouteTag
            ACCESS  read-only
            DESCRIPTION
                 "ospfAreaAggregateExtRouteTag is implemented as read-only on
                  Nokia SROS in release 14.0."

        VARIATION   ospfAreaAggregateLsdbType
            ACCESS  read-only
            DESCRIPTION
                 "ospfAreaAggregateLsdbType is implemented as read-only on Nokia
                  SROS in release 14.0."

        VARIATION   ospfAreaAggregateMask
            ACCESS  read-only
            DESCRIPTION
                 "ospfAreaAggregateMask is implemented as read-only on Nokia
                  SROS in release 14.0."

        VARIATION   ospfAreaAggregateNet
            ACCESS  read-only
            DESCRIPTION
                 "ospfAreaAggregateNet is implemented as read-only on Nokia SROS
                  in release 14.0."

        VARIATION   ospfAreaAggregateStatus
            ACCESS  read-only
            DESCRIPTION
                 "ospfAreaAggregateStatus is implemented as read-only on Nokia
                  SROS in release 14.0."

        VARIATION   ospfAreaBdrRtrCount
            ACCESS  read-only
            DESCRIPTION
                 "ospfAreaBdrRtrCount is implemented as read-only on Nokia SROS
                  in release 14.0."

        VARIATION   ospfAreaBdrRtrStatus
            ACCESS  read-only
            DESCRIPTION
                 "ospfAreaBdrRtrStatus is implemented as read-only on Nokia SROS
                  in release 14.0."

        VARIATION   ospfAreaId
            ACCESS  read-only
            DESCRIPTION
                 "ospfAreaId is implemented as read-only on Nokia SROS in
                  release 14.0."

        VARIATION   ospfAreaLsaCksumSum
            ACCESS  read-only
            DESCRIPTION
                 "ospfAreaLsaCksumSum is implemented as read-only on Nokia SROS
                  in release 14.0."

        VARIATION   ospfAreaLsaCount
            ACCESS  read-only
            DESCRIPTION
                 "ospfAreaLsaCount is implemented as read-only on Nokia SROS in
                  release 14.0."

        VARIATION   ospfAreaLsaCountNumber
            ACCESS  read-only
            DESCRIPTION
                 "ospfAreaLsaCountNumber is implemented as read-only on Nokia
                  SROS in release 14.0."

        VARIATION   ospfAreaNssaTranslatorEvents
            ACCESS  read-only
            DESCRIPTION
                 "ospfAreaNssaTranslatorEvents is implemented as read-only on
                  Nokia SROS in release 14.0."

        VARIATION   ospfAreaNssaTranslatorRole
            ACCESS  read-only
            DESCRIPTION
                 "ospfAreaNssaTranslatorRole is implemented as read-only on
                  Nokia SROS in release 14.0."

        VARIATION   ospfAreaNssaTranslatorStabilityInterval
            ACCESS  read-only
            DESCRIPTION
                 "ospfAreaNssaTranslatorStabilityInterval is implemented as
                  read-only on Nokia SROS in release 14.0."

        VARIATION   ospfAreaNssaTranslatorState
            ACCESS  read-only
            DESCRIPTION
                 "ospfAreaNssaTranslatorState is implemented as read-only on
                  Nokia SROS in release 14.0."

        VARIATION   ospfAreaRangeAreaId
            ACCESS  read-only
            DESCRIPTION
                 "ospfAreaRangeAreaId is implemented as read-only on Nokia SROS
                  in release 14.0."

        VARIATION   ospfAreaRangeEffect
            ACCESS  read-only
            DESCRIPTION
                 "ospfAreaRangeEffect is implemented as read-only on Nokia SROS
                  in release 14.0."

        VARIATION   ospfAreaRangeMask
            ACCESS  read-only
            DESCRIPTION
                 "ospfAreaRangeMask is implemented as read-only on Nokia SROS in
                  release 14.0."

        VARIATION   ospfAreaRangeNet
            ACCESS  read-only
            DESCRIPTION
                 "ospfAreaRangeNet is implemented as read-only on Nokia SROS in
                  release 14.0."

        VARIATION   ospfAreaRangeStatus
            ACCESS  read-only
            DESCRIPTION
                 "ospfAreaRangeStatus is implemented as read-only on Nokia SROS
                  in release 14.0."

        VARIATION   ospfAreaStatus
            ACCESS  read-only
            DESCRIPTION
                 "ospfAreaStatus is implemented as read-only on Nokia SROS in
                  release 14.0."

        VARIATION   ospfAreaSummary
            ACCESS  read-only
            DESCRIPTION
                 "ospfAreaSummary is implemented as read-only on Nokia SROS in
                  release 14.0."

        VARIATION   ospfAsBdrRtrCount
            ACCESS  read-only
            DESCRIPTION
                 "ospfAsBdrRtrCount is implemented as read-only on Nokia SROS in
                  release 14.0."

        VARIATION   ospfAsLsaCksumSum
            ACCESS  read-only
            DESCRIPTION
                 "ospfAsLsaCksumSum is implemented as read-only on Nokia SROS in
                  release 14.0."

        VARIATION   ospfAsLsaCount
            ACCESS  read-only
            DESCRIPTION
                 "ospfAsLsaCount is implemented as read-only on Nokia SROS in
                  release 14.0."

        VARIATION   ospfAsLsdbAdvertisement
            ACCESS  read-only
            DESCRIPTION
                 "ospfAsLsdbAdvertisement is implemented as read-only on Nokia
                  SROS in release 14.0."

        VARIATION   ospfAsLsdbAge
            ACCESS  read-only
            DESCRIPTION
                 "ospfAsLsdbAge is implemented as read-only on Nokia SROS in
                  release 14.0."

        VARIATION   ospfAsLsdbChecksum
            ACCESS  read-only
            DESCRIPTION
                 "ospfAsLsdbChecksum is implemented as read-only on Nokia SROS
                  in release 14.0."

        VARIATION   ospfAsLsdbSequence
            ACCESS  read-only
            DESCRIPTION
                 "ospfAsLsdbSequence is implemented as read-only on Nokia SROS
                  in release 14.0."

        VARIATION   ospfDemandExtensions
            ACCESS  read-only
            DESCRIPTION
                 "ospfDemandExtensions is implemented as read-only on Nokia SROS
                  in release 14.0."

        VARIATION   ospfDiscontinuityTime
            ACCESS  read-only
            DESCRIPTION
                 "ospfDiscontinuityTime is implemented as read-only on Nokia
                  SROS in release 14.0."

        VARIATION   ospfExitOverflowInterval
            ACCESS  read-only
            DESCRIPTION
                 "ospfExitOverflowInterval is implemented as read-only on Nokia
                  SROS in release 14.0."

        VARIATION   ospfExtLsdbAdvertisement
            ACCESS  read-only
            DESCRIPTION
                 "ospfExtLsdbAdvertisement is implemented as read-only on Nokia
                  SROS in release 14.0."

        VARIATION   ospfExtLsdbAge
            ACCESS  read-only
            DESCRIPTION
                 "ospfExtLsdbAge is implemented as read-only on Nokia SROS in
                  release 14.0."

        VARIATION   ospfExtLsdbChecksum
            ACCESS  read-only
            DESCRIPTION
                 "ospfExtLsdbChecksum is implemented as read-only on Nokia SROS
                  in release 14.0."

        VARIATION   ospfExtLsdbLimit
            ACCESS  read-only
            DESCRIPTION
                 "ospfExtLsdbLimit is implemented as read-only on Nokia SROS in
                  release 14.0."

        VARIATION   ospfExtLsdbLsid
            ACCESS  read-only
            DESCRIPTION
                 "ospfExtLsdbLsid is implemented as read-only on Nokia SROS in
                  release 14.0."

        VARIATION   ospfExtLsdbRouterId
            ACCESS  read-only
            DESCRIPTION
                 "ospfExtLsdbRouterId is implemented as read-only on Nokia SROS
                  in release 14.0."

        VARIATION   ospfExtLsdbSequence
            ACCESS  read-only
            DESCRIPTION
                 "ospfExtLsdbSequence is implemented as read-only on Nokia SROS
                  in release 14.0."

        VARIATION   ospfExtLsdbType
            ACCESS  read-only
            DESCRIPTION
                 "ospfExtLsdbType is implemented as read-only on Nokia SROS in
                  release 14.0."

        VARIATION   ospfExternLsaCksumSum
            ACCESS  read-only
            DESCRIPTION
                 "ospfExternLsaCksumSum is implemented as read-only on Nokia
                  SROS in release 14.0."

        VARIATION   ospfExternLsaCount
            ACCESS  read-only
            DESCRIPTION
                 "ospfExternLsaCount is implemented as read-only on Nokia SROS
                  in release 14.0."

        VARIATION   ospfHostAreaID
            ACCESS  read-only
            DESCRIPTION
                 "ospfHostAreaID is implemented as read-only on Nokia SROS in
                  release 14.0."

        VARIATION   ospfHostCfgAreaID
            ACCESS  read-only
            DESCRIPTION
                 "ospfHostCfgAreaID is implemented as read-only on Nokia SROS in
                  release 14.0."

        VARIATION   ospfHostIpAddress
            ACCESS  read-only
            DESCRIPTION
                 "ospfHostIpAddress is implemented as read-only on Nokia SROS in
                  release 14.0."

        VARIATION   ospfHostMetric
            ACCESS  read-only
            DESCRIPTION
                 "ospfHostMetric is implemented as read-only on Nokia SROS in
                  release 14.0."

        VARIATION   ospfHostStatus
            ACCESS  read-only
            DESCRIPTION
                 "ospfHostStatus is implemented as read-only on Nokia SROS in
                  release 14.0."

        VARIATION   ospfHostTOS
            ACCESS  read-only
            DESCRIPTION
                 "ospfHostTOS is implemented as read-only on Nokia SROS in
                  release 14.0."

        VARIATION   ospfIfAdminStat
            ACCESS  read-only
            DESCRIPTION
                 "ospfIfAdminStat is implemented as read-only on Nokia SROS in
                  release 14.0."

        VARIATION   ospfIfAreaId
            ACCESS  read-only
            DESCRIPTION
                 "ospfIfAreaId is implemented as read-only on Nokia SROS in
                  release 14.0."

        VARIATION   ospfIfAuthKey
            ACCESS  read-only
            DESCRIPTION
                 "ospfIfAuthKey is implemented as read-only on Nokia SROS in
                  release 14.0."

        VARIATION   ospfIfAuthType
            ACCESS  read-only
            DESCRIPTION
                 "ospfIfAuthType is implemented as read-only on Nokia SROS in
                  release 14.0."

        VARIATION   ospfIfBackupDesignatedRouter
            ACCESS  read-only
            DESCRIPTION
                 "ospfIfBackupDesignatedRouter is implemented as read-only on
                  Nokia SROS in release 14.0."

        VARIATION   ospfIfBackupDesignatedRouterId
            ACCESS  read-only
            DESCRIPTION
                 "ospfIfBackupDesignatedRouterId is implemented as read-only on
                  Nokia SROS in release 14.0."

        VARIATION   ospfIfDemand
            ACCESS  read-only
            DESCRIPTION
                 "ospfIfDemand is implemented as read-only on Nokia SROS in
                  release 14.0."

        VARIATION   ospfIfDesignatedRouter
            ACCESS  read-only
            DESCRIPTION
                 "ospfIfDesignatedRouter is implemented as read-only on Nokia
                  SROS in release 14.0."

        VARIATION   ospfIfDesignatedRouterId
            ACCESS  read-only
            DESCRIPTION
                 "ospfIfDesignatedRouterId is implemented as read-only on Nokia
                  SROS in release 14.0."

        VARIATION   ospfIfEvents
            ACCESS  read-only
            DESCRIPTION
                 "ospfIfEvents is implemented as read-only on Nokia SROS in
                  release 14.0."

        VARIATION   ospfIfHelloInterval
            ACCESS  read-only
            DESCRIPTION
                 "ospfIfHelloInterval is implemented as read-only on Nokia SROS
                  in release 14.0."

        VARIATION   ospfIfIpAddress
            ACCESS  read-only
            DESCRIPTION
                 "ospfIfIpAddress is implemented as read-only on Nokia SROS in
                  release 14.0."

        VARIATION   ospfIfLsaCksumSum
            ACCESS  read-only
            DESCRIPTION
                 "ospfIfLsaCksumSum is implemented as read-only on Nokia SROS in
                  release 14.0."

        VARIATION   ospfIfLsaCount
            ACCESS  read-only
            DESCRIPTION
                 "ospfIfLsaCount is implemented as read-only on Nokia SROS in
                  release 14.0."

        VARIATION   ospfIfMetricAddressLessIf
            ACCESS  read-only
            DESCRIPTION
                 "ospfIfMetricAddressLessIf is implemented as read-only on Nokia
                  SROS in release 14.0."

        VARIATION   ospfIfMetricIpAddress
            ACCESS  read-only
            DESCRIPTION
                 "ospfIfMetricIpAddress is implemented as read-only on Nokia
                  SROS in release 14.0."

        VARIATION   ospfIfMetricStatus
            ACCESS  read-only
            DESCRIPTION
                 "ospfIfMetricStatus is implemented as read-only on Nokia SROS
                  in release 14.0."

        VARIATION   ospfIfMetricTOS
            ACCESS  read-only
            DESCRIPTION
                 "ospfIfMetricTOS is implemented as read-only on Nokia SROS in
                  release 14.0."

        VARIATION   ospfIfMetricValue
            ACCESS  read-only
            DESCRIPTION
                 "ospfIfMetricValue is implemented as read-only on Nokia SROS in
                  release 14.0."

        VARIATION   ospfIfMulticastForwarding
            ACCESS  read-only
            DESCRIPTION
                 "ospfIfMulticastForwarding is implemented as read-only on Nokia
                  SROS in release 14.0."

        VARIATION   ospfIfPollInterval
            ACCESS  read-only
            DESCRIPTION
                 "ospfIfPollInterval is implemented as read-only on Nokia SROS
                  in release 14.0."

        VARIATION   ospfIfRetransInterval
            ACCESS  read-only
            DESCRIPTION
                 "ospfIfRetransInterval is implemented as read-only on Nokia
                  SROS in release 14.0."

        VARIATION   ospfIfRtrDeadInterval
            ACCESS  read-only
            DESCRIPTION
                 "ospfIfRtrDeadInterval is implemented as read-only on Nokia
                  SROS in release 14.0."

        VARIATION   ospfIfRtrPriority
            ACCESS  read-only
            DESCRIPTION
                 "ospfIfRtrPriority is implemented as read-only on Nokia SROS in
                  release 14.0."

        VARIATION   ospfIfState
            ACCESS  read-only
            DESCRIPTION
                 "ospfIfState is implemented as read-only on Nokia SROS in
                  release 14.0."

        VARIATION   ospfIfStatus
            ACCESS  read-only
            DESCRIPTION
                 "ospfIfStatus is implemented as read-only on Nokia SROS in
                  release 14.0."

        VARIATION   ospfIfTransitDelay
            ACCESS  read-only
            DESCRIPTION
                 "ospfIfTransitDelay is implemented as read-only on Nokia SROS
                  in release 14.0."

        VARIATION   ospfIfType
            ACCESS  read-only
            DESCRIPTION
                 "ospfIfType is implemented as read-only on Nokia SROS in
                  release 14.0."

        VARIATION   ospfImportAsExtern
            ACCESS  read-only
            DESCRIPTION
                 "ospfImportAsExtern is implemented as read-only on Nokia SROS
                  in release 14.0."

        VARIATION   ospfLocalLsdbAdvertisement
            ACCESS  read-only
            DESCRIPTION
                 "ospfLocalLsdbAdvertisement is implemented as read-only on
                  Nokia SROS in release 14.0."

        VARIATION   ospfLocalLsdbAge
            ACCESS  read-only
            DESCRIPTION
                 "ospfLocalLsdbAge is implemented as read-only on Nokia SROS in
                  release 14.0."

        VARIATION   ospfLocalLsdbChecksum
            ACCESS  read-only
            DESCRIPTION
                 "ospfLocalLsdbChecksum is implemented as read-only on Nokia
                  SROS in release 14.0."

        VARIATION   ospfLocalLsdbSequence
            ACCESS  read-only
            DESCRIPTION
                 "ospfLocalLsdbSequence is implemented as read-only on Nokia
                  SROS in release 14.0."

        VARIATION   ospfLsdbAdvertisement
            ACCESS  read-only
            DESCRIPTION
                 "ospfLsdbAdvertisement is implemented as read-only on Nokia
                  SROS in release 14.0."

        VARIATION   ospfLsdbAge
            ACCESS  read-only
            DESCRIPTION
                 "ospfLsdbAge is implemented as read-only on Nokia SROS in
                  release 14.0."

        VARIATION   ospfLsdbAreaId
            ACCESS  read-only
            DESCRIPTION
                 "ospfLsdbAreaId is implemented as read-only on Nokia SROS in
                  release 14.0."

        VARIATION   ospfLsdbChecksum
            ACCESS  read-only
            DESCRIPTION
                 "ospfLsdbChecksum is implemented as read-only on Nokia SROS in
                  release 14.0."

        VARIATION   ospfLsdbLsid
            ACCESS  read-only
            DESCRIPTION
                 "ospfLsdbLsid is implemented as read-only on Nokia SROS in
                  release 14.0."

        VARIATION   ospfLsdbRouterId
            ACCESS  read-only
            DESCRIPTION
                 "ospfLsdbRouterId is implemented as read-only on Nokia SROS in
                  release 14.0."

        VARIATION   ospfLsdbSequence
            ACCESS  read-only
            DESCRIPTION
                 "ospfLsdbSequence is implemented as read-only on Nokia SROS in
                  release 14.0."

        VARIATION   ospfLsdbType
            ACCESS  read-only
            DESCRIPTION
                 "ospfLsdbType is implemented as read-only on Nokia SROS in
                  release 14.0."

        VARIATION   ospfMulticastExtensions
            ACCESS  read-only
            DESCRIPTION
                 "ospfMulticastExtensions is implemented as read-only on Nokia
                  SROS in release 14.0."

        VARIATION   ospfNbmaNbrPermanence
            ACCESS  read-only
            DESCRIPTION
                 "ospfNbmaNbrPermanence is implemented as read-only on Nokia
                  SROS in release 14.0."

        VARIATION   ospfNbmaNbrStatus
            ACCESS  read-only
            DESCRIPTION
                 "ospfNbmaNbrStatus is implemented as read-only on Nokia SROS in
                  release 14.0."

        VARIATION   ospfNbrAddressLessIndex
            ACCESS  read-only
            DESCRIPTION
                 "ospfNbrAddressLessIndex is implemented as read-only on Nokia
                  SROS in release 14.0."

        VARIATION   ospfNbrEvents
            ACCESS  read-only
            DESCRIPTION
                 "ospfNbrEvents is implemented as read-only on Nokia SROS in
                  release 14.0."

        VARIATION   ospfNbrHelloSuppressed
            ACCESS  read-only
            DESCRIPTION
                 "ospfNbrHelloSuppressed is implemented as read-only on Nokia
                  SROS in release 14.0."

        VARIATION   ospfNbrIpAddr
            ACCESS  read-only
            DESCRIPTION
                 "ospfNbrIpAddr is implemented as read-only on Nokia SROS in
                  release 14.0."

        VARIATION   ospfNbrLsRetransQLen
            ACCESS  read-only
            DESCRIPTION
                 "ospfNbrLsRetransQLen is implemented as read-only on Nokia SROS
                  in release 14.0."

        VARIATION   ospfNbrOptions
            ACCESS  read-only
            DESCRIPTION
                 "ospfNbrOptions is implemented as read-only on Nokia SROS in
                  release 14.0."

        VARIATION   ospfNbrPriority
            ACCESS  read-only
            DESCRIPTION
                 "ospfNbrPriority is implemented as read-only on Nokia SROS in
                  release 14.0."

        VARIATION   ospfNbrRestartHelperAge
            ACCESS  read-only
            DESCRIPTION
                 "ospfNbrRestartHelperAge is implemented as read-only on Nokia
                  SROS in release 14.0."

        VARIATION   ospfNbrRestartHelperExitReason
            ACCESS  read-only
            DESCRIPTION
                 "ospfNbrRestartHelperExitReason is implemented as read-only on
                  Nokia SROS in release 14.0."

        VARIATION   ospfNbrRestartHelperStatus
            ACCESS  read-only
            DESCRIPTION
                 "ospfNbrRestartHelperStatus is implemented as read-only on
                  Nokia SROS in release 14.0."

        VARIATION   ospfNbrRtrId
            ACCESS  read-only
            DESCRIPTION
                 "ospfNbrRtrId is implemented as read-only on Nokia SROS in
                  release 14.0."

        VARIATION   ospfNbrState
            ACCESS  read-only
            DESCRIPTION
                 "ospfNbrState is implemented as read-only on Nokia SROS in
                  release 14.0."

        VARIATION   ospfOpaqueLsaSupport
            ACCESS  read-only
            DESCRIPTION
                 "ospfOpaqueLsaSupport is implemented as read-only on Nokia SROS
                  in release 14.0."

        VARIATION   ospfOriginateNewLsas
            ACCESS  read-only
            DESCRIPTION
                 "ospfOriginateNewLsas is implemented as read-only on Nokia SROS
                  in release 14.0."

        VARIATION   ospfRFC1583Compatibility
            ACCESS  read-only
            DESCRIPTION
                 "ospfRFC1583Compatibility is implemented as read-only on Nokia
                  SROS in release 14.0."

        VARIATION   ospfReferenceBandwidth
            ACCESS  read-only
            DESCRIPTION
                 "ospfReferenceBandwidth is implemented as read-only on Nokia
                  SROS in release 14.0."

        VARIATION   ospfRestartAge
            ACCESS  read-only
            DESCRIPTION
                 "ospfRestartAge is implemented as read-only on Nokia SROS in
                  release 14.0."

        VARIATION   ospfRestartExitReason
            ACCESS  read-only
            DESCRIPTION
                 "ospfRestartExitReason is implemented as read-only on Nokia
                  SROS in release 14.0."

        VARIATION   ospfRestartInterval
            ACCESS  read-only
            DESCRIPTION
                 "ospfRestartInterval is implemented as read-only on Nokia SROS
                  in release 14.0."

        VARIATION   ospfRestartStatus
            ACCESS  read-only
            DESCRIPTION
                 "ospfRestartStatus is implemented as read-only on Nokia SROS in
                  release 14.0."

        VARIATION   ospfRestartStrictLsaChecking
            ACCESS  read-only
            DESCRIPTION
                 "ospfRestartStrictLsaChecking is implemented as read-only on
                  Nokia SROS in release 14.0."

        VARIATION   ospfRestartSupport
            ACCESS  read-only
            DESCRIPTION
                 "ospfRestartSupport is implemented as read-only on Nokia SROS
                  in release 14.0."

        VARIATION   ospfRouterId
            ACCESS  read-only
            DESCRIPTION
                 "ospfRouterId is implemented as read-only on Nokia SROS in
                  release 14.0."

        VARIATION   ospfRxNewLsas
            ACCESS  read-only
            DESCRIPTION
                 "ospfRxNewLsas is implemented as read-only on Nokia SROS in
                  release 14.0."

        VARIATION   ospfSpfRuns
            ACCESS  read-only
            DESCRIPTION
                 "ospfSpfRuns is implemented as read-only on Nokia SROS in
                  release 14.0."

        VARIATION   ospfStubAreaId
            ACCESS  read-only
            DESCRIPTION
                 "ospfStubAreaId is implemented as read-only on Nokia SROS in
                  release 14.0."

        VARIATION   ospfStubMetric
            ACCESS  read-only
            DESCRIPTION
                 "ospfStubMetric is implemented as read-only on Nokia SROS in
                  release 14.0."

        VARIATION   ospfStubMetricType
            ACCESS  read-only
            DESCRIPTION
                 "ospfStubMetricType is implemented as read-only on Nokia SROS
                  in release 14.0."

        VARIATION   ospfStubRouterAdvertisement
            ACCESS  read-only
            DESCRIPTION
                 "ospfStubRouterAdvertisement is implemented as read-only on
                  Nokia SROS in release 14.0."

        VARIATION   ospfStubRouterSupport
            ACCESS  read-only
            DESCRIPTION
                 "ospfStubRouterSupport is implemented as read-only on Nokia
                  SROS in release 14.0."

        VARIATION   ospfStubStatus
            ACCESS  read-only
            DESCRIPTION
                 "ospfStubStatus is implemented as read-only on Nokia SROS in
                  release 14.0."

        VARIATION   ospfStubTOS
            ACCESS  read-only
            DESCRIPTION
                 "ospfStubTOS is implemented as read-only on Nokia SROS in
                  release 14.0."

        VARIATION   ospfTOSSupport
            ACCESS  read-only
            DESCRIPTION
                 "ospfTOSSupport is implemented as read-only on Nokia SROS in
                  release 14.0."

        VARIATION   ospfVersionNumber
            ACCESS  read-only
            DESCRIPTION
                 "ospfVersionNumber is implemented as read-only on Nokia SROS in
                  release 14.0."

        VARIATION   ospfVirtIfAreaId
            ACCESS  read-only
            DESCRIPTION
                 "ospfVirtIfAreaId is implemented as read-only on Nokia SROS in
                  release 14.0."

        VARIATION   ospfVirtIfAuthKey
            ACCESS  read-only
            DESCRIPTION
                 "ospfVirtIfAuthKey is implemented as read-only on Nokia SROS in
                  release 14.0."

        VARIATION   ospfVirtIfAuthType
            ACCESS  read-only
            DESCRIPTION
                 "ospfVirtIfAuthType is implemented as read-only on Nokia SROS
                  in release 14.0."

        VARIATION   ospfVirtIfEvents
            ACCESS  read-only
            DESCRIPTION
                 "ospfVirtIfEvents is implemented as read-only on Nokia SROS in
                  release 14.0."

        VARIATION   ospfVirtIfHelloInterval
            ACCESS  read-only
            DESCRIPTION
                 "ospfVirtIfHelloInterval is implemented as read-only on Nokia
                  SROS in release 14.0."

        VARIATION   ospfVirtIfLsaCksumSum
            ACCESS  read-only
            DESCRIPTION
                 "ospfVirtIfLsaCksumSum is implemented as read-only on Nokia
                  SROS in release 14.0."

        VARIATION   ospfVirtIfLsaCount
            ACCESS  read-only
            DESCRIPTION
                 "ospfVirtIfLsaCount is implemented as read-only on Nokia SROS
                  in release 14.0."

        VARIATION   ospfVirtIfNeighbor
            ACCESS  read-only
            DESCRIPTION
                 "ospfVirtIfNeighbor is implemented as read-only on Nokia SROS
                  in release 14.0."

        VARIATION   ospfVirtIfRetransInterval
            ACCESS  read-only
            DESCRIPTION
                 "ospfVirtIfRetransInterval is implemented as read-only on Nokia
                  SROS in release 14.0."

        VARIATION   ospfVirtIfRtrDeadInterval
            ACCESS  read-only
            DESCRIPTION
                 "ospfVirtIfRtrDeadInterval is implemented as read-only on Nokia
                  SROS in release 14.0."

        VARIATION   ospfVirtIfState
            ACCESS  read-only
            DESCRIPTION
                 "ospfVirtIfState is implemented as read-only on Nokia SROS in
                  release 14.0."

        VARIATION   ospfVirtIfStatus
            ACCESS  read-only
            DESCRIPTION
                 "ospfVirtIfStatus is implemented as read-only on Nokia SROS in
                  release 14.0."

        VARIATION   ospfVirtIfTransitDelay
            ACCESS  read-only
            DESCRIPTION
                 "ospfVirtIfTransitDelay is implemented as read-only on Nokia
                  SROS in release 14.0."

        VARIATION   ospfVirtLocalLsdbAdvertisement
            ACCESS  read-only
            DESCRIPTION
                 "ospfVirtLocalLsdbAdvertisement is implemented as read-only on
                  Nokia SROS in release 14.0."

        VARIATION   ospfVirtLocalLsdbAge
            ACCESS  read-only
            DESCRIPTION
                 "ospfVirtLocalLsdbAge is implemented as read-only on Nokia SROS
                  in release 14.0."

        VARIATION   ospfVirtLocalLsdbChecksum
            ACCESS  read-only
            DESCRIPTION
                 "ospfVirtLocalLsdbChecksum is implemented as read-only on Nokia
                  SROS in release 14.0."

        VARIATION   ospfVirtLocalLsdbSequence
            ACCESS  read-only
            DESCRIPTION
                 "ospfVirtLocalLsdbSequence is implemented as read-only on Nokia
                  SROS in release 14.0."

        VARIATION   ospfVirtNbrArea
            ACCESS  read-only
            DESCRIPTION
                 "ospfVirtNbrArea is implemented as read-only on Nokia SROS in
                  release 14.0."

        VARIATION   ospfVirtNbrEvents
            ACCESS  read-only
            DESCRIPTION
                 "ospfVirtNbrEvents is implemented as read-only on Nokia SROS in
                  release 14.0."

        VARIATION   ospfVirtNbrHelloSuppressed
            ACCESS  read-only
            DESCRIPTION
                 "ospfVirtNbrHelloSuppressed is implemented as read-only on
                  Nokia SROS in release 14.0."

        VARIATION   ospfVirtNbrIpAddr
            ACCESS  read-only
            DESCRIPTION
                 "ospfVirtNbrIpAddr is implemented as read-only on Nokia SROS in
                  release 14.0."

        VARIATION   ospfVirtNbrLsRetransQLen
            ACCESS  read-only
            DESCRIPTION
                 "ospfVirtNbrLsRetransQLen is implemented as read-only on Nokia
                  SROS in release 14.0."

        VARIATION   ospfVirtNbrOptions
            ACCESS  read-only
            DESCRIPTION
                 "ospfVirtNbrOptions is implemented as read-only on Nokia SROS
                  in release 14.0."

        VARIATION   ospfVirtNbrRestartHelperAge
            ACCESS  read-only
            DESCRIPTION
                 "ospfVirtNbrRestartHelperAge is implemented as read-only on
                  Nokia SROS in release 14.0."

        VARIATION   ospfVirtNbrRestartHelperExitReason
            ACCESS  read-only
            DESCRIPTION
                 "ospfVirtNbrRestartHelperExitReason is implemented as read-only
                  on Nokia SROS in release 14.0."

        VARIATION   ospfVirtNbrRestartHelperStatus
            ACCESS  read-only
            DESCRIPTION
                 "ospfVirtNbrRestartHelperStatus is implemented as read-only on
                  Nokia SROS in release 14.0."

        VARIATION   ospfVirtNbrRtrId
            ACCESS  read-only
            DESCRIPTION
                 "ospfVirtNbrRtrId is implemented as read-only on Nokia SROS in
                  release 14.0."

        VARIATION   ospfVirtNbrState
            ACCESS  read-only
            DESCRIPTION
                 "ospfVirtNbrState is implemented as read-only on Nokia SROS in
                  release 14.0."

    SUPPORTS        OSPF-TRAP-MIB
        INCLUDES {
           ospfTrapControlGroup,
           ospfTrapEventGroup
        }

        VARIATION   ospfSetTrap
            ACCESS  read-only
            DESCRIPTION
                 "ospfSetTrap is implemented as read-only. The generation of
                  OSPF notifications is controlled by tmnxEventTable in the
                  TIMETRA-LOG-MIB."

    SUPPORTS        TIMETRA-OSPF-NG-MIB
        INCLUDES {
           tmnxOspfAreaAggrGroup,
           tmnxOspfAreaV9v0Group,
           tmnxOspfFRRV10v0Group,
           tmnxOspfFRRV11v0Group,
           tmnxOspfGenNotificationV7v0Grp,
           tmnxOspfGeneralV10v0Group,
           tmnxOspfGeneralV11v0Group,
           tmnxOspfGeneralV12v0Group,
           tmnxOspfGeneralV13v0Group,
           tmnxOspfGeneralV14v0Group,
           tmnxOspfGeneralV5v0Group,
           tmnxOspfGeneralV6v0Group,
           tmnxOspfGeneralV6v1Group,
           tmnxOspfGeneralV7v0Group,
           tmnxOspfGeneralV8v0Group,
           tmnxOspfHostGroup,
           tmnxOspfIfV8v0Group,
           tmnxOspfMD5KeyV13v0Group,
           tmnxOspfNgIfOperV9v0Group,
           tmnxOspfNgIfStatsV9v0Group,
           tmnxOspfNgIfV9v0Group,
           tmnxOspfNgLinkLsdbV9v0Group,
           tmnxOspfNgNbrV9v0Group,
           tmnxOspfNotificationV12v0Group,
           tmnxOspfNotificationV13v0Group,
           tmnxOspfNotificationV7v0Group,
           tmnxOspfNotificationV9v0Group,
           tmnxOspfNotifyObjsGroup,
           tmnxOspfSegmentRoutingTEGroup,
           tmnxOspfShamLinksV13v0Group,
           tmnxOspfVirtIfGroup,
           tmnxOspfVirtIfV8v0Group,
           tmnxOspfVirtNbrGroup
        }

        VARIATION   tmnxOspfAreaAggrRouteTag
            ACCESS  read-only
            DESCRIPTION
                 "tmnxOspfAreaAggrRouteTag is implemented as read-only on Nokia
                  SROS in release 14.0."

        VARIATION   tmnxOspfAreaNssaTranslatorRole
            ACCESS  read-only
            DESCRIPTION
                 "tmnxOspfAreaNssaTranslatorRole is implemented as read-only on
                  Nokia SROS in release 14.0."

        VARIATION   tmnxOspfAreaNssaTranslatorStabInt
            ACCESS  read-only
            DESCRIPTION
                 "tmnxOspfAreaNssaTranslatorStabInt is implemented as read-only
                  on Nokia SROS in release 14.0."

        VARIATION   tmnxOspfAreaStubMetricType
            ACCESS  read-only
            DESCRIPTION
                 "tmnxOspfAreaStubMetricType is implemented as read-only on
                  Nokia SROS in release 14.0."

        VARIATION   tmnxOspfBootOverloadAdmState
            SYNTAX  INTEGER {
                       disabled             (1),
                       enabled              (2)
                    -- enabledWaitForBgp    (3)
                    }
            DESCRIPTION
                 "tmnxOspfBootOverloadAdmState only supports 'disabled (1)' and
                  'enabled (2)'. 'enabledWaitForBgp (3) is not implemented."

        VARIATION   tmnxOspfDemandExtensions
            ACCESS  read-only
            DESCRIPTION
                 "tmnxOspfDemandExtensions is implemented as read-only on Nokia
                  SROS in release 14.0."

        VARIATION   tmnxOspfIfDemand
            ACCESS  read-only
            DESCRIPTION
                 "tmnxOspfIfDemand is implemented as read-only on Nokia SROS in
                  release 14.0."

        VARIATION   tmnxOspfIfMulticastForwarding
            ACCESS  read-only
            DESCRIPTION
                 "tmnxOspfIfMulticastForwarding is implemented as read-only on
                  Nokia SROS in release 14.0."

        VARIATION   tmnxOspfMulticastExtensions
            ACCESS  read-only
            DESCRIPTION
                 "tmnxOspfMulticastExtensions is implemented as read-only on
                  Nokia SROS in release 14.0."

        VARIATION   tmnxOspfNgIfMD5KeyStartTime
            ACCESS  read-only
            DESCRIPTION
                 "tmnxOspfNgIfMD5KeyStartTime is implemented as read-only on
                  Nokia SROS in release 14.0."

        VARIATION   tmnxOspfNgIfMD5KeyStopTime
            ACCESS  read-only
            DESCRIPTION
                 "tmnxOspfNgIfMD5KeyStopTime is implemented as read-only on
                  Nokia SROS in release 14.0."

        VARIATION   tmnxOspfNgNbrRestartReason
            SYNTAX  INTEGER (0..255)
            DESCRIPTION
                 "tmnxOspfNgNbrRestartReason supports any value as OSPF graceful
                  restart reason."

        VARIATION   tmnxOspfRestartInterval
            ACCESS  read-only
            DESCRIPTION
                 "tmnxOspfRestartInterval is implemented as read-only on Nokia
                  SROS in release 14.0."

        VARIATION   tmnxOspfRestartSupport
            ACCESS  read-only
            DESCRIPTION
                 "tmnxOspfRestartSupport is implemented as read-only on Nokia
                  SROS in release 14.0."

        VARIATION   tmnxOspfShamIfMD5KeyStartTime
            ACCESS  read-only
            DESCRIPTION
                 "tmnxOspfShamIfMD5KeyStartTime is implemented as read-only on
                  Nokia SROS in release 14.0."

        VARIATION   tmnxOspfShamIfMD5KeyStopTime
            ACCESS  read-only
            DESCRIPTION
                 "tmnxOspfShamIfMD5KeyStopTime is implemented as read-only on
                  Nokia SROS in release 14.0."

        VARIATION   tmnxOspfSrPfxSidActive
            DESCRIPTION
                 "tmnxOspfSrPfxSidActive object is not implemented. Reading this
                  object will always return false."

        VARIATION   tmnxOspfVirtIfMD5KeyStartTime
            ACCESS  read-only
            DESCRIPTION
                 "tmnxOspfVirtIfMD5KeyStartTime is implemented as read-only on
                  Nokia SROS in release 14.0."

        VARIATION   tmnxOspfVirtIfMD5KeyStopTime
            ACCESS  read-only
            DESCRIPTION
                 "tmnxOspfVirtIfMD5KeyStopTime is implemented as read-only on
                  Nokia SROS in release 14.0."

    ::= { tmnxSROSAgentV14v0  29 }

--
-- SROS OTU CAPABILITIES
--
tmnxSROSOtuV14v0                  AGENT-CAPABILITIES
    PRODUCT-RELEASE "Nokia SROS"
    STATUS          current
    DESCRIPTION
         "Implementation of the OTU (Optical Transport Unit) feature on Nokia
          SROS systems release 14.0."

    SUPPORTS        TIMETRA-OTU-MIB
        INCLUDES {
           tmnxOtuIfBaseConfigGroupV8v0,
           tmnxOtuIfFineGrBerGroupV11v0,
           tmnxOtuIfPMGroupV8v0,
           tmnxOtuIfPSIGroupV8v0,
           tmnxOtuIfSMGroup,
           tmnxOtuIfSMGroupV8v0,
           tmnxOtuIfV13v0Group,
           tmnxOtuNotificationGroup,
           tmnxOtuStatsGroup,
           tmnxOtuStatsGroupV8v0
        }

    ::= { tmnxSROSAgentV14v0  69 }

--
-- SROS PCEP CAPABILITIES
--
tmnxSROSPcepV14v0                 AGENT-CAPABILITIES
    PRODUCT-RELEASE "Nokia SROS"
    STATUS          current
    DESCRIPTION
         "Implementation of Path Computation Element communication Protocol
          (PCEP) for Nokia SROS systems release 14.0."

    SUPPORTS        PCE-PCEP-MIB
        INCLUDES {
           pcePcepGeneralGroup
-- EXCLUDE pcePcepNotificationsGroup
        }

        VARIATION   pcePcepEntityConnectMaxRetry
            ACCESS  not-implemented
            DESCRIPTION
                 "pcePcepEntityConnectMaxRetry was not implemented."

        VARIATION   pcePcepEntityInitBackoffTimer
            ACCESS  not-implemented
            DESCRIPTION
                 "pcePcepEntityInitBackoffTimer was not implemented."

        VARIATION   pcePcepEntityMaxBackoffTimer
            ACCESS  not-implemented
            DESCRIPTION
                 "pcePcepEntityMaxBackoffTimer was not implemented."

        VARIATION   pcePcepEntityMaxDeadTimer
            ACCESS  not-implemented
            DESCRIPTION
                 "pcePcepEntityMaxDeadTimer was not implemented."

        VARIATION   pcePcepEntityMaxKeepAliveTimer
            ACCESS  not-implemented
            DESCRIPTION
                 "pcePcepEntityMaxKeepAliveTimer was not implemented."

        VARIATION   pcePcepEntityMinDeadTimer
            ACCESS  not-implemented
            DESCRIPTION
                 "pcePcepEntityMinDeadTimer was not implemented."

        VARIATION   pcePcepEntityMinKeepAliveTimer
            ACCESS  not-implemented
            DESCRIPTION
                 "pcePcepEntityMinKeepAliveTimer was not implemented."

        VARIATION   pcePcepNotificationsMaxRate
            ACCESS  not-implemented
            DESCRIPTION
                 "pcePcepNotificationsMaxRate was not implemented."

        VARIATION   pcePcepPeerAvgRspTime
            ACCESS  not-implemented
            DESCRIPTION
                 "pcePcepPeerAvgRspTime was not implemented."

        VARIATION   pcePcepPeerDiscontinuityTime
            ACCESS  not-implemented
            DESCRIPTION
                 "pcePcepPeerDiscontinuityTime was not implemented."

        VARIATION   pcePcepPeerHWMRspTime
            ACCESS  not-implemented
            DESCRIPTION
                 "pcePcepPeerHWMRspTime was not implemented."

        VARIATION   pcePcepPeerInitiateSession
            ACCESS  not-implemented
            DESCRIPTION
                 "pcePcepPeerInitiateSession was not implemented."

        VARIATION   pcePcepPeerLWMRspTime
            ACCESS  not-implemented
            DESCRIPTION
                 "pcePcepPeerLWMRspTime was not implemented."

        VARIATION   pcePcepPeerNumCorruptRcvd
            ACCESS  not-implemented
            DESCRIPTION
                 "pcePcepPeerNumCorruptRcvd was not implemented."

        VARIATION   pcePcepPeerNumRepRcvdUnknown
            ACCESS  not-implemented
            DESCRIPTION
                 "pcePcepPeerNumRepRcvdUnknown was not implemented."

        VARIATION   pcePcepPeerNumReqRcvdCancelRcvd
            ACCESS  not-implemented
            DESCRIPTION
                 "pcePcepPeerNumReqRcvdCancelRcvd was not implemented."

        VARIATION   pcePcepPeerNumReqRcvdCancelSent
            ACCESS  not-implemented
            DESCRIPTION
                 "pcePcepPeerNumReqRcvdCancelSent was not implemented."

        VARIATION   pcePcepPeerNumReqRcvdClosed
            ACCESS  not-implemented
            DESCRIPTION
                 "pcePcepPeerNumReqRcvdClosed was not implemented."

        VARIATION   pcePcepPeerNumReqRcvdEroSent
            ACCESS  not-implemented
            DESCRIPTION
                 "pcePcepPeerNumReqRcvdEroSent was not implemented."

        VARIATION   pcePcepPeerNumReqRcvdErrorSent
            ACCESS  not-implemented
            DESCRIPTION
                 "pcePcepPeerNumReqRcvdErrorSent was not implemented."

        VARIATION   pcePcepPeerNumReqRcvdNoPathSent
            ACCESS  not-implemented
            DESCRIPTION
                 "pcePcepPeerNumReqRcvdNoPathSent was not implemented."

        VARIATION   pcePcepPeerNumReqRcvdPendRep
            ACCESS  not-implemented
            DESCRIPTION
                 "pcePcepPeerNumReqRcvdPendRep was not implemented."

        VARIATION   pcePcepPeerNumReqRcvdUnknown
            ACCESS  not-implemented
            DESCRIPTION
                 "pcePcepPeerNumReqRcvdUnknown was not implemented."

        VARIATION   pcePcepPeerNumReqSentCancelRcvd
            ACCESS  not-implemented
            DESCRIPTION
                 "pcePcepPeerNumReqSentCancelRcvd was not implemented."

        VARIATION   pcePcepPeerNumReqSentCancelSent
            ACCESS  not-implemented
            DESCRIPTION
                 "pcePcepPeerNumReqSentCancelSent was not implemented."

        VARIATION   pcePcepPeerNumReqSentClosed
            ACCESS  not-implemented
            DESCRIPTION
                 "pcePcepPeerNumReqSentClosed was not implemented."

        VARIATION   pcePcepPeerNumReqSentEroRcvd
            ACCESS  not-implemented
            DESCRIPTION
                 "pcePcepPeerNumReqSentEroRcvd was not implemented."

        VARIATION   pcePcepPeerNumReqSentErrorRcvd
            ACCESS  not-implemented
            DESCRIPTION
                 "pcePcepPeerNumReqSentErrorRcvd was not implemented."

        VARIATION   pcePcepPeerNumReqSentNoPathRcvd
            ACCESS  not-implemented
            DESCRIPTION
                 "pcePcepPeerNumReqSentNoPathRcvd was not implemented."

        VARIATION   pcePcepPeerNumReqSentPendRep
            ACCESS  not-implemented
            DESCRIPTION
                 "pcePcepPeerNumReqSentPendRep was not implemented."

        VARIATION   pcePcepPeerNumReqSentTimeout
            ACCESS  not-implemented
            DESCRIPTION
                 "pcePcepPeerNumReqSentTimeout was not implemented."

        VARIATION   pcePcepPeerNumSvecRcvd
            ACCESS  not-implemented
            DESCRIPTION
                 "pcePcepPeerNumSvecRcvd was not implemented."

        VARIATION   pcePcepPeerNumSvecReqRcvd
            ACCESS  not-implemented
            DESCRIPTION
                 "pcePcepPeerNumSvecReqRcvd was not implemented."

        VARIATION   pcePcepPeerNumSvecReqSent
            ACCESS  not-implemented
            DESCRIPTION
                 "pcePcepPeerNumSvecReqSent was not implemented."

        VARIATION   pcePcepPeerNumSvecSent
            ACCESS  not-implemented
            DESCRIPTION
                 "pcePcepPeerNumSvecSent was not implemented."

        VARIATION   pcePcepPeerNumUnknownRcvd
            ACCESS  not-implemented
            DESCRIPTION
                 "pcePcepPeerNumUnknownRcvd was not implemented."

        VARIATION   pcePcepPeerSessionExists
            ACCESS  not-implemented
            DESCRIPTION
                 "pcePcepPeerSessionExists was not implemented."

        VARIATION   pcePcepPeerSessionFailTime
            ACCESS  not-implemented
            DESCRIPTION
                 "pcePcepPeerSessionFailTime was not implemented."

        VARIATION   pcePcepPeerSessionFailUpTime
            ACCESS  not-implemented
            DESCRIPTION
                 "pcePcepPeerSessionFailUpTime was not implemented."

        VARIATION   pcePcepPeerSessionUpTime
            ACCESS  not-implemented
            DESCRIPTION
                 "pcePcepPeerSessionUpTime was not implemented."

        VARIATION   pcePcepSessTable
            ACCESS  not-implemented
            DESCRIPTION
                 "pcePcepSessTable was not implemented."

    SUPPORTS        TIMETRA-PCEP-MIB
        INCLUDES {
           tmnxPcepConfigGroup,
           tmnxPcepPccConfigGroup,
           tmnxPcepPccLspUpdInfoGroup,
           tmnxPcepPccPeerConfigGroup,
           tmnxPcepPccReqMsgInfoGroup,
           tmnxPcepPccReqPathProfInfoGroup,
           tmnxPcepPcePeerGroup,
           tmnxPcepPeerStatsGroup,
           tmnxPcepTableChngdGroup
        }

        VARIATION   tmnxPcepEntityAdminState
            SYNTAX  INTEGER {
                    -- noop                 (1)
                       inService            (2),
                       outOfService         (3)
                    }
            DESCRIPTION
                 "tmnxPcepEntityAdminState supports only the values 'inService
                  (2)' and 'outOfService (3)'."

        VARIATION   tmnxPcepEntityLocalAddrType
            SYNTAX  InetAddressType {
                       unknown              (0),
                       ipv4                 (1)
                    -- ipv6                 (2)
                    -- ipv4z                (3)
                    -- ipv6z                (4)
                    -- dns                  (16)
                    }
            DESCRIPTION
                 "tmnxPcepEntityLocalAddrType supports only the InetAddressType
                  values 'unknown (0)' and 'ipv4 (1)'."

        VARIATION   tmnxPcepPeerAddrType
            SYNTAX  InetAddressType {
                    -- unknown              (0)
                       ipv4                 (1)
                    -- ipv6                 (2)
                    -- ipv4z                (3)
                    -- ipv6z                (4)
                    -- dns                  (16)
                    }
            DESCRIPTION
                 "tmnxPcepPeerAddrType supports only the InetAddressType value
                  'ipv4 (1)'."

    ::= { tmnxSROSAgentV14v0  90 }

--
-- SROS PIM CAPABILITIES
--
tmnxSROSPimV14v0                  AGENT-CAPABILITIES
    PRODUCT-RELEASE "Nokia SROS"
    STATUS          current
    DESCRIPTION
         "Implementation of PIM protocol capabilities for Nokia SROS systems
          release 14.0."

    SUPPORTS        TIMETRA-PIM-NG-MIB
        INCLUDES {
           tmnxPimAsmExtranetV13v0Grp,
           tmnxPimIfSecNbrV6v0Group,
           tmnxPimNgCDV12v0Grp,
           tmnxPimNgDMAutoRpV14v0Group,
           tmnxPimNgDataMtPlcyV14v0Group,
           tmnxPimNgEchoGroup,
           tmnxPimNgEmbeddedRPV7v0Group,
           tmnxPimNgFastFailover11v0Group,
           tmnxPimNgGenStatMdtsV14v0Group,
           tmnxPimNgGenV14v0Group,
           tmnxPimNgGlobalGroupV10v0,
           tmnxPimNgGlobalGroupV8v0,
           tmnxPimNgGlobalGrpSrcV10v0Group,
           tmnxPimNgGlobalGrpSrcV9v0Group,
           tmnxPimNgGlobalSSMV6v1Group,
           tmnxPimNgIfGroup,
           tmnxPimNgIfIPMSIV9v0Group,
           tmnxPimNgIfIpv6BfdV9v0Group,
           tmnxPimNgIfStatsV10v0Group,
           tmnxPimNgIfStatsV7v0Group,
           tmnxPimNgIfStatsV9v0Group,
           tmnxPimNgIfV12v0Group,
           tmnxPimNgIfV13v0Group,
           tmnxPimNgIfV14v0Group,
           tmnxPimNgIfV8v0Group,
           tmnxPimNgInterASMvpnV11v0Group,
           tmnxPimNgLdpEntryV10v0Group,
           tmnxPimNgMVPNSndrRecvV11v0Group,
           tmnxPimNgMcastInbandSigV13v0Grp,
           tmnxPimNgMulticastSpmsiV13v0Grp,
           tmnxPimNgMvpnExtranetGroupV10v0,
           tmnxPimNgMvpnSrcPrefixV12v0Grp,
           tmnxPimNgMvpnV8v0Group,
           tmnxPimNgMvpnV9v0Group,
           tmnxPimNgMvpnV9v0R4Group,
           tmnxPimNgNotificationGroup,
           tmnxPimNgNotificationV14v0Group,
           tmnxPimNgNotificationV7v0Group,
           tmnxPimNgNotifyObjsV14v0Group,
           tmnxPimNgNotifyObjsV7v0Group,
           tmnxPimNgNotifyObjsV8v0Group,
           tmnxPimNgNotifyObjsV9v0Group,
           tmnxPimNgObsoletedV13v0Group,
           tmnxPimNgSgStatcExtrntV12v0Grp,
           tmnxPimNgUnicastRtRemV12v0Group,
           tmnxPimNgV7v0Group
        }

        VARIATION   vRtrPimNgAFGenMvpnUMHSelection
            SYNTAX  INTEGER {
                       highestip            (0),
                       hashbased            (1)
                    -- tunnelstatus         (2)
                    }
            DESCRIPTION
                 "vRtrPimNgAFGenMvpnUMHSelection does not support the value
                  'tunnelStatus (2)' for version 9.0R1 on Nokia SROS."

        VARIATION   vRtrPimNgIfMcacConstAdminState
            SYNTAX  INTEGER {
                    -- noop                 (1)
                       inService            (2),
                       outOfService         (3)
                    }
            DESCRIPTION
                 "vRtrPimNgIfMcacConstAdminState supports only the values
                  'inService (2)' and 'outOfService (3)'."

        VARIATION   vRtrPimNgMvpnUMHPEStandbyAddr
            SYNTAX  InetAddress (SIZE (4))
            DESCRIPTION
                 "vRtrPimNgMvpnUMHPEStandbyAddr supports only InetAddressType
                  'ipv4'."

        VARIATION   vRtrPimNgMvpnUMHPEStandbyAdrTyp
            SYNTAX  InetAddressType {
                    -- unknown              (0)
                       ipv4                 (1)
                    -- ipv6                 (2)
                    -- ipv4z                (3)
                    -- ipv6z                (4)
                    -- dns                  (16)
                    }
            DESCRIPTION
                 "vRtrPimNgMvpnUMHPEStandbyAdrTyp supports only the
                  InetAddressType value 'ipv4 (1)'."

        VARIATION   vRtrPimNgRsvpIfSenderAddr
            SYNTAX  InetAddress (SIZE (4))
            DESCRIPTION
                 "vRtrPimNgRsvpIfSenderAddr supports only InetAddressType
                  'ipv4'."

        VARIATION   vRtrPimNgRsvpIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrPimNgRsvpIfSenderAddrType supports only the
                  InetAddressType value 'ipv4 (1)'."

    ::= { tmnxSROSAgentV14v0  30 }

--
-- SROS PIM_SNOOPING CAPABILITIES
--
tmnxSROSPimSnoopingV14v0          AGENT-CAPABILITIES
    PRODUCT-RELEASE "Nokia SROS"
    STATUS          current
    DESCRIPTION
         "Implementation of the PIM Snooping feature on Nokia SROS systems
          release 14.0."

    SUPPORTS        TIMETRA-PIM-SNOOPING-MIB
        INCLUDES {
           tmnxPimSnpgGlobalGroup,
           tmnxPimSnpgIfGroup,
           tmnxPimSnpgIfSecNbrV6v0Group,
           tmnxPimSnpgIfV14v0Group,
           tmnxPimSnpgNotificationGroup
        }

    ::= { tmnxSROSAgentV14v0  63 }

--
-- SROS PORT CAPABILITIES
--
tmnxSROSPortV14v0                 AGENT-CAPABILITIES
    PRODUCT-RELEASE "Nokia SROS"
    STATUS          current
    DESCRIPTION
         "Implementation of hardware port capabilities for Nokia SROS systems
          release 14.0."

    SUPPORTS        TIMETRA-PORT-MIB
        INCLUDES {
-- EXCLUDE tmnx7710PortTDMGroupV5v0
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
-- EXCLUDE tmnxFrIntfGroup
-- EXCLUDE tmnxFrf12IntfGroup
           tmnxHsmdaGroupV10v0,
-- EXCLUDE tmnxMcMfrBundleGroup
           tmnxMcMlpppBundleGroup,
           tmnxMlBundleGroupV6v0,
-- EXCLUDE tmnxMlImaBundleGroup
           tmnxMlpppBundleGroup,
           tmnxMlpppBundleGroupV7v0,
-- EXCLUDE tmnxNamedPoolGroupV6v0
           tmnxOpticalPortGroup,
           tmnxOpticalPortGroupV9v0,
           tmnxPortATMGroupV7v0,
           tmnxPortATMGroupV9v0,
           tmnxPortAggRateLimitV13v0Group,
           tmnxPortAggRateV12v0Group,
-- EXCLUDE tmnxPortCEMGroupV8v0
-- EXCLUDE tmnxPortCemGroupV6v0
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
           tmnxPortParentLocV12v0Group,
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia SROS in release 14.0."

        VARIATION   tmnxBundleImaGrpNeClockMode
            ACCESS  read-only
            DESCRIPTION
                 "tmnxBundleImaGrpNeClockMode is implemented as read-only on
                  Nokia SROS in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia SROS
                  in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12),
                       cemEncap             (13)
                    }
            DESCRIPTION
                 "tmnxPortEncapType is implemented as read-only for Multi-Link
                  PPP (MLPPP) bundles and IMA bundles."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia SROS. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnxSROSAgentV14v0  31 }

--
-- 7750 PORT CAPABILITIES
--
tmnx7750PortV14v0                 AGENT-CAPABILITIES
    PRODUCT-RELEASE "Nokia SROS"
    STATUS          current
    DESCRIPTION
         "Implementation of hardware port capabilities for Nokia 7750 systems
          release 14.0."

    SUPPORTS        TIMETRA-PORT-MIB
        INCLUDES {
-- EXCLUDE tmnx7710PortTDMGroupV5v0
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
           tmnxFrIntfGroup,
           tmnxFrf12IntfGroup,
           tmnxHsmdaGroupV10v0,
           tmnxMcMfrBundleGroup,
           tmnxMcMlpppBundleGroup,
           tmnxMlBundleGroupV6v0,
           tmnxMlImaBundleGroup,
           tmnxMlpppBundleGroup,
           tmnxMlpppBundleGroupV7v0,
           tmnxNamedPoolGroupV6v0,
           tmnxOpticalPortGroup,
           tmnxOpticalPortGroupV9v0,
           tmnxPortATMGroupV7v0,
           tmnxPortATMGroupV9v0,
           tmnxPortAggRateLimitV13v0Group,
           tmnxPortAggRateV12v0Group,
           tmnxPortCEMGroupV8v0,
           tmnxPortCemGroupV6v0,
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
           tmnxPortParentLocV12v0Group,
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia 7750 in release 14.0."

        VARIATION   tmnxBundleImaGrpNeClockMode
            ACCESS  read-only
            DESCRIPTION
                 "tmnxBundleImaGrpNeClockMode is implemented as read-only on
                  Nokia 7750 in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1ClockSource
            SYNTAX  INTEGER {
                       loopTimed            (1),
                       nodeTimed            (2),
                       adaptive             (3)
                    -- differential         (4)
                    }
            DESCRIPTION
                 "tmnxDS1ClockSource value of 'differential (4)' is not
                  supported on Nokia 7750."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia 7750
                  in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12),
                       cemEncap             (13)
                    }
            DESCRIPTION
                 "tmnxPortEncapType is implemented as read-only for Multi-Link
                  PPP (MLPPP) bundles and IMA bundles."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia 7750. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnx7750AgentV14v0  31 }

--
-- 7750c12 PORT CAPABILITIES
--
tmnx7750c12PortV14v0              AGENT-CAPABILITIES
    PRODUCT-RELEASE "Nokia SROS"
    STATUS          current
    DESCRIPTION
         "Implementation of hardware port capabilities for Nokia 7750 c12
          systems release 14.0."

    SUPPORTS        TIMETRA-PORT-MIB
        INCLUDES {
           tmnx7710PortTDMGroupV5v0,
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
           tmnxFrIntfGroup,
           tmnxFrf12IntfGroup,
-- EXCLUDE tmnxHsmdaGroupV10v0
           tmnxMcMfrBundleGroup,
           tmnxMcMlpppBundleGroup,
           tmnxMlBundleGroupV6v0,
           tmnxMlImaBundleGroup,
           tmnxMlpppBundleGroup,
           tmnxMlpppBundleGroupV7v0,
           tmnxNamedPoolGroupV6v0,
           tmnxOpticalPortGroup,
           tmnxOpticalPortGroupV9v0,
           tmnxPortATMGroupV7v0,
           tmnxPortATMGroupV9v0,
           tmnxPortAggRateLimitV13v0Group,
           tmnxPortAggRateV12v0Group,
           tmnxPortCEMGroupV8v0,
           tmnxPortCemGroupV6v0,
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
           tmnxPortParentLocV12v0Group,
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia 7750 c12 in release 14.0."

        VARIATION   tmnxBundleImaGrpNeClockMode
            ACCESS  read-only
            DESCRIPTION
                 "tmnxBundleImaGrpNeClockMode is implemented as read-only on
                  Nokia 7750 c12 in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1ClockSource
            SYNTAX  INTEGER {
                       loopTimed            (1),
                       nodeTimed            (2),
                       adaptive             (3)
                    -- differential         (4)
                    }
            DESCRIPTION
                 "tmnxDS1ClockSource value of 'differential (4)' is not
                  supported on Nokia 7750 c12."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia 7750
                  c12 in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12),
                       cemEncap             (13)
                    }
            DESCRIPTION
                 "tmnxPortEncapType is implemented as read-only for Multi-Link
                  PPP (MLPPP) bundles and IMA bundles."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia 7750 c12. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnx7750c12AgentV14v0  31 }

--
-- 7750c4 PORT CAPABILITIES
--
tmnx7750c4PortV14v0               AGENT-CAPABILITIES
    PRODUCT-RELEASE "Nokia SROS"
    STATUS          current
    DESCRIPTION
         "Implementation of hardware port capabilities for Nokia 7750 c4 systems
          release 14.0."

    SUPPORTS        TIMETRA-PORT-MIB
        INCLUDES {
           tmnx7710PortTDMGroupV5v0,
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
           tmnxFrIntfGroup,
           tmnxFrf12IntfGroup,
-- EXCLUDE tmnxHsmdaGroupV10v0
           tmnxMcMfrBundleGroup,
           tmnxMcMlpppBundleGroup,
           tmnxMlBundleGroupV6v0,
           tmnxMlImaBundleGroup,
           tmnxMlpppBundleGroup,
           tmnxMlpppBundleGroupV7v0,
           tmnxNamedPoolGroupV6v0,
           tmnxOpticalPortGroup,
           tmnxOpticalPortGroupV9v0,
           tmnxPortATMGroupV7v0,
           tmnxPortATMGroupV9v0,
           tmnxPortAggRateLimitV13v0Group,
           tmnxPortAggRateV12v0Group,
           tmnxPortCEMGroupV8v0,
           tmnxPortCemGroupV6v0,
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
           tmnxPortParentLocV12v0Group,
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia 7750 c4 in release 14.0."

        VARIATION   tmnxBundleImaGrpNeClockMode
            ACCESS  read-only
            DESCRIPTION
                 "tmnxBundleImaGrpNeClockMode is implemented as read-only on
                  Nokia 7750 c4 in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1ClockSource
            SYNTAX  INTEGER {
                       loopTimed            (1),
                       nodeTimed            (2),
                       adaptive             (3)
                    -- differential         (4)
                    }
            DESCRIPTION
                 "tmnxDS1ClockSource value of 'differential (4)' is not
                  supported on Nokia 7750 c4."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia 7750
                  c4 in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12),
                       cemEncap             (13)
                    }
            DESCRIPTION
                 "tmnxPortEncapType is implemented as read-only for Multi-Link
                  PPP (MLPPP) bundles and IMA bundles."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia 7750 c4. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnx7750c4AgentV14v0  31 }

--
-- 7450 PORT CAPABILITIES
--
tmnx7450PortV14v0                 AGENT-CAPABILITIES
    PRODUCT-RELEASE "Nokia SROS"
    STATUS          current
    DESCRIPTION
         "Implementation of hardware port capabilities for Nokia 7450 systems
          release 14.0."

    SUPPORTS        TIMETRA-PORT-MIB
        INCLUDES {
-- EXCLUDE tmnx7710PortTDMGroupV5v0
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
           tmnxFrIntfGroup,
           tmnxFrf12IntfGroup,
           tmnxHsmdaGroupV10v0,
           tmnxMcMfrBundleGroup,
           tmnxMcMlpppBundleGroup,
           tmnxMlBundleGroupV6v0,
           tmnxMlImaBundleGroup,
           tmnxMlpppBundleGroup,
           tmnxMlpppBundleGroupV7v0,
           tmnxNamedPoolGroupV6v0,
           tmnxOpticalPortGroup,
           tmnxOpticalPortGroupV9v0,
           tmnxPortATMGroupV7v0,
           tmnxPortATMGroupV9v0,
           tmnxPortAggRateLimitV13v0Group,
           tmnxPortAggRateV12v0Group,
-- EXCLUDE tmnxPortCEMGroupV8v0
-- EXCLUDE tmnxPortCemGroupV6v0
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
           tmnxPortParentLocV12v0Group,
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia 7450 in release 14.0."

        VARIATION   tmnxBundleImaGrpNeClockMode
            ACCESS  read-only
            DESCRIPTION
                 "tmnxBundleImaGrpNeClockMode is implemented as read-only on
                  Nokia 7450 in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1ClockSource
            SYNTAX  INTEGER {
                       loopTimed            (1),
                       nodeTimed            (2)
                    -- adaptive             (3)
                    -- differential         (4)
                    }
            DESCRIPTION
                 "tmnxDS1ClockSource values of 'adaptive (3)' and 'differential
                  (4)' are not supported on Nokia 7450."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia 7450
                  in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12)
                    -- cemEncap             (13)
                    }
            DESCRIPTION
                 "tmnxPortEncapType is implemented as read-only for Multi-Link
                  PPP (MLPPP) bundles and IMA bundles. Also the value 'cemEncap
                  (13)' is not supported on Nokia 7450."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia 7450. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnx7450AgentV14v0  31 }

--
-- 7710 PORT CAPABILITIES
--
tmnx7710PortV14v0                 AGENT-CAPABILITIES
    PRODUCT-RELEASE "Nokia SROS"
    STATUS          current
    DESCRIPTION
         "Implementation of hardware port capabilities for Nokia 7710 systems
          release 14.0."

    SUPPORTS        TIMETRA-PORT-MIB
        INCLUDES {
           tmnx7710PortTDMGroupV5v0,
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
-- EXCLUDE tmnxFrIntfGroup
-- EXCLUDE tmnxFrf12IntfGroup
-- EXCLUDE tmnxHsmdaGroupV10v0
-- EXCLUDE tmnxMcMfrBundleGroup
           tmnxMcMlpppBundleGroup,
           tmnxMlBundleGroupV6v0,
-- EXCLUDE tmnxMlImaBundleGroup
           tmnxMlpppBundleGroup,
           tmnxMlpppBundleGroupV7v0,
-- EXCLUDE tmnxNamedPoolGroupV6v0
           tmnxOpticalPortGroup,
           tmnxOpticalPortGroupV9v0,
           tmnxPortATMGroupV7v0,
           tmnxPortATMGroupV9v0,
           tmnxPortAggRateLimitV13v0Group,
           tmnxPortAggRateV12v0Group,
           tmnxPortCEMGroupV8v0,
           tmnxPortCemGroupV6v0,
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
-- EXCLUDE tmnxPortParentLocV12v0Group
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia 7710 in release 14.0."

        VARIATION   tmnxBundleImaGrpNeClockMode
            ACCESS  read-only
            DESCRIPTION
                 "tmnxBundleImaGrpNeClockMode is implemented as read-only on
                  Nokia 7710 in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia 7710
                  in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12),
                       cemEncap             (13)
                    }
            DESCRIPTION
                 "tmnxPortEncapType is implemented as read-only for Multi-Link
                  PPP (MLPPP) bundles and IMA bundles."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia 7710. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnx7710AgentV14v0  31 }

--
-- 7950 PORT CAPABILITIES
--
tmnx7950PortV14v0                 AGENT-CAPABILITIES
    PRODUCT-RELEASE "Nokia SROS"
    STATUS          current
    DESCRIPTION
         "Implementation of hardware port capabilities for Nokia 7950 systems
          release 14.0."

    SUPPORTS        TIMETRA-PORT-MIB
        INCLUDES {
-- EXCLUDE tmnx7710PortTDMGroupV5v0
           tmnxCiscoHDLCGroup,
           tmnxCohOptPortGroup,
           tmnxCohOptPortStatsGroup,
           tmnxCohOptPortStatsV12v0Group,
           tmnxCohOptPortV11v0Group,
           tmnxCohOptPortV12v0Group,
           tmnxDDMLaneGroupV10v0,
           tmnxDS3V12v0Group,
           tmnxDigitalDiagMonitorGroup,
           tmnxDot1xPaePortGroup,
-- EXCLUDE tmnxFrIntfGroup
-- EXCLUDE tmnxFrf12IntfGroup
-- EXCLUDE tmnxHsmdaGroupV10v0
-- EXCLUDE tmnxMcMfrBundleGroup
           tmnxMcMlpppBundleGroup,
           tmnxMlBundleGroupV6v0,
-- EXCLUDE tmnxMlImaBundleGroup
           tmnxMlpppBundleGroup,
           tmnxMlpppBundleGroupV7v0,
-- EXCLUDE tmnxNamedPoolGroupV6v0
           tmnxOpticalPortGroup,
           tmnxOpticalPortGroupV9v0,
           tmnxPortATMGroupV7v0,
           tmnxPortATMGroupV9v0,
           tmnxPortAggRateLimitV13v0Group,
           tmnxPortAggRateV12v0Group,
-- EXCLUDE tmnxPortCEMGroupV8v0
-- EXCLUDE tmnxPortCemGroupV6v0
           tmnxPortDwdmGroup,
           tmnxPortEgrExpShaperV9v0Group,
           tmnxPortEgrHsmdaOverV11v0Group,
           tmnxPortEgrHsmdaStatV11v0Group,
           tmnxPortEgrQGrpV11v0Group,
           tmnxPortEgrQosStatsGroup,
           tmnxPortEgrVPortStatsV9v0Group,
           tmnxPortEthPTPAsymGroupV14v0,
           tmnxPortEthSymMonNotifyGrpV12v0,
           tmnxPortEtherAccessV14v0Group,
           tmnxPortEtherPhysStatsGroup,
           tmnxPortEtherRsFecModeGroup,
           tmnxPortEtherSymMonGroupV12v0,
           tmnxPortEtherV9v0Group,
           tmnxPortEthernetV10v0Group,
           tmnxPortEthernetV11v0Group,
           tmnxPortEthernetV12v0Group,
           tmnxPortEthernetV7v0Group,
           tmnxPortFRGroup,
           tmnxPortFwdEngStatsGroup,
           tmnxPortGroup,
           tmnxPortGroupV14v0,
           tmnxPortGroupV7v0,
           tmnxPortGroupV8v0,
           tmnxPortIngrMdaQosStatR2r1Group,
           tmnxPortLoadBalGroupV10v0,
           tmnxPortNetEgrV10v0Group,
           tmnxPortNotificationGroupV8v0,
           tmnxPortNotificationGroupV8v9,
           tmnxPortNotificationGroupV9v4,
           tmnxPortNotificationV11v0Group,
           tmnxPortNotificationV9v0Group,
           tmnxPortNotifyObjsGroupV8v9,
           tmnxPortObjAppV9v0Group,
           tmnxPortParentLocV12v0Group,
           tmnxPortPlcyGroup,
           tmnxPortQStatV7v0Group,
           tmnxPortQosStatsGroup,
           tmnxPortQueueOvrV13v0Group,
           tmnxPortSchedPlcyOvrV13v0Group,
           tmnxPortSchedPlcyV12v0Group,
           tmnxPortSchedStatsGroup,
           tmnxPortSchedV13v0Group,
           tmnxPortSonetV3v0Group,
           tmnxPortStatsR2r1Group,
           tmnxPortTDME1GroupV6v1,
           tmnxPortTDMGroupV7v0,
-- EXCLUDE tmnxPortTestGroup
           tmnxPortTopologyV13v0Group,
           tmnxPortV13v0Group,
           tmnxPortV9v0Group,
           tmnxPortVPortV11v0Group,
           tmnxPortVPortV12v0Group,
           tmnxPrtEthSmMnNotifyObjsGrpV12v0,
           tmnxPwPortV10v0Group,
           tmnxQosAppObjsGroup,
           tmnxScalarPortV11v0Group,
           tmnxScalarPortV3v0Group,
           tmnxSonetPortV12v0Group,
           tmnxWaveTrackerGroup,
           tmnxWaveTrackerV11v0Group
        }

        VARIATION   tmnxBundleImaGrpFeClockMode
            ACCESS  read-only
            DESCRIPTION
                 "tmnxBundleImaGrpFeClockMode is implemented as read-only on
                  Nokia 7950 in release 14.0."

        VARIATION   tmnxBundleImaGrpNeClockMode
            ACCESS  read-only
            DESCRIPTION
                 "tmnxBundleImaGrpNeClockMode is implemented as read-only on
                  Nokia 7950 in release 14.0."

        VARIATION   tmnxBundleType
            SYNTAX  INTEGER {
                       mlppp                (1),
                    -- mlfr                 (2)
                       imagrp               (3)
                    }
            DESCRIPTION
                 "tmnxBundleType value of 'mlfr (2)' is not supported."

        VARIATION   tmnxDS0ChanGroupRowStatus
            SYNTAX  RowStatus {
                       active               (1),
                    -- notInService         (2)
                    -- notReady             (3)
                       createAndGo          (4),
                    -- createAndWait        (5)
                       destroy              (6)
                    }
            DESCRIPTION
                 "tmnxDS0ChanGroupRowStatus supports only 'active (1)',
                  'createAndGo (4)', and 'destroy (6)'."

        VARIATION   tmnxDS1RowStatus
            SYNTAX  RowStatus {
                       active               (1),
                    -- notInService         (2)
                    -- notReady             (3)
                       createAndGo          (4),
                    -- createAndWait        (5)
                       destroy              (6)
                    }
            DESCRIPTION
                 "tmnxDS1RowStatus supports only 'active (1)', 'createAndGo
                  (4)', and 'destroy (6)'."

        VARIATION   tmnxDS3ChannelClockSource
            SYNTAX  INTEGER {
                       loopTimed            (1),
                       nodeTimed            (2)
                    -- adaptive             (3)
                    -- differential         (4)
                    }
            DESCRIPTION
                 "tmnxDS3ChannelClockSource values of 'adaptive (3)' and
                  'differential (4)' are not supported."

        VARIATION   tmnxDS3ChannelReportAlarm
            SYNTAX  BITS {
                       notUsed              (0),
                       ais                  (1),
                       los                  (2),
                       oof                  (3),
                       rai                  (4),
                       looped               (5)
                    -- berSd                (6)
                    -- berSf                (7)
                    }
            DESCRIPTION
                 "tmnxDS3ChannelReportAlarm does not support berSd and berSf
                  values of TmnxDSXReportAlarm"

        VARIATION   tmnxDS3ChannelRowStatus
            SYNTAX  RowStatus {
                       active               (1),
                    -- notInService         (2)
                    -- notReady             (3)
                       createAndGo          (4),
                    -- createAndWait        (5)
                       destroy              (6)
                    }
            DESCRIPTION
                 "tmnxDS3ChannelRowStatus supports only 'active (1)',
                  'createAndGo (4)', and 'destroy (6)'."

        VARIATION   tmnxEqOobPortFailure
            ACCESS  not-implemented
            DESCRIPTION
                 "tmnxEqOobPortFailure notification is not implemented. This
                  notification was made obsolete in the 3.0 release.

                  The Out-of-band, OOB, port is what we refer to as the
                  management port or cpm port. It has an entry in ifTable and
                  linkup, linkDown and tmnxEqPortError notifications are sent
                  for the management port just as for any other port in the
                  system."

        VARIATION   tmnxEqPortFailure
            ACCESS  not-implemented
            DESCRIPTION
                 "tmnxEqPortFailure notification is not implemented.
                  tmnxEqPortError is used instead. This notification was made
                  obsolete in the 3.0 release.

                  Standard IETF linkDown notification is sent when a physical
                  port failure is detected. tmnxEqPortError is sent with a ASCII
                  reason message when port errors are detected.

                  It was originally intended that tmnxEqPortError be used to
                  report errors that do not cause port state change to 'down'.

                  tmnxEqPortFailure was intended to report errors that do cause
                  the port state change to 'down'.

                  However, in the implementation tmnxEqPortError is used for
                  both fatal and non-fatal errors."

        VARIATION   tmnxEqPortWrongSFP
            ACCESS  not-implemented
            DESCRIPTION
                 "tmnxEqPortWrongSFP notification is not implemented. In earlier
                  releases it was generated when a wrong type of SFP optics
                  module was plugged into a 1 Gig MDA, SONET MDA, or 100FX MDA.

                  Because of the large variety of SFPs now supported and their
                  different encoding schemes for compliance bits, the check for
                  wrong SFP has been removed.

                  A wrong SFP can be inferred from the port statistics."

        VARIATION   tmnxPortAlias
            DESCRIPTION
                 "tmnxPortAlias is implemented as read-only for LAG ports."

        VARIATION   tmnxPortClearAlarms
            ACCESS  read-only
            DESCRIPTION
                 "tmnxPortClearAlarms is implemented as read-only on Nokia 7950
                  in release 14.0."

        VARIATION   tmnxPortDescription
            DESCRIPTION
                 "tmnxPortDescription is implemented as read-only for LAG
                  ports."

        VARIATION   tmnxPortEncapType
            SYNTAX  INTEGER {
                       unknown              (0),
                       nullEncap            (1),
                       qEncap               (2),
                       mplsEncap            (3),
                       bcpNullEncap         (4),
                       bcpDot1qEncap        (5),
                       ipcpEncap            (6),
                       frEncap              (7),
                       pppAutoEncap         (8),
                       atmEncap             (9),
                       qinqEncap            (10),
                       wanMirrorEncap       (11),
                       ciscoHDLCEncap       (12),
                       cemEncap             (13)
                    }
            DESCRIPTION
                 "tmnxPortEncapType is implemented as read-only for Multi-Link
                  PPP (MLPPP) bundles and IMA bundles."

        VARIATION   tmnxPortEntry
            DESCRIPTION
                 "Vports are created by routed TLS and cannot be modified.
                  Management ports cannot be modified."

        VARIATION   tmnxPortEtherAcctPolicyId
            DESCRIPTION
                 "tmnxPortEtherAcctPolicyId is implemented as read-only for LAG
                  ports that are not the primary LAG port."

        VARIATION   tmnxPortEtherAutoNegotiate
            DESCRIPTION
                 "tmnxPortEtherAutoNegotiate is implemented as read-only for LAG
                  ports that are not the primary LAG port."

        VARIATION   tmnxPortEtherCollectStats
            DESCRIPTION
                 "tmnxPortEtherCollectStats is implemented as read-only for LAG
                  ports that are not the primary LAG port."

        VARIATION   tmnxPortEtherDuplex
            DESCRIPTION
                 "tmnxPortEtherDuplex is implemented as read-only for LAG ports
                  that are not the primary LAG port."

        VARIATION   tmnxPortEtherEgressRate
            DESCRIPTION
                 "tmnxPortEtherEgressRate is implemented as read-only for LAG
                  ports that are not the primary LAG port."

        VARIATION   tmnxPortEtherMTU
            DESCRIPTION
                 "tmnxPortEtherMTU is implemented as read-only for LAG ports."

        VARIATION   tmnxPortEtherSpeed
            DESCRIPTION
                 "tmnxPortEtherSpeed is implemented as read-only for LAG ports
                  that are not the primary LAG port."

        VARIATION   tmnxPortEtherXGigMode
            DESCRIPTION
                 "tmnxPortEtherXGigMode is implemented as read-only for LAG
                  ports that are not the primary LAG port."

        VARIATION   tmnxPortHoldTimeDown
            DESCRIPTION
                 "tmnxPortHoldTimeDown is implemented as read-only for LAG
                  ports, Multi-Link PPP (MLPPP) bundles, and IMA bundles."

        VARIATION   tmnxPortHoldTimeUp
            DESCRIPTION
                 "tmnxPortHoldTimeUp is implemented as read-only for LAG ports,
                  Multi-Link PPP (MLPPP) bundles, and IMA bundles."

        VARIATION   tmnxPortLastAlarmEvent
            DESCRIPTION
                 "tmnxPortLastAlarmEvent is not supported on Nokia 7950. The
                  value of tmnxPortLastAlarmEvent is always '0.0'."

        VARIATION   tmnxPortMode
            DESCRIPTION
                 "tmnxPortMode is implemented as read-only for LAG ports,
                  Multi-Link PPP (MLPPP) bundles, and IMA bundles.

                  Setting/changing tmnxPortMode on channelized interfaces is
                  H/W dependent."

        VARIATION   tmnxPortNetworkEgrQueues
            DESCRIPTION
                 "tmnxPortNetworkEgrQueues is implemented as read-only for LAG
                  ports, Multi-Link PPP (MLPPP) bundles, and IMA bundles.

                  tmnxPortNetworkEgrQueues can only be modified for channels
                  and ethernet ports."

        VARIATION   tmnxPortNotifyBerSdTca
            ACCESS  not-implemented
            DESCRIPTION
                 "tmnxPortNotifyBerSdTca notification is not implemented. This
                  notification was made obsolete in the 3.0 release."

        VARIATION   tmnxPortNotifyBerSfTca
            ACCESS  not-implemented
            DESCRIPTION
                 "tmnxPortNotifyBerSfTca notification is not implemented. This
                  notification was made obsolete in the 3.0 release."

        VARIATION   tmnxPortTopologyEntry
            CREATION-REQUIRES {
                       tmnxPortTopologyRowStatus,
                       tmnxPortFarEndId
                    }
            DESCRIPTION
                 "Objects tmnxPortTopologyRowStatus and tmnxPortFarEndId must be
                  set for row creation to succeed."

        VARIATION   tmnxPortTopologyRowStatus
            SYNTAX  RowStatus {
                       active               (1),
                    -- notInService         (2)
                    -- notReady             (3)
                       createAndGo          (4),
                    -- createAndWait        (5)
                       destroy              (6)
                    }
            DESCRIPTION
                 "tmnxPortTopologyRowStatus supports only 'active (1)',
                  'createAndGo (4)', and 'destroy (6)'."

        VARIATION   tmnxPortTransceiverCode
            ACCESS  not-implemented
            DESCRIPTION
                 "tmnxPortTransceiverCode object is not implemented. This object
                  was made obsolete in the 5.0 release."

        VARIATION   tmnxQosServiceDegraded
            ACCESS  not-implemented
            DESCRIPTION
                 "tmnxQosServiceDegraded notification is not implemented. This
                  notification was made obsolete in the 3.0 release."

        VARIATION   tmnxSonetPathRowStatus
            SYNTAX  RowStatus {
                       active               (1),
                    -- notInService         (2)
                    -- notReady             (3)
                       createAndGo          (4),
                    -- createAndWait        (5)
                       destroy              (6)
                    }
            DESCRIPTION
                 "tmnxSonetPathRowStatus supports only 'active (1)',
                  'createAndGo (4)', and 'destroy (6)'."

    ::= { tmnx7950AgentV14v0  31 }

--
-- SROS PPP CAPABILITIES
--
tmnxSROSPppV14v0                  AGENT-CAPABILITIES
    PRODUCT-RELEASE "Nokia SROS"
    STATUS          current
    DESCRIPTION
         "Implementation of PPP protocol capabilities for Nokia SROS systems
          release 14.0."

    SUPPORTS        TIMETRA-PPP-MIB
        INCLUDES {
           tmnxPpp7450V4v0Group,
           tmnxPpp7750V4v0Group,
           tmnxPppCompressionGroup,
           tmnxPppNotificationGroup
        }

    ::= { tmnxSROSAgentV14v0  32 }

--
-- SROS PPPoE CAPABILITIES
--
tmnxSROSPppoeV14v0                AGENT-CAPABILITIES
    PRODUCT-RELEASE "Nokia SROS"
    STATUS          current
    DESCRIPTION
         "Implementation of PPPoE capabilities for Nokia SROS systems release
          14.0."

    SUPPORTS        TIMETRA-PPPOE-MIB
        INCLUDES {
           tmnxPPPLcpIgnoreMagic,
           tmnxPPPMlpppGroup,
           tmnxPPPPlcyAllowSameCidGroup,
           tmnxPPPRejectDisabledNcp,
           tmnxPPPV9v0Group,
           tmnxPPPoEDefaultUsernameGroup,
           tmnxPPPoEV10v0NotifyGroup,
           tmnxPPPoEV12v0Group,
           tmnxPPPoEV14v0Group,
           tmnxPPPoEV6v0BsxGroup,
           tmnxPPPoEV8v0Group,
           tmnxPPPoEV9v0Group
        }

        VARIATION   tmnxPppoePlcyOptionType
            SYNTAX  INTEGER {
                       ipv4(1),
                       ascii(2),
                       hex(3)
                    -- ipv6(4)
                    -- domain(5)
                    }
            DESCRIPTION
                 "The value 'ipv6(4)' and 'domain(5)' is not supported."

    ::= { tmnxSROSAgentV14v0  58 }

--
-- 7710 PPPoE CAPABILITIES
--
tmnx7710PppoeV14v0                AGENT-CAPABILITIES
    PRODUCT-RELEASE "Nokia SROS"
    STATUS          current
    DESCRIPTION
         "Implementation of PPPoE capabilities for Nokia 7710 systems release
          14.0."

    SUPPORTS        TIMETRA-PPPOE-MIB
        INCLUDES {
           tmnxPPPLcpIgnoreMagic,
           tmnxPPPMlpppGroup,
           tmnxPPPPlcyAllowSameCidGroup,
           tmnxPPPRejectDisabledNcp,
           tmnxPPPV9v0Group,
           tmnxPPPoEDefaultUsernameGroup,
           tmnxPPPoEV10v0NotifyGroup,
           tmnxPPPoEV12v0Group,
           tmnxPPPoEV14v0Group,
-- EXCLUDE tmnxPPPoEV6v0BsxGroup
           tmnxPPPoEV8v0Group,
           tmnxPPPoEV9v0Group
        }

        VARIATION   tmnxPppoePlcyOptionType
            SYNTAX  INTEGER {
                       ipv4(1),
                       ascii(2),
                       hex(3)
                    -- ipv6(4)
                    -- domain(5)
                    }
            DESCRIPTION
                 "The value 'ipv6(4)' and 'domain(5)' is not supported."

        VARIATION   tmnxPppoeSessionL2tpConnectionId
            ACCESS  not-implemented
            DESCRIPTION
                 "tmnxPppoeSessionL2tpConnectionId is not implemented on Nokia
                  7710 in release 14.0."

        VARIATION   tmnxPppoeSessionL2tpVrtrId
            ACCESS  not-implemented
            DESCRIPTION
                 "tmnxPppoeSessionL2tpVrtrId is not implemented on Nokia 7710 in
                  release 14.0."

    ::= { tmnx7710AgentV14v0  58 }

--
-- 7950 PPPoE CAPABILITIES
--
tmnx7950PppoeV14v0                AGENT-CAPABILITIES
    PRODUCT-RELEASE "Nokia SROS"
    STATUS          current
    DESCRIPTION
         "Implementation of PPPoE capabilities for Nokia 7950 systems release
          14.0."

--    SUPPORTS        TIMETRA-PPPOE-MIB
--        INCLUDES {
--        }

    ::= { tmnx7950AgentV14v0  58 }

--
-- 7750 PTP CAPABILITIES
--
tmnx7750PtpV14v0                  AGENT-CAPABILITIES
    PRODUCT-RELEASE "Nokia SROS"
    STATUS          current
    DESCRIPTION
         "Implementation of Precision Timing Protocol (PTP1588) on Nokia 7750
          systems release 14.0. PTP1588 is only accessible on a system with an
          active CPM/SFM that supports PTP."

    SUPPORTS        TIMETRA-PTP-MIB
        INCLUDES {
           tmnxPtpClockRecoveryGroup,
           tmnxPtpConfigV13v0Group,
           tmnxPtpLocalConfigGroup,
           tmnxPtpLocalConfigV12v0Group,
           tmnxPtpLocalOperGroup,
           tmnxPtpMasterClockGroup,
           tmnxPtpMasterClockV12v0Group,
           tmnxPtpNotificationsGroup,
           tmnxPtpNotificationsV12v0Group,
           tmnxPtpNotifyObjsV12v0Group,
           tmnxPtpPacketRateStatsGroup,
           tmnxPtpPacketStatsGroup,
           tmnxPtpPacketStatsV10v0Group,
           tmnxPtpPeerBaseConfigGroup,
           tmnxPtpPeerBaseConfigV12v0Group,
           tmnxPtpPeerMasterStatusGroup,
           tmnxPtpPeerOperGroup,
           tmnxPtpPeerUnicastStatusGroup,
           tmnxPtpPortGroup,
           tmnxPtpPortStatsGroup,
           tmnxPtpTimeInfoGroup,
           tmnxPtpTimeStampGroup,
           tmnxPtpVRtrGroup,
           tmnxPtpVRtrIfConfigGroup,
           tmnxPtpVRtrIfTimeStampGroup
        }

        VARIATION   tmnxPtpPeerRowStatus
            SYNTAX  RowStatus {
                       active               (1),
                    -- notInService         (2)
                    -- notReady             (3)
                       createAndGo          (4),
                    -- createAndWait        (5)
                       destroy              (6)
                    }
            DESCRIPTION
                 "tmnxPtpPeerRowStatus supports only 'active (1)', 'createAndGo
                  (4)', and 'destroy (6)'."

        VARIATION   tmnxPtpPortRowStatus
            SYNTAX  RowStatus {
                       active               (1),
                    -- notInService         (2)
                    -- notReady             (3)
                       createAndGo          (4),
                    -- createAndWait        (5)
                       destroy              (6)
                    }
            DESCRIPTION
                 "tmnxPtpPortRowStatus supports only 'active (1)', 'createAndGo
                  (4)', and 'destroy (6)'."

        VARIATION   tmnxPtpVRtrRowStatus
            SYNTAX  RowStatus {
                       active               (1),
                    -- notInService         (2)
                    -- notReady             (3)
                       createAndGo          (4),
                    -- createAndWait        (5)
                       destroy              (6)
                    }
            DESCRIPTION
                 "tmnxPtpVRtrRowStatus supports only 'active (1)', 'createAndGo
                  (4)', and 'destroy (6)'."

    ::= { tmnx7750AgentV14v0  83 }

--
-- 7450 PTP CAPABILITIES
--
tmnx7450PtpV14v0                  AGENT-CAPABILITIES
    PRODUCT-RELEASE "Nokia SROS"
    STATUS          current
    DESCRIPTION
         "Implementation of Precision Timing Protocol (PTP1588) on Nokia 7450
          systems release 14.0. PTP1588 is only accessible on a system with an
          active CPM/SFM that supports PTP."

    SUPPORTS        TIMETRA-PTP-MIB
        INCLUDES {
           tmnxPtpClockRecoveryGroup,
           tmnxPtpConfigV13v0Group,
           tmnxPtpLocalConfigGroup,
           tmnxPtpLocalConfigV12v0Group,
           tmnxPtpLocalOperGroup,
           tmnxPtpMasterClockGroup,
           tmnxPtpMasterClockV12v0Group,
           tmnxPtpNotificationsGroup,
           tmnxPtpNotificationsV12v0Group,
           tmnxPtpNotifyObjsV12v0Group,
           tmnxPtpPacketRateStatsGroup,
           tmnxPtpPacketStatsGroup,
           tmnxPtpPacketStatsV10v0Group,
           tmnxPtpPeerBaseConfigGroup,
           tmnxPtpPeerBaseConfigV12v0Group,
           tmnxPtpPeerMasterStatusGroup,
           tmnxPtpPeerOperGroup,
           tmnxPtpPeerUnicastStatusGroup,
           tmnxPtpPortGroup,
           tmnxPtpPortStatsGroup,
           tmnxPtpTimeInfoGroup,
           tmnxPtpTimeStampGroup,
           tmnxPtpVRtrGroup,
           tmnxPtpVRtrIfConfigGroup,
           tmnxPtpVRtrIfTimeStampGroup
        }

        VARIATION   tmnxPtpPeerRowStatus
            SYNTAX  RowStatus {
                       active               (1),
                    -- notInService         (2)
                    -- notReady             (3)
                       createAndGo          (4),
                    -- createAndWait        (5)
                       destroy              (6)
                    }
            DESCRIPTION
                 "tmnxPtpPeerRowStatus supports only 'active (1)', 'createAndGo
                  (4)', and 'destroy (6)'."

        VARIATION   tmnxPtpPortRowStatus
            SYNTAX  RowStatus {
                       active               (1),
                    -- notInService         (2)
                    -- notReady             (3)
                       createAndGo          (4),
                    -- createAndWait        (5)
                       destroy              (6)
                    }
            DESCRIPTION
                 "tmnxPtpPortRowStatus supports only 'active (1)', 'createAndGo
                  (4)', and 'destroy (6)'."

        VARIATION   tmnxPtpVRtrRowStatus
            SYNTAX  RowStatus {
                       active               (1),
                    -- notInService         (2)
                    -- notReady             (3)
                       createAndGo          (4),
                    -- createAndWait        (5)
                       destroy              (6)
                    }
            DESCRIPTION
                 "tmnxPtpVRtrRowStatus supports only 'active (1)', 'createAndGo
                  (4)', and 'destroy (6)'."

    ::= { tmnx7450AgentV14v0  83 }

--
-- 7950 PTP CAPABILITIES
--
tmnx7950PtpV14v0                  AGENT-CAPABILITIES
    PRODUCT-RELEASE "Nokia SROS"
    STATUS          current
    DESCRIPTION
         "Implementation of Precision Timing Protocol (PTP1588) on Nokia 7950
          systems release 14.0. PTP1588 is only accessible on a system with an
          active CPM/SFM that supports PTP."

    SUPPORTS        TIMETRA-PTP-MIB
        INCLUDES {
           tmnxPtpClockRecoveryGroup,
           tmnxPtpConfigV13v0Group,
           tmnxPtpLocalConfigGroup,
           tmnxPtpLocalConfigV12v0Group,
           tmnxPtpLocalOperGroup,
           tmnxPtpMasterClockGroup,
           tmnxPtpMasterClockV12v0Group,
           tmnxPtpNotificationsGroup,
           tmnxPtpNotificationsV12v0Group,
           tmnxPtpNotifyObjsV12v0Group,
           tmnxPtpPacketRateStatsGroup,
           tmnxPtpPacketStatsGroup,
           tmnxPtpPacketStatsV10v0Group,
           tmnxPtpPeerBaseConfigGroup,
           tmnxPtpPeerBaseConfigV12v0Group,
           tmnxPtpPeerMasterStatusGroup,
           tmnxPtpPeerOperGroup,
           tmnxPtpPeerUnicastStatusGroup,
           tmnxPtpPortGroup,
           tmnxPtpPortStatsGroup,
           tmnxPtpTimeInfoGroup,
           tmnxPtpTimeStampGroup,
           tmnxPtpVRtrGroup,
           tmnxPtpVRtrIfConfigGroup,
           tmnxPtpVRtrIfTimeStampGroup
        }

        VARIATION   tmnxPtpPeerRowStatus
            SYNTAX  RowStatus {
                       active               (1),
                    -- notInService         (2)
                    -- notReady             (3)
                       createAndGo          (4),
                    -- createAndWait        (5)
                       destroy              (6)
                    }
            DESCRIPTION
                 "tmnxPtpPeerRowStatus supports only 'active (1)', 'createAndGo
                  (4)', and 'destroy (6)'."

        VARIATION   tmnxPtpPortRowStatus
            SYNTAX  RowStatus {
                       active               (1),
                    -- notInService         (2)
                    -- notReady             (3)
                       createAndGo          (4),
                    -- createAndWait        (5)
                       destroy              (6)
                    }
            DESCRIPTION
                 "tmnxPtpPortRowStatus supports only 'active (1)', 'createAndGo
                  (4)', and 'destroy (6)'."

        VARIATION   tmnxPtpVRtrRowStatus
            SYNTAX  RowStatus {
                       active               (1),
                    -- notInService         (2)
                    -- notReady             (3)
                       createAndGo          (4),
                    -- createAndWait        (5)
                       destroy              (6)
                    }
            DESCRIPTION
                 "tmnxPtpVRtrRowStatus supports only 'active (1)', 'createAndGo
                  (4)', and 'destroy (6)'."

    ::= { tmnx7950AgentV14v0  83 }

--
-- 7750SR-7 PXC CAPABILITIES
--
tmnx7750SR7PxcV14v0               AGENT-CAPABILITIES
    PRODUCT-RELEASE "Nokia SROS"
    STATUS          current
    DESCRIPTION
         "Implementation of Port Cross-Connect (PXC) capabilities for Nokia 7750
          SR-7 systems release 14.0."

    SUPPORTS        TIMETRA-PXC-MIB
        INCLUDES {
           tmnxFpePwPortV14v0Group,
           tmnxFpeV14v0Group,
           tmnxFpeVxlanV14v0Group,
           tmnxPxcV14v0Group
        }

        VARIATION   tmnxFpeRowStatus
            SYNTAX  RowStatus {
                       active               (1),
                    -- notInService         (2)
                    -- notReady             (3)
                       createAndGo          (4),
                    -- createAndWait        (5)
                       destroy              (6)
                    }
            DESCRIPTION
                 "tmnxFpeRowStatus supports only 'active (1)', 'createAndGo
                  (4)', and 'destroy (6)'."

        VARIATION   tmnxPxcRowStatus
            SYNTAX  RowStatus {
                       active               (1),
                    -- notInService         (2)
                    -- notReady             (3)
                       createAndGo          (4),
                    -- createAndWait        (5)
                       destroy              (6)
                    }
            DESCRIPTION
                 "tmnxPxcRowStatus supports only 'active (1)', 'createAndGo
                  (4)', and 'destroy (6)'."

    ::= { tmnx7750SR7AgentV14v0  95 }

--
-- 7750SR-12 PXC CAPABILITIES
--
tmnx7750SR12PxcV14v0              AGENT-CAPABILITIES
    PRODUCT-RELEASE "Nokia SROS"
    STATUS          current
    DESCRIPTION
         "Implementation of Port Cross-Connect (PXC) capabilities for Nokia 7750
          SR-12 systems release 14.0."

    SUPPORTS        TIMETRA-PXC-MIB
        INCLUDES {
           tmnxFpePwPortV14v0Group,
           tmnxFpeV14v0Group,
           tmnxFpeVxlanV14v0Group,
           tmnxPxcV14v0Group
        }

        VARIATION   tmnxFpeRowStatus
            SYNTAX  RowStatus {
                       active               (1),
                    -- notInService         (2)
                    -- notReady             (3)
                       createAndGo          (4),
                    -- createAndWait        (5)
                       destroy              (6)
                    }
            DESCRIPTION
                 "tmnxFpeRowStatus supports only 'active (1)', 'createAndGo
                  (4)', and 'destroy (6)'."

        VARIATION   tmnxPxcRowStatus
            SYNTAX  RowStatus {
                       active               (1),
                    -- notInService         (2)
                    -- notReady             (3)
                       createAndGo          (4),
                    -- createAndWait        (5)
                       destroy              (6)
                    }
            DESCRIPTION
                 "tmnxPxcRowStatus supports only 'active (1)', 'createAndGo
                  (4)', and 'destroy (6)'."

    ::= { tmnx7750SR12AgentV14v0  95 }

--
-- 7750SR-12e PXC CAPABILITIES
--
tmnx7750SR12ePxcV14v0             AGENT-CAPABILITIES
    PRODUCT-RELEASE "Nokia SROS"
    STATUS          current
    DESCRIPTION
         "Implementation of Port Cross-Connect (PXC) capabilities for Nokia 7750
          SR-12e systems release 14.0."

    SUPPORTS        TIMETRA-PXC-MIB
        INCLUDES {
           tmnxFpePwPortV14v0Group,
           tmnxFpeV14v0Group,
           tmnxFpeVxlanV14v0Group,
           tmnxPxcV14v0Group
        }

        VARIATION   tmnxFpeRowStatus
            SYNTAX  RowStatus {
                       active               (1),
                    -- notInService         (2)
                    -- notReady             (3)
                       createAndGo          (4),
                    -- createAndWait        (5)
                       destroy              (6)
                    }
            DESCRIPTION
                 "tmnxFpeRowStatus supports only 'active (1)', 'createAndGo
                  (4)', and 'destroy (6)'."

        VARIATION   tmnxPxcRowStatus
            SYNTAX  RowStatus {
                       active               (1),
                    -- notInService         (2)
                    -- notReady             (3)
                       createAndGo          (4),
                    -- createAndWait        (5)
                       destroy              (6)
                    }
            DESCRIPTION
                 "tmnxPxcRowStatus supports only 'active (1)', 'createAndGo
                  (4)', and 'destroy (6)'."

    ::= { tmnx7750SR12eAgentV14v0  95 }

--
-- 7950 PXC CAPABILITIES
--
tmnx7950PxcV14v0                  AGENT-CAPABILITIES
    PRODUCT-RELEASE "Nokia SROS"
    STATUS          current
    DESCRIPTION
         "Implementation of Port Cross-Connect (PXC) capabilities for Nokia 7950
          systems release 14.0."

    SUPPORTS        TIMETRA-PXC-MIB
        INCLUDES {
           tmnxFpePwPortV14v0Group,
           tmnxFpeV14v0Group,
           tmnxFpeVxlanV14v0Group,
           tmnxPxcV14v0Group
        }

        VARIATION   tmnxFpeRowStatus
            SYNTAX  RowStatus {
                       active               (1),
                    -- notInService         (2)
                    -- notReady             (3)
                       createAndGo          (4),
                    -- createAndWait        (5)
                       destroy              (6)
                    }
            DESCRIPTION
                 "tmnxFpeRowStatus supports only 'active (1)', 'createAndGo
                  (4)', and 'destroy (6)'."

        VARIATION   tmnxPxcRowStatus
            SYNTAX  RowStatus {
                       active               (1),
                    -- notInService         (2)
                    -- notReady             (3)
                       createAndGo          (4),
                    -- createAndWait        (5)
                       destroy              (6)
                    }
            DESCRIPTION
                 "tmnxPxcRowStatus supports only 'active (1)', 'createAndGo
                  (4)', and 'destroy (6)'."

    ::= { tmnx7950AgentV14v0  95 }

--
-- SROS PYTHON CAPABILITIES
--
tmnxSROSPythonV14v0               AGENT-CAPABILITIES
    PRODUCT-RELEASE "Nokia SROS"
    STATUS          current
    DESCRIPTION
         "Implementation of PYTHON capabilities for Nokia SROS systems release
          14.0."

    SUPPORTS        TIMETRA-PYTHON-MIB
        INCLUDES {
           tmnxPythonGroup,
           tmnxPythonIsaGroup
        }

        VARIATION   tmnxPyPlcyCacheAdminState
            SYNTAX  INTEGER {
                    -- noop                 (1)
                       inService            (2),
                       outOfService         (3)
                    }
            DESCRIPTION
                 "tmnxPyPlcyCacheAdminState supports only the values 'inService
                  (2)' and 'outOfService (3)'."

        VARIATION   tmnxPyPlcyCacheRowStatus
            SYNTAX  RowStatus {
                       active               (1),
                    -- notInService         (2)
                    -- notReady             (3)
                       createAndGo          (4),
                    -- createAndWait        (5)
                       destroy              (6)
                    }
            DESCRIPTION
                 "tmnxPyPlcyCacheRowStatus supports only 'active (1)',
                  'createAndGo (4)', and 'destroy (6)'."

        VARIATION   tmnxPyPlcyMessageRowStatus
            SYNTAX  RowStatus {
                       active               (1),
                    -- notInService         (2)
                    -- notReady             (3)
                       createAndGo          (4),
                    -- createAndWait        (5)
                       destroy              (6)
                    }
            DESCRIPTION
                 "tmnxPyPlcyMessageRowStatus supports only 'active (1)',
                  'createAndGo (4)', and 'destroy (6)'."

        VARIATION   tmnxPyPlcyRowStatus
            SYNTAX  RowStatus {
                       active               (1),
                    -- notInService         (2)
                    -- notReady             (3)
                       createAndGo          (4),
                    -- createAndWait        (5)
                       destroy              (6)
                    }
            DESCRIPTION
                 "tmnxPyPlcyRowStatus supports only 'active (1)', 'createAndGo
                  (4)', and 'destroy (6)'."

        VARIATION   tmnxPythonScriptAdminState
            SYNTAX  INTEGER {
                    -- noop                 (1)
                       inService            (2),
                       outOfService         (3)
                    }
            DESCRIPTION
                 "tmnxPythonScriptAdminState supports only the values 'inService
                  (2)' and 'outOfService (3)'."

        VARIATION   tmnxPythonScriptRowStatus
            SYNTAX  RowStatus {
                       active               (1),
                    -- notInService         (2)
                    -- notReady             (3)
                       createAndGo          (4),
                    -- createAndWait        (5)
                       destroy              (6)
                    }
            DESCRIPTION
                 "tmnxPythonScriptRowStatus supports only 'active (1)',
                  'createAndGo (4)', and 'destroy (6)'."

    ::= { tmnxSROSAgentV14v0  87 }

--
-- SROS QOS CAPABILITIES
--
tmnxSROSQosV14v0                  AGENT-CAPABILITIES
    PRODUCT-RELEASE "Nokia SROS"
    STATUS          current
    DESCRIPTION
         "Implementation of Quality of Service, Qos, capabilities for Nokia SROS
          systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
-- EXCLUDE tmnxQosAtmTdpV5v0Group
-- EXCLUDE tmnxQosAtmTdpV9v0Group
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
           tmnxQosHsmdaV9v0Group,
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
-- EXCLUDE tmnxQosNamedPoolPolicyV6v0Group
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
           tmnxQosParentLocEsmV12v0Group,
           tmnxQosParentLocV12v0Group,
           tmnxQosPlcyV12v0Group,
-- EXCLUDE tmnxQosPolicerV8v0Group
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapIngressMacCritType
            DESCRIPTION
                 "The value 'vid' is no supported on 7710"

    ::= { tmnxSROSAgentV14v0  33 }

--
-- 7750 QOS CAPABILITIES
--
tmnx7750QosV14v0                  AGENT-CAPABILITIES
    PRODUCT-RELEASE "Nokia SROS"
    STATUS          current
    DESCRIPTION
         "Implementation of Quality of Service, Qos, capabilities for Nokia 7750
          systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
           tmnxQosAtmTdpV5v0Group,
           tmnxQosAtmTdpV9v0Group,
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
           tmnxQosHsmdaV9v0Group,
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
           tmnxQosNamedPoolPolicyV6v0Group,
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
           tmnxQosParentLocEsmV12v0Group,
           tmnxQosParentLocV12v0Group,
           tmnxQosPlcyV12v0Group,
           tmnxQosPolicerV8v0Group,
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapIngressMacCritType
            DESCRIPTION
                 "The value 'vid' is no supported on 7710"

    ::= { tmnx7750AgentV14v0  33 }

--
-- 7750c12 QOS CAPABILITIES
--
tmnx7750c12QosV14v0               AGENT-CAPABILITIES
    PRODUCT-RELEASE "Nokia SROS"
    STATUS          current
    DESCRIPTION
         "Implementation of Quality of Service, Qos, capabilities for Nokia 7750
          c12 systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
           tmnxQosAtmTdpV5v0Group,
           tmnxQosAtmTdpV9v0Group,
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
-- EXCLUDE tmnxQosHsmdaV9v0Group
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
           tmnxQosNamedPoolPolicyV6v0Group,
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
           tmnxQosParentLocEsmV12v0Group,
           tmnxQosParentLocV12v0Group,
           tmnxQosPlcyV12v0Group,
           tmnxQosPolicerV8v0Group,
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosEgrQueuePoolName
            ACCESS  not-implemented
            DESCRIPTION
                 "tQosIngQueuePoolName is not implemented on Nokia 7750 c12 in
                  8.0 R1 release."

        VARIATION   tQosIngQueuePoolName
            ACCESS  not-implemented
            DESCRIPTION
                 "tQosIngQueuePoolName is not implemented on Nokia 7750 c12 in
                  8.0 R1 release."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapEgressQueuePoolName
            ACCESS  not-implemented
            DESCRIPTION
                 "tSapEgressQueuePoolName is not implemented on Nokia 7750 c12
                  in 6.0 R1 release."

        VARIATION   tSapIngressMacCritType
            DESCRIPTION
                 "The value 'vid' is no supported on 7710"

        VARIATION   tSapIngressQueuePoolName
            ACCESS  not-implemented
            DESCRIPTION
                 "tSapIngressQueuePoolName is not implemented on Nokia 7750 c12
                  in 6.0 R1 release."

    ::= { tmnx7750c12AgentV14v0  33 }

--
-- 7750c4 QOS CAPABILITIES
--
tmnx7750c4QosV14v0                AGENT-CAPABILITIES
    PRODUCT-RELEASE "Nokia SROS"
    STATUS          current
    DESCRIPTION
         "Implementation of Quality of Service, Qos, capabilities for Nokia 7750
          c4 systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
           tmnxQosAtmTdpV5v0Group,
           tmnxQosAtmTdpV9v0Group,
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
-- EXCLUDE tmnxQosHsmdaV9v0Group
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
           tmnxQosNamedPoolPolicyV6v0Group,
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
           tmnxQosParentLocEsmV12v0Group,
           tmnxQosParentLocV12v0Group,
           tmnxQosPlcyV12v0Group,
           tmnxQosPolicerV8v0Group,
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosEgrQueuePoolName
            ACCESS  not-implemented
            DESCRIPTION
                 "tQosIngQueuePoolName is not implemented on Nokia 7750 c4 in
                  8.0 R1 release."

        VARIATION   tQosIngQueuePoolName
            ACCESS  not-implemented
            DESCRIPTION
                 "tQosIngQueuePoolName is not implemented on Nokia 7750 c4 in
                  8.0 R1 release."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapEgressQueuePoolName
            ACCESS  not-implemented
            DESCRIPTION
                 "tSapEgressQueuePoolName is not implemented on Nokia 7750 c4 in
                  6.0 R1 release."

        VARIATION   tSapIngressMacCritType
            DESCRIPTION
                 "The value 'vid' is no supported on 7710"

        VARIATION   tSapIngressQueuePoolName
            ACCESS  not-implemented
            DESCRIPTION
                 "tSapIngressQueuePoolName is not implemented on Nokia 7750 c4
                  in 6.0 R1 release."

    ::= { tmnx7750c4AgentV14v0  33 }

--
-- 7450 QOS CAPABILITIES
--
tmnx7450QosV14v0                  AGENT-CAPABILITIES
    PRODUCT-RELEASE "Nokia SROS"
    STATUS          current
    DESCRIPTION
         "Implementation of Quality of Service, Qos, capabilities for Nokia 7450
          systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
           tmnxQosAtmTdpV5v0Group,
           tmnxQosAtmTdpV9v0Group,
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
           tmnxQosHsmdaV9v0Group,
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
           tmnxQosNamedPoolPolicyV6v0Group,
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
           tmnxQosParentLocEsmV12v0Group,
           tmnxQosParentLocV12v0Group,
           tmnxQosPlcyV12v0Group,
           tmnxQosPolicerV8v0Group,
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapIngressMacCritType
            DESCRIPTION
                 "The value 'vid' is no supported on 7710"

    ::= { tmnx7450AgentV14v0  33 }

--
-- 7710 QOS CAPABILITIES
--
tmnx7710QosV14v0                  AGENT-CAPABILITIES
    PRODUCT-RELEASE "Nokia SROS"
    STATUS          current
    DESCRIPTION
         "Implementation of Quality of Service, Qos, capabilities for Nokia 7710
          systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
           tmnxQosAtmTdpV5v0Group,
           tmnxQosAtmTdpV9v0Group,
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
-- EXCLUDE tmnxQosHsmdaV9v0Group
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
-- EXCLUDE tmnxQosNamedPoolPolicyV6v0Group
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
-- EXCLUDE tmnxQosParentLocEsmV12v0Group
-- EXCLUDE tmnxQosParentLocV12v0Group
           tmnxQosPlcyV12v0Group,
-- EXCLUDE tmnxQosPolicerV8v0Group
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosEgrQGroupFCLastChanged
            ACCESS  not-implemented
            DESCRIPTION
                 "tQosEgrQGroupFCLastChanged is not implemented on Nokia 7710 in
                  release 14.0."

        VARIATION   tQosEgrQGroupFCQueue
            ACCESS  not-implemented
            DESCRIPTION
                 "tQosEgrQGroupFCQueue is not implemented on Nokia 7710 in
                  release 14.0."

        VARIATION   tQosEgrQGroupFCRowStatus
            ACCESS  not-implemented
            DESCRIPTION
                 "tQosEgrQGroupFCRowStatus is not implemented on Nokia 7710 in
                  release 14.0."

        VARIATION   tQosEgrQueuePoolName
            ACCESS  not-implemented
            DESCRIPTION
                 "tQosIngQueuePoolName is not implemented on Nokia 7710 in 8.0
                  R1 release."

        VARIATION   tQosIngQueuePoolName
            ACCESS  not-implemented
            DESCRIPTION
                 "tQosIngQueuePoolName is not implemented on Nokia 7710 in 8.0
                  R1 release."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapEgressQueuePoolName
            ACCESS  not-implemented
            DESCRIPTION
                 "tSapEgressQueuePoolName is not implemented on Nokia 7710 in
                  6.0 R1 release."

        VARIATION   tSapEgressQueueXPWredQ
            ACCESS  not-implemented
            DESCRIPTION
                 "tSapEgressQueueXPWredQ is not implemented on Nokia 7710 in
                  release 14.0."

        VARIATION   tSapEgressQueueXPWredQSlope
            ACCESS  not-implemented
            DESCRIPTION
                 "tSapEgressQueueXPWredQSlope is not implemented on Nokia 7710
                  in release 14.0."

        VARIATION   tSapIngressMacCritType
            DESCRIPTION
                 "The value 'vid' is no supported on 7710"

        VARIATION   tSapIngressQueuePoolName
            ACCESS  not-implemented
            DESCRIPTION
                 "tSapIngressQueuePoolName is not implemented on Nokia 7710 in
                  6.0 R1 release."

    ::= { tmnx7710AgentV14v0  33 }

--
-- 7950 QOS CAPABILITIES
--
tmnx7950QosV14v0                  AGENT-CAPABILITIES
    PRODUCT-RELEASE "Nokia SROS"
    STATUS          current
    DESCRIPTION
         "Implementation of Quality of Service, Qos, capabilities for Nokia 7950
          systems release 14.0."

    SUPPORTS        TIMETRA-QOS-MIB
        INCLUDES {
           tQosFCQGrpFC8v0Group,
           tQosNetworkV14v0Group,
           tQosQGrpFCGroup,
           tQosQGrpV8v0Group,
           tQosSapIngEgrV14v0Group,
           tQosSharedQueueV14v0Group,
           tmnxQosAdvCfgPlcyV13v0Group,
           tmnxQosAdvConfigV10v0Group,
-- EXCLUDE tmnxQosAtmTdpV5v0Group
-- EXCLUDE tmnxQosAtmTdpV9v0Group
           tmnxQosBurstLimitGroup,
           tmnxQosDSCPGroup,
           tmnxQosEgrQGrpGroup,
           tmnxQosEgrReClassifyV10v0Group,
           tmnxQosEgressGroup,
           tmnxQosEgressQueuePlcrGroup,
           tmnxQosFCGroup,
           tmnxQosFlowBasedRulesV13v0Group,
           tmnxQosFrameBasedV6v0Group,
           tmnxQosGlobalGroup,
           tmnxQosHsmdaV10v0Group,
           tmnxQosHsmdaV11v0Group,
-- EXCLUDE tmnxQosHsmdaV9v0Group
           tmnxQosIngressPlcyV13v0Group,
           tmnxQosMacCritVidFltrV9v0Group,
           tmnxQosMatchListV13v0Group,
           tmnxQosMcFrEgrGroup,
           tmnxQosMcFrIngrGroup,
           tmnxQosMcMlpppEgrGroup,
           tmnxQosMcMlpppIngrGroup,
-- EXCLUDE tmnxQosNamedPoolPolicyV6v0Group
           tmnxQosNamedPoolV9v0Group,
           tmnxQosNetworkIngFCV13v0Group,
           tmnxQosNetworkPlcyV13v0Group,
           tmnxQosNetworkV10v0Group,
           tmnxQosNetworkV11v0Group,
           tmnxQosNetworkV9v0Group,
-- EXCLUDE tmnxQosParentLocEsmV12v0Group
           tmnxQosParentLocV12v0Group,
           tmnxQosPlcyV12v0Group,
-- EXCLUDE tmnxQosPolicerV8v0Group
           tmnxQosPolicerV9v0Group,
           tmnxQosPolicyV10v0Group,
           tmnxQosPortSchPlcyV13v0Group,
           tmnxQosPortSchedPlcyV13v0Group,
           tmnxQosQueueGrpPolcrV10v0Group,
           tmnxQosQueueObjV8v0Group,
           tmnxQosSapAtmV7v0Group,
           tmnxQosSapEgrFCDot1pDEV12v0Group,
           tmnxQosSapEgrIPCritV13v0Group,
           tmnxQosSapEgrIpCritGroup,
           tmnxQosSapEgrPlcrV12v0Group,
           tmnxQosSapEgressV8v0Group,
           tmnxQosSapEgressV9v0Group,
           tmnxQosSapIPCritExtV12v0Group,
           tmnxQosSapIngIPMacCritV12v0Group,
           tmnxQosSapIngressV10v0Group,
           tmnxQosSapIngressV13v0Group,
           tmnxQosSapIngressV9v0Group,
           tmnxQosSapIpv6FilterR4r0Group,
           tmnxQosSchedulerRateV11v0Group,
           tmnxQosSchedulerV13v0Group,
           tmnxQosSlopeGroup,
           tmnxSapEgressFCV11v0Group,
           tmnxSapIngressIPCritGroup,
           tmnxSlopePolicyV14v0Group
        }

        VARIATION   tNetworkIngIPCritDstIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritDstIpAddrType supports only the
                  InetAddressType values 'unknown (0)', 'ipv4 (1)', and 'ipv6
                  (2)'."

        VARIATION   tNetworkIngIPCritSrcIpAddrType
            SYNTAX  InetAddressType {
                       unknown              (0),
                       ipv4                 (1),
                       ipv6                 (2)
                    -- ipv4z                (3)
                    -- ipv6z                (4)
                    -- dns                  (16)
                    }
            DESCRIPTION
                 "tNetworkIngIPCritSrcIpAddrType supports only the
                  InetAddressType values 'unknown (0)', 'ipv4 (1)', and 'ipv6
                  (2)'."

        VARIATION   tNetworkIngIPCritType
            SYNTAX  InetAddressType {
                    -- unknown              (0)
                       ipv4                 (1),
                       ipv6                 (2)
                    -- ipv4z                (3)
                    -- ipv6z                (4)
                    -- dns                  (16)
                    }
            DESCRIPTION
                 "tNetworkIngIPCritType supports only the InetAddressType values
                  'ipv4 (1)', and 'ipv6 (2)'."

        VARIATION   tNetworkPolicyIngMatchCriteria
            SYNTAX  INTEGER {
                       ip(1),
                    -- mac(2)
                       none(3)
                    }
            DESCRIPTION
                 "tNetworkPolicyIngMatchCriteria does not support the value 'mac
                  (2)' as defined by the TMatchCriteria textual-convention."

        VARIATION   tQosPrefixListEntryPrefix
            SYNTAX  InetAddress (SIZE (4))
            DESCRIPTION
                 "tQosPrefixListEntryPrefix supports only InetAddressType values
                  'ipv4 (1)'."

        VARIATION   tQosPrefixListEntryPrefixType
            SYNTAX  InetAddressType {
                    -- unknown              (0)
                       ipv4                 (1)
                    -- ipv6                 (2)
                    -- ipv4z                (3)
                    -- ipv6z                (4)
                    -- dns                  (16)
                    }
            DESCRIPTION
                 "tQosPrefixListEntryPrefixType supports only the
                  InetAddressType value 'ipv4 (1)'."

        VARIATION   tQosPrefixListType
            SYNTAX  INTEGER {
                       ipv4(1)
                    -- ipv6(2)
                    }
            DESCRIPTION
                 "tQosPrefixListType does not support the value 'ipv6 (2)' as
                  defined by the tQosPrefixListType textual-convention."

        VARIATION   tSapEgrDynamicPolicerStatMode
            SYNTAX  INTEGER {
                       noStats              (0),
                       minimal              (1),
                       offeredProfileNoCIR  (2),
                       offeredTotalCIR      (3),
                       offeredProfileCIR    (4),
                       offeredLimitedCappedCIR(5),
                       offeredProfileCappedCIR(6)
                    -- offeredTotalCIRExceed (8)
                    }
            DESCRIPTION
                 "tSapEgrDynamicPolicerStatMode does not support value
                  'offeredTotalCIRExceed (8)' as defined by the
                  TmnxEgrPolicerStatMode textual convention."

        VARIATION   tSapEgrIPCritActionProfile
            SYNTAX  INTEGER {
                       none                 (0),
                       in                   (1),
                       out                  (2),
                    -- de                   (3)
                       exceed               (4),
                       inplus               (5)
                    }
            DESCRIPTION
                 "tSapEgrIPCritActionProfile does not support value 'de (3)' as
                  defined by the TEgressProfileOrNone textual convention."

        VARIATION   tSapEgrIPCritDestIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritDestIpAddrType supports only the InetAddressType
                  values 'unknown (0)' and 'ipv4 (1)'."

        VARIATION   tSapEgrIPCritSourceIpAddrType
            SYNTAX  InetAddressType {
                       unknown              (0),
                       ipv4                 (1)
                    -- ipv6                 (2)
                    -- ipv4z                (3)
                    -- ipv6z                (4)
                    -- dns                  (16)
                    }
            DESCRIPTION
                 "tSapEgrIPCritSourceIpAddrType supports only the
                  InetAddressType values 'unknown (0)' and 'ipv4 (1)'."

        VARIATION   tSapEgressDSCPprofile
            SYNTAX  INTEGER {
                       none                 (0),
                       in                   (1),
                       out                  (2),
                    -- de                   (3)
                       exceed               (4),
                       inplus               (5)
                    }
            DESCRIPTION
                 "tSapEgressDSCPprofile does not support value 'de (3)' as
                  defined by the TEgressProfileOrNone textual convention."

        VARIATION   tSapEgressMatchCriteria
            SYNTAX  INTEGER {
                       ip(1),
                    -- mac(2)
                       none(3)
                    }
            DESCRIPTION
                 "tSapEgressMatchCriteria does not support the value 'mac' as
                  defined by the TMatchCriteria textual convention."

        VARIATION   tSapEgressPrecProfile
            SYNTAX  INTEGER {
                       none                 (0),
                       in                   (1),
                       out                  (2),
                    -- de                   (3)
                       exceed               (4),
                       inplus               (5)
                    }
            DESCRIPTION
                 "tSapEgressPrecProfile does not support value 'de (3)' as
                  defined by the TEgressProfileOrNone textual convention."

        VARIATION   tSapIngressMacCritType
            DESCRIPTION
                 "The value 'vid' is no supported on 7710"

    ::= { tmnx7950AgentV14v0  33 }

--
-- SROS RAD_PROX CAPABILITIES
--
tmnxSROSRadProxV14v0              AGENT-CAPABILITIES
    PRODUCT-RELEASE "Nokia SROS"
    STATUS          current
    DESCRIPTION
         "Implementation of Radius on Nokia SROS systems release 14.0."

    SUPPORTS        TIMETRA-RADIUS-MIB
        INCLUDES {
           tmnxRadIsaAuthGroup,
           tmnxRadIsaAuthV14v0Group,
           tmnxRadProxSrvV11v0Group,
           tmnxRadProxSrvV12v0Group,
           tmnxRadProxSrvV14v0Group,
           tmnxRadRouteDownlGroup,
           tmnxRadScriptPlcyGroup,
           tmnxRadServGroup,
           tmnxRadServHealthCheckGroup,
           tmnxRadServIpv6Group,
           tmnxRadServV11v0Group,
           tmnxRadSrvPlcyAcctOnOffV11v0Grp,
           tmnxRadSrvPlcyV14v0Group,
           tmnxRadiusV11v0NotifyGroup
        }

        VARIATION   tmnxRadIsaPlcyRowStatus
            SYNTAX  RowStatus {
                       active               (1),
                    -- notInService         (2)
                    -- notReady             (3)
                       createAndGo          (4),
                    -- createAndWait        (5)
                       destroy              (6)
                    }
            DESCRIPTION
                 "tmnxRadIsaPlcyRowStatus supports only 'active (1)',
                  'createAndGo (4)', and 'destroy (6)'."

        VARIATION   tmnxRadIsaPlcySrvSrcAddrType
            SYNTAX  InetAddressType {
                       unknown              (0),
                       ipv4                 (1)
                    -- ipv6                 (2)
                    -- ipv4z                (3)
                    -- ipv6z                (4)
                    -- dns                  (16)
                    }
            DESCRIPTION
                 "tmnxRadIsaPlcySrvSrcAddrType supports only the InetAddressType
                  values 'unknown (0)' and 'ipv4 (1)'."

        VARIATION   tmnxRadIsaSrvAddrType
            SYNTAX  InetAddressType {
                    -- unknown              (0)
                       ipv4                 (1)
                    -- ipv6                 (2)
                    -- ipv4z                (3)
                    -- ipv6z                (4)
                    -- dns                  (16)
                    }
            DESCRIPTION
                 "tmnxRadIsaSrvAddrType supports only the InetAddressType value
                  'ipv4 (1)'."

        VARIATION   tmnxRadIsaSrvRowStatus
            SYNTAX  RowStatus {
                       active               (1),
                    -- notInService         (2)
                    -- notReady             (3)
                       createAndGo          (4),
                    -- createAndWait        (5)
                       destroy              (6)
                    }
            DESCRIPTION
                 "tmnxRadIsaSrvRowStatus supports only 'active (1)',
                  'createAndGo (4)', and 'destroy (6)'."

        VARIATION   tmnxRadProxSrvAdminState
            SYNTAX  INTEGER {
                    -- noop                 (1)
                       inService            (2),
                       outOfService         (3)
                    }
            DESCRIPTION
                 "tmnxRadProxSrvAdminState supports only the values 'inService
                  (2)' and 'outOfService (3)'."

        VARIATION   tmnxRadProxSrvIfRowStatus
            SYNTAX  RowStatus {
                       active               (1),
                    -- notInService         (2)
                    -- notReady             (3)
                       createAndGo          (4),
                    -- createAndWait        (5)
                       destroy              (6)
                    }
            DESCRIPTION
                 "tmnxRadProxSrvIfRowStatus supports only 'active (1)',
                  'createAndGo (4)', and 'destroy (6)'."

        VARIATION   tmnxRadProxSrvRowStatus
            SYNTAX  RowStatus {
                       active               (1),
                    -- notInService         (2)
                    -- notReady             (3)
                       createAndGo          (4),
                    -- createAndWait        (5)
                       destroy              (6)
                    }
            DESCRIPTION
                 "tmnxRadProxSrvRowStatus supports only 'active (1)',
                  'createAndGo (4)', and 'destroy (6)'."

        VARIATION   tmnxRadProxUsrToRspRowStatus
            SYNTAX  RowStatus {
                       active               (1),
                    -- notInService         (2)
                    -- notReady             (3)
                       createAndGo          (4),
                    -- createAndWait        (5)
                       destroy              (6)
                    }
            DESCRIPTION
                 "tmnxRadProxUsrToRspRowStatus supports only 'active (1)',
                  'createAndGo (4)', and 'destroy (6)'."

        VARIATION   tmnxRadRouteDownlAdminState
            SYNTAX  INTEGER {
                    -- noop                 (1)
                       inService            (2),
                       outOfService         (3)
                    }
            DESCRIPTION
                 "tmnxRadRouteDownlAdminState supports only the values
                  'inService (2)' and 'outOfService (3)'."

        VARIATION   tmnxRadRouteDownlRowStatus
            SYNTAX  RowStatus {
                       active               (1),
                    -- notInService         (2)
                    -- notReady             (3)
                       createAndGo          (4),
                    -- createAndWait        (5)
                       destroy              (6)
                    }
            DESCRIPTION
                 "tmnxRadRouteDownlRowStatus supports only 'active (1)',
                  'createAndGo (4)', and 'destroy (6)'."

        VARIATION   tmnxRadScriptPlcyRowStatus
            SYNTAX  RowStatus {
                       active               (1),
                    -- notInService         (2)
                    -- notReady             (3)
                       createAndGo          (4),
                    -- createAndWait        (5)
                       destroy              (6)
                    }
            DESCRIPTION
                 "tmnxRadScriptPlcyRowStatus supports only 'active (1)',
                  'createAndGo (4)', and 'destroy (6)'.

                  tmnxRadScriptPlcyRowStatus supports only 'active (1)',
                  'createAndGo (4)', and 'destroy (6)'."

        VARIATION   tmnxRadServRowStatus
            SYNTAX  RowStatus {
                       active               (1),
                    -- notInService         (2)
                    -- notReady             (3)
                       createAndGo          (4),
                    -- createAndWait        (5)
                       destroy              (6)
                    }
            DESCRIPTION
                 "tmnxRadServRowStatus supports only 'active (1)', 'createAndGo
                  (4)', and 'destroy (6)'."

        VARIATION   tmnxRadSrvPlcyRowStatus
            SYNTAX  RowStatus {
                       active               (1),
                    -- notInService         (2)
                    -- notReady             (3)
                       createAndGo          (4),
                    -- createAndWait        (5)
                       destroy              (6)
                    }
            DESCRIPTION
                 "tmnxRadSrvPlcyRowStatus supports only 'active (1)',
                  'createAndGo (4)', and 'destroy (6)'."

        VARIATION   tmnxRadSrvPlcySrvRowStatus
            SYNTAX  RowStatus {
                       active               (1),
                    -- notInService         (2)
                    -- notReady             (3)
                       createAndGo          (4),
                    -- createAndWait        (5)
                       destroy              (6)
                    }
            DESCRIPTION
                 "tmnxRadSrvPlcySrvRowStatus supports only 'active (1)',
                  'createAndGo (4)', and 'destroy (6)'."

    ::= { tmnxSROSAgentV14v0  81 }

--
-- 7950 RAD_PROX CAPABILITIES
--
tmnx7950RadProxV14v0              AGENT-CAPABILITIES
    PRODUCT-RELEASE "Nokia SROS"
    STATUS          current
    DESCRIPTION
         "Implementation of Radius on Nokia 7950 systems release 14.0."

--    SUPPORTS        TIMETRA-RADIUS-MIB
--        INCLUDES {
--        }

    ::= { tmnx7950AgentV14v0  81 }

--
-- SROS RIP2 CAPABILITIES
--
tmnxSROSRip2V14v0                 AGENT-CAPABILITIES
    PRODUCT-RELEASE "Nokia SROS"
    STATUS          current
    DESCRIPTION
         "Implementation of RIP-2 protocol capabilities for Nokia SROS systems
          release 14.0."

    SUPPORTS        RIPv2-MIB
        INCLUDES {
           rip2GlobalGroup,
           rip2IfConfGroup,
           rip2IfStatGroup,
           rip2PeerGroup
        }

        VARIATION   rip2IfConfAuthKey
            ACCESS  read-only
            DESCRIPTION
                 "rip2IfConfAuthKey is implemented as read-only on Nokia SROS in
                  release 14.0."

        VARIATION   rip2IfConfAuthType
            ACCESS  read-only
            DESCRIPTION
                 "rip2IfConfAuthType is implemented as read-only on Nokia SROS
                  in release 14.0."

        VARIATION   rip2IfConfDefaultMetric
            ACCESS  read-only
            DESCRIPTION
                 "rip2IfConfDefaultMetric is implemented as read-only on Nokia
                  SROS in release 14.0."

        VARIATION   rip2IfConfDomain
            ACCESS  read-only
            DESCRIPTION
                 "rip2IfConfDomain is implemented as read-only on Nokia SROS in
                  release 14.0."

        VARIATION   rip2IfConfReceive
            ACCESS  read-only
            DESCRIPTION
                 "rip2IfConfReceive is implemented as read-only on Nokia SROS in
                  release 14.0."

        VARIATION   rip2IfConfSend
            ACCESS  read-only
            DESCRIPTION
                 "rip2IfConfSend is implemented as read-only on Nokia SROS in
                  release 14.0."

        VARIATION   rip2IfConfSrcAddress
            ACCESS  read-only
            DESCRIPTION
                 "rip2IfConfSrcAddress is implemented as read-only on Nokia SROS
                  in release 14.0."

        VARIATION   rip2IfConfStatus
            ACCESS  read-only
            DESCRIPTION
                 "rip2IfConfStatus is implemented as read-only on Nokia SROS in
                  release 14.0."

        VARIATION   rip2IfStatStatus
            ACCESS  read-only
            DESCRIPTION
                 "rip2IfStatStatus is implemented as read-only on Nokia SROS in
                  release 14.0."

    SUPPORTS        TIMETRA-RIP-MIB
        INCLUDES {
           tmnxRipGlobalGroup,
           tmnxRipGroupGroup,
           tmnxRipInstanceGroup,
           tmnxRipInterfaceGroup,
           tmnxRipNotificationGroup,
           tmnxRipNotificationV7v0Group,
           tmnxRipPeerGroup,
           tmnxRipRoutesGroup,
           tmnxRipRoutesV9v0R4Group,
           tmnxRipV6v1Group,
           tmnxRipV7v0Group
        }

    SUPPORTS        TIMETRA-RIP-NG-MIB
        INCLUDES {
           tmnxRipNgGlobalV12v0Group,
           tmnxRipNgGroupV12v0Group,
           tmnxRipNgInstanceV12v0Group,
           tmnxRipNgInterfaceV12v0Group,
           tmnxRipNgNotificationV12v0Group,
           tmnxRipNgPeerV12v0Group,
           tmnxRipNgRoutesV12v0Group
        }

    ::= { tmnxSROSAgentV14v0  34 }

--
-- 7950 RIP2 CAPABILITIES
--
tmnx7950Rip2V14v0                 AGENT-CAPABILITIES
    PRODUCT-RELEASE "Nokia SROS"
    STATUS          current
    DESCRIPTION
         "Implementation of RIP-2 protocol capabilities for Nokia 7950 systems
          release 14.0."

--    SUPPORTS        RIPv2-MIB
--        INCLUDES {
--        }

--    SUPPORTS        TIMETRA-RIP-MIB
--        INCLUDES {
--        }

--    SUPPORTS        TIMETRA-RIP-NG-MIB
--        INCLUDES {
--        }

    ::= { tmnx7950AgentV14v0  34 }

--
-- SROS RMON CAPABILITIES
--
tmnxSROSRmonV14v0                 AGENT-CAPABILITIES
    PRODUCT-RELEASE "Nokia SROS"
    STATUS          current
    DESCRIPTION
         "Implementation of Remote Monitoring, RMON, capabilities for Nokia SROS
          systems release 14.0."

    SUPPORTS        HC-RMON-MIB
        INCLUDES {
           etherHistoryHighCapacityGroup,
           etherStatsHighCapacityGroup,
           hcRMONInformationGroup,
           mediaIndependentGroup
        }

        VARIATION   mediaIndependentDataSource
            ACCESS  read-only
            DESCRIPTION
                 "mediaIndependentTable is implemented as read-only. The agent
                  creates a row entry in the mediaIndependentTable for each
                  physical port in the system, indexed by the port-id."

        VARIATION   mediaIndependentIndex
            SYNTAX  InterfaceIndex
            DESCRIPTION
                 "The agent creates a row entry in the mediaIndependentTable for
                  each physical port in the system, indexed by the port-id which
                  is also the ifIndex and has a larger value range than that
                  specified for mediaIndependentIndex in the HC-RMON-MIB."

        VARIATION   mediaIndependentOwner
            ACCESS  read-only
            DESCRIPTION
                 "mediaIndependentTable is implemented as read-only."

        VARIATION   mediaIndependentStatus
            ACCESS  read-only
            DESCRIPTION
                 "mediaIndependentTable is implemented as read-only. Rows cannot
                  be created in the table by SNMP SET requests. The agent
                  creates a row entry in the mediaIndependentTable for each
                  physical port in the system, indexed by the port-id."

    SUPPORTS        RMON-MIB
        INCLUDES {
           rmonAlarmGroup,
           rmonEtherStatsGroup,
           rmonEthernetHistoryGroup,
           rmonEventGroup,
-- EXCLUDE rmonFilterGroup
           rmonHistoryControlGroup
-- EXCLUDE rmonHostGroup
-- EXCLUDE rmonHostTopNGroup
-- EXCLUDE rmonMatrixGroup
-- EXCLUDE rmonPacketCaptureGroup
        }

        VARIATION   alarmOwner
            SYNTAX  OwnerString (SIZE (0..80))
            DESCRIPTION
                 "The length of the alarmOwner string is limited to a maximum of
                  80 characters."

        VARIATION   etherStatsDataSource
            ACCESS  read-only
            DESCRIPTION
                 "etherStatsTable is implemented as read-only. The agent creates
                  a row entry in the etherStatsTable for each ethernet port in
                  the system, indexed by the port-id."

        VARIATION   etherStatsIndex
            SYNTAX  InterfaceIndex
            DESCRIPTION
                 "The agent creates a row entry in the etherStatsTable for each
                  ethernet port in the system that is indexed by the port-id or
                  ifIndex value and so has a larger value range than that
                  specified for etherStatsIndex in the RMON-MIB."

        VARIATION   etherStatsOversizePkts
            DESCRIPTION
                 "etherStatsOversizePkts indicates the total number of packets
                  received that were longer than the maximum frame size for the
                  particular media, usually 12287 octets (excluding framing
                  bits, but including FCS octets), and were otherwise well
                  formed.

                  TIMETRA-PORT-MIB::tmnxPortEtherPkts1519toMax,
                  TIMETRA-PORT-MIB::tmnxPortEtherHCOverPkts1519toMax and
                  TIMETRA-PORT-MIB::tmnxPortEtherHCPkts1519toMax are used to
                  indicate the total number of packets received that were longer
                  than 1518 octets but less than the maximum frame size for the
                  particular media, usually 12287 octets (excluding framing
                  bits, but including FCS octets)."

        VARIATION   etherStatsOwner
            ACCESS  read-only
            DESCRIPTION
                 "etherStatsTable is implemented as read-only."

        VARIATION   etherStatsStatus
            ACCESS  read-only
            DESCRIPTION
                 "etherStatsTable is implemented as read-only. Rows cannot be
                  created by SNMP SET requests. The agent creates a row entry in
                  the etherStatsTable for each ethernet port in the system,
                  indexed by the port-id."

        VARIATION   eventOwner
            SYNTAX  OwnerString (SIZE (0..80))
            DESCRIPTION
                 "The length of the eventOwner string is limited to a maximum of
                  80 characters."

    ::= { tmnxSROSAgentV14v0  35 }

--
-- SROS ROUTE_NEXT_HOP_TEMPL CAPABILITIES
--
tmnxSROSRouteNextHopTemplV14v0    AGENT-CAPABILITIES
    PRODUCT-RELEASE "Nokia SROS"
    STATUS          current
    DESCRIPTION
         "Implementation of route next-hop template capabilities for Nokia SROS
          systems release 14.0."

    SUPPORTS        TIMETRA-ROUTE-NEXT-HOP-TEMPLATE-MIB
        INCLUDES {
           tmnxRouteNextHopTemplateGroup
        }

        VARIATION   tmnxRouteNHTemplAdminGrpTblLstCh
            ACCESS  not-implemented
            DESCRIPTION
                 "tmnxRouteNHTemplAdminGrpTblLstCh is not implemented on Nokia
                  SROS in release 14.0."

        VARIATION   tmnxRouteNHTemplateTblLastCh
            ACCESS  not-implemented
            DESCRIPTION
                 "tmnxRouteNHTemplateTblLastCh is not implemented on Nokia SROS
                  in release 14.0."

    ::= { tmnxSROSAgentV14v0 100 }

--
-- SROS ROUTE_POLICY CAPABILITIES
--
tmnxSROSRoutePolicyV14v0          AGENT-CAPABILITIES
    PRODUCT-RELEASE "Nokia SROS"
    STATUS          current
    DESCRIPTION
         "Implementation of Route Policy capabilities for Nokia SROS systems
          release 14.0."

    SUPPORTS        TIMETRA-ROUTE-POLICY-MIB
        INCLUDES {
           tRPAdminPSAcceptOrigValidGroup,
           tmnxRPASPathGroupV14v0Group,
           tmnxRPASPathObjectsV5v0Group,
           tmnxRPAddPathsGroup,
           tmnxRPAdminControlObjV11v0Group,
           tmnxRPAdminControlObjectsGroup,
           tmnxRPAdvertiseLabelGroup,
           tmnxRPBackupPathGroup,
           tmnxRPBgpLeakingGroup,
           tmnxRPCommunityObjectsV5v0Group,
           tmnxRPCreationOriginGroup,
           tmnxRPCreationOriginV14v0Group,
           tmnxRPDampingObjectsV5v0Group,
           tmnxRPFlowSpecGroup,
           tmnxRPInetPrefixListObjectsV5v0Group,
           tmnxRPOperPSAcceptActionFCGroup,
           tmnxRPPSCondRouteGroup,
           tmnxRPPSCriteriaObjsV14v0Group,
           tmnxRPPolicyEntryObjV11v0Group,
           tmnxRPPolicyObjectsV10v0Group,
           tmnxRPPolicyObjectsV11v0Group,
           tmnxRPPolicyObjectsV12v0Group,
           tmnxRPPolicyObjectsV8v0Group,
-- EXCLUDE tmnxRPPolicyObjectsV9v0Group,
           tmnxRPPolicyVarExtGroup,
           tmnxRPPolicyVarObjectsGroup,
           tmnxRPPrefixListObjectsV5v0Group,
           tmnxRPPrefixListV13v0Group,
           tmnxRPQPPBV9v0R4Group,
           tmnxRPStickyEcmpGroup
        }

        VARIATION   tRPAdminASPathGroupRowStatus
            SYNTAX  RowStatus {
                       active               (1),
                    -- notInService         (2)
                    -- notReady             (3)
                       createAndGo          (4),
                    -- createAndWait        (5)
                       destroy              (6)
                    }
            DESCRIPTION
                 "tRPAdminASPathGroupRowStatus supports only 'active (1)',
                  'createAndGo (4)', and 'destroy (6)'."

        VARIATION   tRPAdminASPathRowStatus
            SYNTAX  RowStatus {
                       active               (1),
                    -- notInService         (2)
                    -- notReady             (3)
                       createAndGo          (4),
                    -- createAndWait        (5)
                       destroy              (6)
                    }
            DESCRIPTION
                 "tRPAdminASPathRowStatus supports only 'active (1)',
                  'createAndGo (4)', and 'destroy (6)'."

        VARIATION   tRPAdminCommunityRowStatus
            SYNTAX  RowStatus {
                       active               (1),
                    -- notInService         (2)
                    -- notReady             (3)
                       createAndGo          (4),
                    -- createAndWait        (5)
                       destroy              (6)
                    }
            DESCRIPTION
                 "tRPAdminCommunityRowStatus supports only 'active (1)',
                  'createAndGo (4)', and 'destroy (6)'."

        VARIATION   tRPAdminDampingRowStatus
            SYNTAX  RowStatus {
                       active               (1),
                    -- notInService         (2)
                    -- notReady             (3)
                       createAndGo          (4),
                    -- createAndWait        (5)
                       destroy              (6)
                    }
            DESCRIPTION
                 "tRPAdminDampingRowStatus supports only 'active (1)',
                  'createAndGo (4)', and 'destroy (6)'."

        VARIATION   tRPAdminPSAcceptActionASPath
            SYNTAX  INTEGER {
                       none(1),
                       add                  (2),
                    -- remove(3)
                       replace(4)
                    }
            DESCRIPTION
                 "tRPAdminPSAcceptActionASPath does not support the value
                  'remove(3)' as defined by TPolicyEntryEdit textual
                  convention."

        VARIATION   tRPAdminPSAcceptActionOrigin
            SYNTAX  INTEGER {
                       none                 (1),
                       igp                  (2),
                       egp                  (3),
                       incomplete           (4)
                    -- any                  (5)
                    -- aaa                  (6)
                    -- dhcp                 (7)
                    -- ludb                 (8)
                    }
            DESCRIPTION
                 "tRPAdminPSAcceptActionOrigin does not support the values
                  'any(5)', 'aaa(6)', 'dhcp(7)' and 'ludb(8)'."

        VARIATION   tRPAdminPSDefaultActionASPath
            SYNTAX  INTEGER {
                       none(1),
                       add                  (2),
                    -- remove(3)
                       replace(4)
                    }
            DESCRIPTION
                 "tRPAdminPSDefaultActionASPath does not support the value
                  'remove(3)' as defined by TPolicyEntryEdit textual
                  convention."

        VARIATION   tRPAdminPSDefaultActionOrigin
            SYNTAX  INTEGER {
                       none                 (1),
                       igp                  (2),
                       egp                  (3),
                       incomplete           (4)
                    -- any                  (5)
                    -- aaa                  (6)
                    -- dhcp                 (7)
                    -- ludb                 (8)
                    }
            DESCRIPTION
                 "tRPAdminPSDefaultActionOrigin does not support the values
                  'any(5)', 'aaa(6)', 'dhcp(7)' and 'ludb(8)'."

        VARIATION   tRPAdminPSFromCriteriaFamily
            SYNTAX  BITS {
                       ipv4Unicast          (0),
                       ipv4Multicast        (1),
                    -- ipv4UastMcast        (2)
                    -- ipv4MplsLabel        (3)
                       ipv4Vpn              (4),
                       ipv6Unicast          (5),
                       ipv6Multicast        (6),
                    -- ipv6UcastMcast       (7)
                    -- ipv6MplsLabel        (8)
                       ipv6Vpn              (9),
                       l2Vpn                (10),
                       ipv4Mvpn             (11),
                       msPw                 (12),
                       ipv4Flow             (13),
                       mdtSafi              (14),
                       routeTarget          (15),
                       mcastVpnIpv4         (16),
                       mvpnIpv6             (17),
                       ipv6Flow             (18),
                       evpn                 (19),
                       reserved20           (20)
                    }
            DESCRIPTION
                 "tRPAdminPSFromCriteriaFamily does not support values
                  'ipv4UastMcast (2)', 'ipv4MplsLabel (3)', 'ipv6UcastMcast
                  (7)', and 'ipv6MplsLabel (8)' as defined by the
                  TmnxBGPFamilyType textual convention."

        VARIATION   tRPAdminPSFromCriteriaRowStatus
            SYNTAX  RowStatus {
                       active               (1),
                    -- notInService         (2)
                    -- notReady             (3)
                       createAndGo          (4),
                    -- createAndWait        (5)
                       destroy              (6)
                    }
            DESCRIPTION
                 "tRPAdminPSFromCriteriaRowStatus supports only 'active (1)',
                  'createAndGo (4)', and 'destroy (6)'."

        VARIATION   tRPAdminPSFromCriteriaState
            SYNTAX  INTEGER {
                       none(1),
                       srrpMaster(2),
                       srrpNonMaster(3)
                    -- mobileMaster         (4)
                    -- mobileSlave          (5)
                    }
            DESCRIPTION
                 "tRPAdminPSFromCriteriaState does not support the values
                  'mobileMaster(4)' and 'mobileSlave(5)'."

        VARIATION   tRPAdminPSParamsRowStatus
            SYNTAX  RowStatus {
                       active               (1),
                    -- notInService         (2)
                    -- notReady             (3)
                       createAndGo          (4),
                    -- createAndWait        (5)
                       destroy              (6)
                    }
            DESCRIPTION
                 "tRPAdminPSParamsRowStatus supports only 'active (1)',
                  'createAndGo (4)', and 'destroy (6)'."

        VARIATION   tRPAdminPSToCriteriaRowStatus
            SYNTAX  RowStatus {
                       active               (1),
                    -- notInService         (2)
                    -- notReady             (3)
                       createAndGo          (4),
                    -- createAndWait        (5)
                       destroy              (6)
                    }
            DESCRIPTION
                 "tRPAdminPSToCriteriaRowStatus supports only 'active (1)',
                  'createAndGo (4)', and 'destroy (6)'."

        VARIATION   tRPAdminPolicyStatementRowStatus
            SYNTAX  RowStatus {
                       active               (1),
                    -- notInService         (2)
                    -- notReady             (3)
                       createAndGo          (4),
                    -- createAndWait        (5)
                       destroy              (6)
                    }
            DESCRIPTION
                 "tRPAdminPolicyStatementRowStatus supports only 'active (1)',
                  'createAndGo (4)', and 'destroy (6)'."

        VARIATION   tRPOperASPathEntryLastChanged
            ACCESS  not-implemented
            DESCRIPTION
                 "tRPOperASPathEntryLastChanged is not implemented on Nokia SROS
                  in release 14.0.

                  tRPOperASPathEntryLastChanged was obsoleted in release 5.0.
                  The TIMETRA-SYSTEM-MIB::tmnxConfigModify notification is used
                  instead."

        VARIATION   tRPOperASPathTableLastChanged
            ACCESS  not-implemented
            DESCRIPTION
                 "tRPOperASPathTableLastChanged is not implemented on Nokia SROS
                  in release 14.0.

                  tRPOperASPathTableLastChanged was obsoleted in release 5.0.
                  The TIMETRA-SYSTEM-MIB::tmnxConfigModify notification is used
                  instead."

        VARIATION   tRPOperCommunityEntryLastChanged
            ACCESS  not-implemented
            DESCRIPTION
                 "tRPOperCommunityEntryLastChanged is not implemented on Nokia
                  SROS in release 14.0.

                  tRPOperCommunityEntryLastChanged was obsoleted in release
                  5.0. The TIMETRA-SYSTEM-MIB::tmnxConfigModify notification is
                  used instead."

        VARIATION   tRPOperCommunityTableLastChanged
            ACCESS  not-implemented
            DESCRIPTION
                 "tRPOperCommunityTableLastChanged is not implemented on Nokia
                  SROS in release 14.0.

                  tRPOperCommunityTableLastChanged was obsoleted in release
                  5.0. The TIMETRA-SYSTEM-MIB::tmnxConfigModify notification is
                  used instead."

        VARIATION   tRPOperDampingEntryLastChanged
            ACCESS  not-implemented
            DESCRIPTION
                 "tRPOperDampingEntryLastChanged is not implemented on Nokia
                  SROS in release 14.0.

                  tRPOperDampingEntryLastChanged was obsoleted in release 5.0.
                  The TIMETRA-SYSTEM-MIB::tmnxConfigModify notification is used
                  instead."

        VARIATION   tRPOperDampingTableLastChanged
            ACCESS  not-implemented
            DESCRIPTION
                 "tRPOperDampingTableLastChanged is not implemented on Nokia
                  SROS in release 14.0.

                  tRPOperDampingTableLastChanged was obsoleted in release 5.0.
                  The TIMETRA-SYSTEM-MIB::tmnxConfigModify notification is used
                  instead."

        VARIATION   tRPOperInetPrefixListLastChg
            ACCESS  not-implemented
            DESCRIPTION
                 "tRPOperInetPrefixListLastChg is not implemented on Nokia SROS
                  in release 14.0.

                  tRPOperInetPrefixListLastChg was obsoleted in release 5.0.
                  The TIMETRA-SYSTEM-MIB::tmnxConfigModify notification is used
                  instead."

        VARIATION   tRPOperInetPrefixListTblLastChg
            ACCESS  not-implemented
            DESCRIPTION
                 "tRPOperInetPrefixListTblLastChg is not implemented on Nokia
                  SROS in release 14.0.

                  tRPOperInetPrefixListTblLastChg was obsoleted in release 5.0.
                  The TIMETRA-SYSTEM-MIB::tmnxConfigModify notification is used
                  instead."

        VARIATION   tRPOperPSAcceptActionParamsEntryLastChanged
            ACCESS  not-implemented
            DESCRIPTION
                 "tRPOperPSAcceptActionParamsEntryLastChanged is not implemented
                  on Nokia SROS in release 14.0.

                  tRPOperPSAcceptActionParamsEntryLastChanged was obsoleted in
                  release 5.0. The TIMETRA-SYSTEM-MIB::tmnxConfigModify
                  notification is used instead."

        VARIATION   tRPOperPSAcceptActionParamsTableLastChanged
            ACCESS  not-implemented
            DESCRIPTION
                 "tRPOperPSAcceptActionParamsTableLastChanged is not implemented
                  on Nokia SROS in release 14.0.

                  tRPOperPSAcceptActionParamsTableLastChanged was obsoleted in
                  release 5.0. The TIMETRA-SYSTEM-MIB::tmnxConfigModify
                  notification is used instead."

        VARIATION   tRPOperPSDefaultActionParamsEntryLastChanged
            ACCESS  not-implemented
            DESCRIPTION
                 "tRPOperPSDefaultActionParamsEntryLastChanged is not
                  implemented on Nokia SROS in release 14.0.

                  tRPOperPSDefaultActionParamsEntryLastChanged was obsoleted in
                  release 5.0. The TIMETRA-SYSTEM-MIB::tmnxConfigModify
                  notification is used instead."

        VARIATION   tRPOperPSDefaultActionParamsTableLastChanged
            ACCESS  not-implemented
            DESCRIPTION
                 "tRPOperPSDefaultActionParamsTableLastChanged is not
                  implemented on Nokia SROS in release 14.0.

                  tRPOperPSDefaultActionParamsTableLastChanged was obsoleted in
                  release 5.0. The TIMETRA-SYSTEM-MIB::tmnxConfigModify
                  notification is used instead."

        VARIATION   tRPOperPSFromCriteriaEntryLastChanged
            ACCESS  not-implemented
            DESCRIPTION
                 "tRPOperPSFromCriteriaEntryLastChanged is not implemented on
                  Nokia SROS in release 14.0.

                  tRPOperPSFromCriteriaEntryLastChanged was obsoleted in
                  release 5.0. The TIMETRA-SYSTEM-MIB::tmnxConfigModify
                  notification is used instead."

        VARIATION   tRPOperPSFromCriteriaFamily
            SYNTAX  BITS {
                       ipv4Unicast          (0),
                       ipv4Multicast        (1),
                    -- ipv4UastMcast        (2)
                    -- ipv4MplsLabel        (3)
                       ipv4Vpn              (4),
                       ipv6Unicast          (5),
                       ipv6Multicast        (6),
                    -- ipv6UcastMcast       (7)
                    -- ipv6MplsLabel        (8)
                       ipv6Vpn              (9),
                       l2Vpn                (10),
                       ipv4Mvpn             (11),
                       msPw                 (12),
                       ipv4Flow             (13),
                       mdtSafi              (14),
                       routeTarget          (15),
                       mcastVpnIpv4         (16),
                       mvpnIpv6             (17),
                       ipv6Flow             (18),
                       evpn                 (19),
                       reserved20           (20)
                    }
            DESCRIPTION
                 "tRPOperPSFromCriteriaFamily does not support values
                  'ipv4UastMcast (2)', 'ipv4MplsLabel (3)', 'ipv6UcastMcast
                  (7)', and 'ipv6MplsLabel (8)' as defined by the
                  TmnxBGPFamilyType textual convention."

        VARIATION   tRPOperPSFromCriteriaState
            SYNTAX  INTEGER {
                       none(1),
                       srrpMaster(2),
                       srrpNonMaster(3)
                    -- mobileMaster         (4)
                    -- mobileSlave          (5)
                    }
            DESCRIPTION
                 "tRPOperPSFromCriteriaState does not support the values
                  'mobileMaster(4)' and 'mobileSlave(5)'."

        VARIATION   tRPOperPSFromCriteriaTableLastChanged
            ACCESS  not-implemented
            DESCRIPTION
                 "tRPOperPSFromCriteriaTableLastChanged is not implemented on
                  Nokia SROS in release 14.0.

                  tRPOperPSFromCriteriaTableLastChanged was obsoleted in
                  release 5.0. The TIMETRA-SYSTEM-MIB::tmnxConfigModify
                  notification is used instead."

        VARIATION   tRPOperPSParamsEntryLastChanged
            ACCESS  not-implemented
            DESCRIPTION
                 "tRPOperPSParamsEntryLastChanged is not implemented on Nokia
                  SROS in release 14.0.

                  tRPOperPSParamsEntryLastChanged was obsoleted in release 5.0.
                  The TIMETRA-SYSTEM-MIB::tmnxConfigModify notification is used
                  instead."

        VARIATION   tRPOperPSParamsTableLastChanged
            ACCESS  not-implemented
            DESCRIPTION
                 "tRPOperPSParamsTableLastChanged is not implemented on Nokia
                  SROS in release 14.0.

                  tRPOperPSParamsTableLastChanged was obsoleted in release 5.0.
                  The TIMETRA-SYSTEM-MIB::tmnxConfigModify notification is used
                  instead."

        VARIATION   tRPOperPSToCriteriaEntryLastChanged
            ACCESS  not-implemented
            DESCRIPTION
                 "tRPOperPSToCriteriaEntryLastChanged is not implemented on
                  Nokia SROS in release 14.0.

                  tRPOperPSToCriteriaEntryLastChanged was obsoleted in release
                  5.0. The TIMETRA-SYSTEM-MIB::tmnxConfigModify notification is
                  used instead."

        VARIATION   tRPOperPSToCriteriaTableLastChanged
            ACCESS  not-implemented
            DESCRIPTION
                 "tRPOperPSToCriteriaTableLastChanged is not implemented on
                  Nokia SROS in release 14.0.

                  tRPOperPSToCriteriaTableLastChanged was obsoleted in release
                  5.0. The TIMETRA-SYSTEM-MIB::tmnxConfigModify notification is
                  used instead."

        VARIATION   tRPOperPolicyStatementEntryLastChanged
            ACCESS  not-implemented
            DESCRIPTION
                 "tRPOperPolicyStatementEntryLastChanged is not implemented on
                  Nokia SROS in release 14.0.

                  tRPOperPolicyStatementEntryLastChanged was obsoleted in
                  release 5.0. The TIMETRA-SYSTEM-MIB::tmnxConfigModify
                  notification is used instead."

        VARIATION   tRPOperPolicyStatementTableLastChanged
            ACCESS  not-implemented
            DESCRIPTION
                 "tRPOperPolicyStatementTableLastChanged is not implemented on
                  Nokia SROS in release 14.0.

                  tRPOperPolicyStatementTableLastChanged was obsoleted in
                  release 5.0. The TIMETRA-SYSTEM-MIB::tmnxConfigModify
                  notification is used instead."

        VARIATION   tRPOperPrefixListEntryLastChanged
            ACCESS  not-implemented
            DESCRIPTION
                 "tRPOperPrefixListEntryLastChanged is not implemented on Nokia
                  SROS in release 14.0.

                  tRPOperPrefixListEntryLastChanged was obsoleted in release
                  5.0. The TIMETRA-SYSTEM-MIB::tmnxConfigModify notification is
                  used instead."

        VARIATION   tRPOperPrefixListTableLastChanged
            ACCESS  not-implemented
            DESCRIPTION
                 "tRPOperPrefixListTableLastChanged is not implemented on Nokia
                  SROS in release 14.0.

                  tRPOperPrefixListTableLastChanged was obsoleted in release
                  5.0. The TIMETRA-SYSTEM-MIB::tmnxConfigModify notification is
                  used instead."

    ::= { tmnxSROSAgentV14v0  36 }

--
-- SROS RPKI CAPABILITIES
--
tmnxSROSRpkiV14v0                 AGENT-CAPABILITIES
    PRODUCT-RELEASE "Nokia SROS"
    STATUS          current
    DESCRIPTION
         "Implementation of rpki protocol capabilities for Nokia SROS systems
          release 14.0."

    SUPPORTS        TIMETRA-RPKI-MIB
        INCLUDES {
           tmnxRpkiNotificationGroup,
           tmnxRpkiOriginValidGroup
        }

    ::= { tmnxSROSAgentV14v0  92 }

--
-- SROS RSVP CAPABILITIES
--
tmnxSROSRsvpV14v0                 AGENT-CAPABILITIES
    PRODUCT-RELEASE "Nokia SROS"
    STATUS          current
    DESCRIPTION
         "Implementation of RSVP protocol capabilities for Nokia SROS systems
          release 14.0."

    SUPPORTS        RSVP-MIB
        INCLUDES {
           rsvpIfGroup,
           rsvpNbrGroup,
           rsvpNotificationGroup
-- EXCLUDE rsvpResvFwdGroup,
-- EXCLUDE rsvpResvGroup,
-- EXCLUDE rsvpSenderGroup,
-- EXCLUDE rsvpSessionGroup,
        }

        VARIATION   lostFlow
            ACCESS  not-implemented
            DESCRIPTION
                 "lostFlow is not implemented on Nokia SROS in release 14.0."

        VARIATION   newFlow
            ACCESS  not-implemented
            DESCRIPTION
                 "newFlow is not implemented on Nokia SROS in release 14.0."

        VARIATION   rsvpIfRefreshBlockadeMultiple
            ACCESS  read-only
            DESCRIPTION
                 "rsvpIfRefreshBlockadeMultiple is implemented as read-only on
                  Nokia SROS in release 14.0."

        VARIATION   rsvpIfRefreshInterval
            ACCESS  not-implemented
            DESCRIPTION
                 "rsvpIfRefreshInterval is not implemented on Nokia SROS in
                  release 14.0."

        VARIATION   rsvpIfRefreshMultiple
            ACCESS  read-only
            DESCRIPTION
                 "rsvpIfRefreshMultiple is implemented as read-only on Nokia
                  SROS in release 14.0."

        VARIATION   rsvpIfRouteDelay
            ACCESS  read-only
            DESCRIPTION
                 "rsvpIfRouteDelay is implemented as read-only on Nokia SROS in
                  release 14.0."

        VARIATION   rsvpIfTTL
            ACCESS  read-only
            DESCRIPTION
                 "rsvpIfTTL is implemented as read-only on Nokia SROS in release
                  14.0."

        VARIATION   rsvpIfUdpRequired
            ACCESS  read-only
            DESCRIPTION
                 "rsvpIfUdpRequired is implemented as read-only on Nokia SROS in
                  release 14.0."

        VARIATION   rsvpNbrProtocol
            ACCESS  read-only
            DESCRIPTION
                 "rsvpNbrProtocol is implemented as read-only on Nokia SROS in
                  release 14.0."

        VARIATION   rsvpNbrStatus
            ACCESS  read-only
            DESCRIPTION
                 "rsvpNbrStatus is implemented as read-only on Nokia SROS in
                  release 14.0.

                  Row entries cannot be created by SNMP SET requests."

    SUPPORTS        TIMETRA-RSVP-MIB
        INCLUDES {
           tmnxRsvpDSTEV7v0Group,
           tmnxRsvpGenTEThresholdV8v0Group,
           tmnxRsvpGeneralGroup,
           tmnxRsvpGeneralV10v0Group,
           tmnxRsvpGeneralV11v0Group,
           tmnxRsvpGeneralV12v0Group,
           tmnxRsvpGeneralV14v0Group,
           tmnxRsvpGeneralV6v0Group,
           tmnxRsvpGeneralV6v1Group,
           tmnxRsvpGeneralV7v0Group,
           tmnxRsvpGeneralV8v0Group,
           tmnxRsvpGeneralV9v0Group,
           tmnxRsvpIfTEThresholdV8v0Group,
           tmnxRsvpIfV5v0Group,
           tmnxRsvpIfV6v0Group,
           tmnxRsvpIfV7v0Group,
           tmnxRsvpIfV8v0Group,
           tmnxRsvpNbrV6v0Group,
           tmnxRsvpNotificationGroup,
           tmnxRsvpNotificationV9v0Group,
           tmnxRsvpSessionGroup,
           tmnxRsvpSessionV5v0Group,
           tmnxRsvpSessionV6v0Group,
           tmnxRsvpSessionV7v0Group
        }

        VARIATION   vRtrRsvpDSTEAdmCtlModel
            SYNTAX  INTEGER {
                       basic                (0),
                       mam                  (1)
                    -- rdm                  (2)
                    }
            DESCRIPTION
                 "vRtrRsvpDSTEAdmCtlModel does not support the value 'rdm' in
                  release 8.0."

        VARIATION   vRtrRsvpDSTEFCMappingRowStatus
            SYNTAX  RowStatus {
                       active               (1),
                    -- notInService         (2)
                    -- notReady             (3)
                       createAndGo          (4),
                    -- createAndWait        (5)
                       destroy              (6)
                    }
            DESCRIPTION
                 "vRtrRsvpDSTEFCMappingRowStatus supports only 'active (1)',
                  'createAndGo (4)', and 'destroy (6)'."

        VARIATION   vRtrRsvpIfAggregate
            ACCESS  read-only
            DESCRIPTION
                 "vRtrRsvpIfAggregate is implemented as read-only on Nokia SROS
                  in release 14.0."

        VARIATION   vRtrRsvpIfAuthChallenge
            ACCESS  not-implemented
            DESCRIPTION
                 "vRtrRsvpIfAuthChallenge is not supported in release 5.0."

        VARIATION   vRtrRsvpIfKeepMultiplier
            ACCESS  not-implemented
            DESCRIPTION
                 "vRtrRsvpIfKeepMultiplier is not implemented on Nokia SROS in
                  release 14.0.

                  vRtrRsvpIfKeepMultiplier was obsoleted in release 3.0."

        VARIATION   vRtrRsvpIfRefreshTime
            ACCESS  not-implemented
            DESCRIPTION
                 "vRtrRsvpIfRefreshTime is not implemented on Nokia SROS in
                  release 14.0.

                  vRtrRsvpIfRefreshTime was obsoleted in release 3.0."

    ::= { tmnxSROSAgentV14v0  37 }

--
-- SROS SAP CAPABILITIES
--
tmnxSROSSapV14v0                  AGENT-CAPABILITIES
    PRODUCT-RELEASE "Nokia SROS"
    STATUS          current
    DESCRIPTION
         "Implementation of SAP capabilities for Nokia SROS systems release
          14.0."

    SUPPORTS        TIMETRA-SAP-MIB
        INCLUDES {
           sapBgpEvpnMplsMhGroup,
           sapEthLoopbackV14v0Group,
           sapL3LoopbackNotifGroup,
           sapLagV12v0Group,
           sapTlsEtreeGroup,
           sapTlsFdbMacStatsGroup,
           sapV14v0NotifyObjsGroup,
           tmnxEvpnMplsMacMovNotifGroup,
           tmnxIPTunnelGreKeyV12v0Group,
           tmnxIpTnlOperChgGroup,
           tmnxIpTunnelEncaNotifyObjsGroup,
           tmnxIpTunnelEncapNotifyGroup,
           tmnxIpTunnelFragStatV12v0Group,
           tmnxIpTunnelV12v0Group,
           tmnxMsapPlcyCpmProtV12v0Group,
           tmnxMsapQosV12v0Group,
           tmnxSapArpHostGroup,
           tmnxSapAtmV6v0Group,
           tmnxSapAtmV9v0Group,
           tmnxSapBaseStatsV13v0Group,
           tmnxSapBaseV6v0Group,
           tmnxSapBgpEvpnAlmpGroup,
           tmnxSapBsxV10v0Group,
           tmnxSapBsxV7v0Group,
           tmnxSapBsxV9v0Group,
           tmnxSapCemNotificationV6v0Group,
           tmnxSapCemV6v0Group,
           tmnxSapCflowdGroupV11v0,
           tmnxSapDCpuProtV11v0Group,
           tmnxSapDcpNotifyObjsV11v0Group,
           tmnxSapDcpNotifyV11v0Group,
           tmnxSapDefHostV14v0Group,
           tmnxSapDefHostV9v0Group,
           tmnxSapDhcpV11v0Group,
           tmnxSapDhcpV13v0Group,
           tmnxSapDhcpV8v0Group,
           tmnxSapDiamNasreqGroup,
           tmnxSapDnGroup,
           tmnxSapEgrEncapGrpV13v0Group,
           tmnxSapEgrPortQGrpV11v0Group,
           tmnxSapEgrQosStatsGroup,
           tmnxSapEthCfmGroup,
           tmnxSapEthCfmMonitorGroup,
           tmnxSapEthCfmV12v0Group,
           tmnxSapEthLoopbackV11v0Group,
           tmnxSapEthLpbkNotifyV11v0Group,
           tmnxSapEthRingGroup,
           tmnxSapFPropBMacV8v0Group,
-- EXCLUDE tmnxSapFilterProfileV9v0Group
           tmnxSapFlowSPecV11v0Group,
           tmnxSapFrGroupV8v0,
           tmnxSapGreObsoletedGroup,
           tmnxSapGreV11v0Group,
           tmnxSapHsmdaV10v0Group,
           tmnxSapHsmdaV9v0Group,
           tmnxSapIgmpTrkGroup,
           tmnxSapIgmpTrkV11v0Group,
           tmnxSapIgmpTrkV8v0Group,
           tmnxSapInfoV14v0Group,
           tmnxSapIpTnlGroup,
           tmnxSapIpV6FilterV14v0Group,
           tmnxSapIpipeFaultPropGroup,
           tmnxSapIpipeNotificationGroup,
           tmnxSapIpipeV8v0Group,
           tmnxSapIpoeV13v0Group,
           tmnxSapL2ptV6v0Group,
           tmnxSapL2tpv3V14v0Group,
           tmnxSapLagV11v0Group,
           tmnxSapMonitorIPGroup,
           tmnxSapMrpV8v0Group,
           tmnxSapMsapV11v0Group,
           tmnxSapMsapV12v0Group,
           tmnxSapMsapV14v0Group,
           tmnxSapMsapV6v1Group,
           tmnxSapMsapV8v0Group,
           tmnxSapMsapV9v0Group,
           tmnxSapMstiV6v0Group,
           tmnxSapMvrpNotificationV8v0Group,
           tmnxSapMvrpV13v0Group,
           tmnxSapNotifObsoletedGroup,
           tmnxSapNotificationV10v0Group,
           tmnxSapNotificationV11v0Group,
           tmnxSapNotificationV13v0Group,
           tmnxSapNotificationV9v0Group,
           tmnxSapNotifyGroup,
           tmnxSapOverrideV8v0Group,
           tmnxSapOverrideV9v0Group,
           tmnxSapPbbGroup,
           tmnxSapPbbV12v0Group,
           tmnxSapPlcrV8v0Group,
           tmnxSapPlcrV9v0Group,
           tmnxSapPortIdV6v0Group,
           tmnxSapQosRateV13v0Group,
           tmnxSapQosSchedV13v0Group,
           tmnxSapQosStatsGroup,
           tmnxSapQosV12v0Group,
           tmnxSapQosV14v0Group,
           tmnxSapQueueOvrV13v0Group,
           tmnxSapRadiusFallbackGroup,
           tmnxSapRipNotifyGroup,
           tmnxSapSchedulerRateV11v0Group,
           tmnxSapShcvPolicyGroup,
           tmnxSapSpbGroup,
           tmnxSapSpbV11v0Group,
           tmnxSapStatHost6Group,
           tmnxSapStatHost6V13v0Group,
           tmnxSapStaticHostRipV13v0Group,
           tmnxSapStaticHostV11v0Group,
           tmnxSapStaticHostV9v0Group,
           tmnxSapStatsV10v0Group,
           tmnxSapStickyMsapGroup,
           tmnxSapSubMgmtV9v0Group,
           tmnxSapTlsPbbV14v0Group,
           tmnxSapTlsV12v0Group,
           tmnxSapTlsV7v0Group,
           tmnxSapTlsV8v0Group,
           tmnxSapV11v0Group,
           tmnxSapV14v0Group,
           tmnxSapV9v0Group,
           tmnxSapVplsV14v0Group,
           tmnxSapVprnLoopbackV14v0Group,
           tmnxTlsMsapPppoeV6v0Group
        }

        VARIATION   bridgedTLS
            ACCESS  not-implemented
            DESCRIPTION
                 "bridgedTLS is not implemented on Nokia SROS in release 14.0."

        VARIATION   msapPlcySubMgmtDefFilterProfile
            ACCESS  not-implemented
            DESCRIPTION
                 "msapPlcySubMgmtDefFilterProfile is not implemented on Nokia
                  SROS in release 14.0."

        VARIATION   sapCflowd
            DESCRIPTION
                 "sapCflowd is not accessible on cards that do not have SMP
                  processors."

        VARIATION   sapCpmProtMonitorIP
            DESCRIPTION
                 "sapCpmProtMonitorIP is supported on 7750 SR-7, 7750 SR-12,
                  7450 ESS-6, 7450 ESS-7, and 7450 ESS-12 only."

        VARIATION   sapCreated
            ACCESS  not-implemented
            DESCRIPTION
                 "sapCreated is not implemented on Nokia SROS in release 14.0.

                  This NOTIFICATION-TYPE is replaced with the
                  TIMETRA-SYSTEM-MIB.tmnxConfigModify notification"

        VARIATION   sapDeleted
            ACCESS  not-implemented
            DESCRIPTION
                 "sapDeleted is not implemented on Nokia SROS in release 14.0.

                  This NOTIFICATION-TYPE is replaced with the
                  TIMETRA-SYSTEM-MIB.tmnxConfigModify notification"

        VARIATION   sapEthLoopbackEntry
            CREATION-REQUIRES {
                       sapEthLoopbackRowStatus,
                       sapEthLoopbackMode
                    }
            DESCRIPTION
                 "Objects sapEthLoopbackRowStatus and sapEthLoopbackMode must be
                  set for row creation to succeed."

        VARIATION   sapEthLoopbackRowStatus
            SYNTAX  RowStatus {
                       active               (1),
                    -- notInService         (2)
                    -- notReady             (3)
                       createAndGo          (4),
                    -- createAndWait        (5)
                       destroy              (6)
                    }
            DESCRIPTION
                 "sapEthLoopbackRowStatus supports only 'active (1)',
                  'createAndGo (4)', and 'destroy (6)'."

        VARIATION   sapFPropBMacAddrRowStatus
            SYNTAX  RowStatus {
                       active               (1),
                    -- notInService         (2)
                    -- notReady             (3)
                       createAndGo          (4),
                    -- createAndWait        (5)
                       destroy              (6)
                    }
            DESCRIPTION
                 "sapFPropBMacAddrRowStatus supports only 'active (1)',
                  'createAndGo (4)', and 'destroy (6)'.

                  At most four rows with the same <svcId, sapPortId,
                  sapEncapValue> index triple are allowed."

        VARIATION   sapReceiveOwnBpdu
            ACCESS  not-implemented
            DESCRIPTION
                 "sapReceiveOwnBpdu is not implemented on Nokia SROS in release
                  14.0."

        VARIATION   sapStaticHostFilterProfile
            ACCESS  not-implemented
            DESCRIPTION
                 "sapStaticHostFilterProfile is not implemented on Nokia SROS in
                  release 14.0."

        VARIATION   sapStaticHostMRtRowStatus
            SYNTAX  RowStatus {
                       active               (1),
                    -- notInService         (2)
                    -- notReady             (3)
                       createAndGo          (4),
                    -- createAndWait        (5)
                       destroy              (6)
                    }
            DESCRIPTION
                 "sapStaticHostMRtRowStatus supports only 'active (1)',
                  'createAndGo (4)', and 'destroy (6)'."

        VARIATION   sapSubMgmtDefFilterProfile
            ACCESS  not-implemented
            DESCRIPTION
                 "sapSubMgmtDefFilterProfile is not implemented on Nokia SROS in
                  release 14.0."

        VARIATION   sapTlsStpBpduEncap
            SYNTAX  INTEGER {
                       dynamic              (1)
                    }
            DESCRIPTION
                 "The only value that can be assigned to sapTlsStpBpduEncap is
                  'dynamic (1)'. Additional values may be supported in a later
                  release."

        VARIATION   sapTmplTlsStpBpduEncap
            SYNTAX  INTEGER {
                       dynamic              (1)
                    }
            DESCRIPTION
                 "The only value that can be assigned to sapTmplTlsStpBpduEncap
                  is 'dynamic (1)'. Additional values may be supported in a
                  later release."

    ::= { tmnxSROSAgentV14v0  64 }

--
-- 7750c12 SAP CAPABILITIES
--
tmnx7750c12SapV14v0               AGENT-CAPABILITIES
    PRODUCT-RELEASE "Nokia SROS"
    STATUS          current
    DESCRIPTION
         "Implementation of SAP capabilities for Nokia 7750 c12 systems release
          14.0."

    SUPPORTS        TIMETRA-SAP-MIB
        INCLUDES {
           sapBgpEvpnMplsMhGroup,
           sapEthLoopbackV14v0Group,
           sapL3LoopbackNotifGroup,
           sapLagV12v0Group,
           sapTlsEtreeGroup,
           sapTlsFdbMacStatsGroup,
           sapV14v0NotifyObjsGroup,
           tmnxEvpnMplsMacMovNotifGroup,
           tmnxIPTunnelGreKeyV12v0Group,
           tmnxIpTnlOperChgGroup,
           tmnxIpTunnelEncaNotifyObjsGroup,
           tmnxIpTunnelEncapNotifyGroup,
           tmnxIpTunnelFragStatV12v0Group,
           tmnxIpTunnelV12v0Group,
-- EXCLUDE tmnxMsapPlcyCpmProtV12v0Group
           tmnxMsapQosV12v0Group,
           tmnxSapArpHostGroup,
           tmnxSapAtmV6v0Group,
           tmnxSapAtmV9v0Group,
           tmnxSapBaseStatsV13v0Group,
           tmnxSapBaseV6v0Group,
           tmnxSapBgpEvpnAlmpGroup,
           tmnxSapBsxV10v0Group,
           tmnxSapBsxV7v0Group,
           tmnxSapBsxV9v0Group,
           tmnxSapCemNotificationV6v0Group,
           tmnxSapCemV6v0Group,
           tmnxSapCflowdGroupV11v0,
           tmnxSapDCpuProtV11v0Group,
           tmnxSapDcpNotifyObjsV11v0Group,
           tmnxSapDcpNotifyV11v0Group,
           tmnxSapDefHostV14v0Group,
           tmnxSapDefHostV9v0Group,
           tmnxSapDhcpV11v0Group,
           tmnxSapDhcpV13v0Group,
           tmnxSapDhcpV8v0Group,
           tmnxSapDiamNasreqGroup,
           tmnxSapDnGroup,
           tmnxSapEgrEncapGrpV13v0Group,
           tmnxSapEgrPortQGrpV11v0Group,
           tmnxSapEgrQosStatsGroup,
           tmnxSapEthCfmGroup,
-- EXCLUDE tmnxSapEthCfmMonitorGroup
           tmnxSapEthCfmV12v0Group,
           tmnxSapEthLoopbackV11v0Group,
           tmnxSapEthLpbkNotifyV11v0Group,
           tmnxSapEthRingGroup,
           tmnxSapFPropBMacV8v0Group,
-- EXCLUDE tmnxSapFilterProfileV9v0Group
           tmnxSapFlowSPecV11v0Group,
           tmnxSapFrGroupV8v0,
           tmnxSapGreObsoletedGroup,
           tmnxSapGreV11v0Group,
-- EXCLUDE tmnxSapHsmdaV10v0Group
-- EXCLUDE tmnxSapHsmdaV9v0Group
           tmnxSapIgmpTrkGroup,
           tmnxSapIgmpTrkV11v0Group,
           tmnxSapIgmpTrkV8v0Group,
           tmnxSapInfoV14v0Group,
           tmnxSapIpTnlGroup,
           tmnxSapIpV6FilterV14v0Group,
           tmnxSapIpipeFaultPropGroup,
           tmnxSapIpipeNotificationGroup,
           tmnxSapIpipeV8v0Group,
           tmnxSapIpoeV13v0Group,
           tmnxSapL2ptV6v0Group,
           tmnxSapL2tpv3V14v0Group,
           tmnxSapLagV11v0Group,
           tmnxSapMonitorIPGroup,
           tmnxSapMrpV8v0Group,
           tmnxSapMsapV11v0Group,
           tmnxSapMsapV12v0Group,
           tmnxSapMsapV14v0Group,
           tmnxSapMsapV6v1Group,
           tmnxSapMsapV8v0Group,
           tmnxSapMsapV9v0Group,
           tmnxSapMstiV6v0Group,
           tmnxSapMvrpNotificationV8v0Group,
           tmnxSapMvrpV13v0Group,
           tmnxSapNotifObsoletedGroup,
           tmnxSapNotificationV10v0Group,
           tmnxSapNotificationV11v0Group,
           tmnxSapNotificationV13v0Group,
           tmnxSapNotificationV9v0Group,
           tmnxSapNotifyGroup,
           tmnxSapOverrideV8v0Group,
           tmnxSapOverrideV9v0Group,
           tmnxSapPbbGroup,
           tmnxSapPbbV12v0Group,
           tmnxSapPlcrV8v0Group,
           tmnxSapPlcrV9v0Group,
           tmnxSapPortIdV6v0Group,
           tmnxSapQosRateV13v0Group,
           tmnxSapQosSchedV13v0Group,
           tmnxSapQosStatsGroup,
           tmnxSapQosV12v0Group,
           tmnxSapQosV14v0Group,
           tmnxSapQueueOvrV13v0Group,
           tmnxSapRadiusFallbackGroup,
           tmnxSapRipNotifyGroup,
           tmnxSapSchedulerRateV11v0Group,
           tmnxSapShcvPolicyGroup,
           tmnxSapSpbGroup,
           tmnxSapSpbV11v0Group,
           tmnxSapStatHost6Group,
           tmnxSapStatHost6V13v0Group,
           tmnxSapStaticHostRipV13v0Group,
           tmnxSapStaticHostV11v0Group,
           tmnxSapStaticHostV9v0Group,
           tmnxSapStatsV10v0Group,
           tmnxSapStickyMsapGroup,
           tmnxSapSubMgmtV9v0Group,
           tmnxSapTlsPbbV14v0Group,
           tmnxSapTlsV12v0Group,
           tmnxSapTlsV7v0Group,
           tmnxSapTlsV8v0Group,
           tmnxSapV11v0Group,
           tmnxSapV14v0Group,
           tmnxSapV9v0Group,
           tmnxSapVplsV14v0Group,
           tmnxSapVprnLoopbackV14v0Group,
           tmnxTlsMsapPppoeV6v0Group
        }

        VARIATION   bridgedTLS
            ACCESS  not-implemented
            DESCRIPTION
                 "bridgedTLS is not implemented on Nokia 7750 c12 in release
                  14.0."

        VARIATION   msapPlcySubMgmtDefFilterProfile
            ACCESS  not-implemented
            DESCRIPTION
                 "msapPlcySubMgmtDefFilterProfile is not implemented on Nokia
                  7750 c12 in release 14.0."

        VARIATION   sapAntiSpoofing
            SYNTAX  INTEGER {
                       disabled             (0),
                       sourceIpAddr         (1),
                       sourceMacAddr        (2),
                       sourceIpAndMacAddr   (3)
                    -- nextHopIpAndMacAddr  (4)
                    }
            DESCRIPTION
                 "sapAntiSpoofing does not support the value
                  'nextHopIpAndMacAddr (4)' on Nokia 7750 c12."

        VARIATION   sapCflowd
            DESCRIPTION
                 "sapCflowd is not accessible on cards that do not have SMP
                  processors."

        VARIATION   sapCpmProtMonitorIP
            DESCRIPTION
                 "sapCpmProtMonitorIP is supported on 7750 SR-7, 7750 SR-12,
                  7450 ESS-6, 7450 ESS-7, and 7450 ESS-12 only."

        VARIATION   sapCreated
            ACCESS  not-implemented
            DESCRIPTION
                 "sapCreated is not implemented on Nokia 7750 c12 in release
                  14.0.

                  This NOTIFICATION-TYPE is replaced with the
                  TIMETRA-SYSTEM-MIB.tmnxConfigModify notification"

        VARIATION   sapDeleted
            ACCESS  not-implemented
            DESCRIPTION
                 "sapDeleted is not implemented on Nokia 7750 c12 in release
                  14.0.

                  This NOTIFICATION-TYPE is replaced with the
                  TIMETRA-SYSTEM-MIB.tmnxConfigModify notification"

        VARIATION   sapEthLoopbackEntry
            CREATION-REQUIRES {
                       sapEthLoopbackRowStatus,
                       sapEthLoopbackMode
                    }
            DESCRIPTION
                 "Objects sapEthLoopbackRowStatus and sapEthLoopbackMode must be
                  set for row creation to succeed."

        VARIATION   sapEthLoopbackRowStatus
            SYNTAX  RowStatus {
                       active               (1),
                    -- notInService         (2)
                    -- notReady             (3)
                       createAndGo          (4),
                    -- createAndWait        (5)
                       destroy              (6)
                    }
            DESCRIPTION
                 "sapEthLoopbackRowStatus supports only 'active (1)',
                  'createAndGo (4)', and 'destroy (6)'."

        VARIATION   sapFPropBMacAddrRowStatus
            SYNTAX  RowStatus {
                       active               (1),
                    -- notInService         (2)
                    -- notReady             (3)
                       createAndGo          (4),
                    -- createAndWait        (5)
                       destroy              (6)
                    }
            DESCRIPTION
                 "sapFPropBMacAddrRowStatus supports only 'active (1)',
                  'createAndGo (4)', and 'destroy (6)'.

                  At most four rows with the same <svcId, sapPortId,
                  sapEncapValue> index triple are allowed."

        VARIATION   sapReceiveOwnBpdu
            ACCESS  not-implemented
            DESCRIPTION
                 "sapReceiveOwnBpdu is not implemented on Nokia 7750 c12 in
                  release 14.0."

        VARIATION   sapStaticHostFilterProfile
            ACCESS  not-implemented
            DESCRIPTION
                 "sapStaticHostFilterProfile is not implemented on Nokia 7750
                  c12 in release 14.0."

        VARIATION   sapStaticHostMRtRowStatus
            SYNTAX  RowStatus {
                       active               (1),
                    -- notInService         (2)
                    -- notReady             (3)
                       createAndGo          (4),
                    -- createAndWait        (5)
                       destroy              (6)
                    }
            DESCRIPTION
                 "sapStaticHostMRtRowStatus supports only 'active (1)',
                  'createAndGo (4)', and 'destroy (6)'."

        VARIATION   sapSubMgmtDefFilterProfile
            ACCESS  not-implemented
            DESCRIPTION
                 "sapSubMgmtDefFilterProfile is not implemented on Nokia 7750
                  c12 in release 14.0."

        VARIATION   sapTlsStpBpduEncap
            SYNTAX  INTEGER {
                       dynamic              (1)
                    }
            DESCRIPTION
                 "The only value that can be assigned to sapTlsStpBpduEncap is
                  'dynamic (1)'. Additional values may be supported in a later
                  release."

        VARIATION   sapTmplTlsStpBpduEncap
            SYNTAX  INTEGER {
                       dynamic              (1)
                    }
            DESCRIPTION
                 "The only value that can be assigned to sapTmplTlsStpBpduEncap
                  is 'dynamic (1)'. Additional values may be supported in a
                  later release."

    ::= { tmnx7750c12AgentV14v0  64 }

--
-- 7750c4 SAP CAPABILITIES
--
tmnx7750c4SapV14v0                AGENT-CAPABILITIES
    PRODUCT-RELEASE "Nokia SROS"
    STATUS          current
    DESCRIPTION
         "Implementation of SAP capabilities for Nokia 7750 c4 systems release
          14.0."

    SUPPORTS        TIMETRA-SAP-MIB
        INCLUDES {
           sapBgpEvpnMplsMhGroup,
           sapEthLoopbackV14v0Group,
           sapL3LoopbackNotifGroup,
           sapLagV12v0Group,
           sapTlsEtreeGroup,
           sapTlsFdbMacStatsGroup,
           sapV14v0NotifyObjsGroup,
           tmnxEvpnMplsMacMovNotifGroup,
           tmnxIPTunnelGreKeyV12v0Group,
           tmnxIpTnlOperChgGroup,
           tmnxIpTunnelEncaNotifyObjsGroup,
           tmnxIpTunnelEncapNotifyGroup,
           tmnxIpTunnelFragStatV12v0Group,
           tmnxIpTunnelV12v0Group,
-- EXCLUDE tmnxMsapPlcyCpmProtV12v0Group
           tmnxMsapQosV12v0Group,
           tmnxSapArpHostGroup,
           tmnxSapAtmV6v0Group,
           tmnxSapAtmV9v0Group,
           tmnxSapBaseStatsV13v0Group,
           tmnxSapBaseV6v0Group,
           tmnxSapBgpEvpnAlmpGroup,
           tmnxSapBsxV10v0Group,
           tmnxSapBsxV7v0Group,
           tmnxSapBsxV9v0Group,
           tmnxSapCemNotificationV6v0Group,
           tmnxSapCemV6v0Group,
           tmnxSapCflowdGroupV11v0,
           tmnxSapDCpuProtV11v0Group,
           tmnxSapDcpNotifyObjsV11v0Group,
           tmnxSapDcpNotifyV11v0Group,
           tmnxSapDefHostV14v0Group,
           tmnxSapDefHostV9v0Group,
           tmnxSapDhcpV11v0Group,
           tmnxSapDhcpV13v0Group,
           tmnxSapDhcpV8v0Group,
           tmnxSapDiamNasreqGroup,
           tmnxSapDnGroup,
           tmnxSapEgrEncapGrpV13v0Group,
           tmnxSapEgrPortQGrpV11v0Group,
           tmnxSapEgrQosStatsGroup,
           tmnxSapEthCfmGroup,
-- EXCLUDE tmnxSapEthCfmMonitorGroup
           tmnxSapEthCfmV12v0Group,
           tmnxSapEthLoopbackV11v0Group,
           tmnxSapEthLpbkNotifyV11v0Group,
           tmnxSapEthRingGroup,
           tmnxSapFPropBMacV8v0Group,
-- EXCLUDE tmnxSapFilterProfileV9v0Group
           tmnxSapFlowSPecV11v0Group,
           tmnxSapFrGroupV8v0,
           tmnxSapGreObsoletedGroup,
           tmnxSapGreV11v0Group,
-- EXCLUDE tmnxSapHsmdaV10v0Group
-- EXCLUDE tmnxSapHsmdaV9v0Group
           tmnxSapIgmpTrkGroup,
           tmnxSapIgmpTrkV11v0Group,
           tmnxSapIgmpTrkV8v0Group,
           tmnxSapInfoV14v0Group,
           tmnxSapIpTnlGroup,
           tmnxSapIpV6FilterV14v0Group,
           tmnxSapIpipeFaultPropGroup,
           tmnxSapIpipeNotificationGroup,
           tmnxSapIpipeV8v0Group,
           tmnxSapIpoeV13v0Group,
           tmnxSapL2ptV6v0Group,
           tmnxSapL2tpv3V14v0Group,
           tmnxSapLagV11v0Group,
           tmnxSapMonitorIPGroup,
           tmnxSapMrpV8v0Group,
           tmnxSapMsapV11v0Group,
           tmnxSapMsapV12v0Group,
           tmnxSapMsapV14v0Group,
           tmnxSapMsapV6v1Group,
           tmnxSapMsapV8v0Group,
           tmnxSapMsapV9v0Group,
           tmnxSapMstiV6v0Group,
           tmnxSapMvrpNotificationV8v0Group,
           tmnxSapMvrpV13v0Group,
           tmnxSapNotifObsoletedGroup,
           tmnxSapNotificationV10v0Group,
           tmnxSapNotificationV11v0Group,
           tmnxSapNotificationV13v0Group,
           tmnxSapNotificationV9v0Group,
           tmnxSapNotifyGroup,
           tmnxSapOverrideV8v0Group,
           tmnxSapOverrideV9v0Group,
           tmnxSapPbbGroup,
           tmnxSapPbbV12v0Group,
           tmnxSapPlcrV8v0Group,
           tmnxSapPlcrV9v0Group,
           tmnxSapPortIdV6v0Group,
           tmnxSapQosRateV13v0Group,
           tmnxSapQosSchedV13v0Group,
           tmnxSapQosStatsGroup,
           tmnxSapQosV12v0Group,
           tmnxSapQosV14v0Group,
           tmnxSapQueueOvrV13v0Group,
           tmnxSapRadiusFallbackGroup,
           tmnxSapRipNotifyGroup,
           tmnxSapSchedulerRateV11v0Group,
           tmnxSapShcvPolicyGroup,
           tmnxSapSpbGroup,
           tmnxSapSpbV11v0Group,
           tmnxSapStatHost6Group,
           tmnxSapStatHost6V13v0Group,
           tmnxSapStaticHostRipV13v0Group,
           tmnxSapStaticHostV11v0Group,
           tmnxSapStaticHostV9v0Group,
           tmnxSapStatsV10v0Group,
           tmnxSapStickyMsapGroup,
           tmnxSapSubMgmtV9v0Group,
           tmnxSapTlsPbbV14v0Group,
           tmnxSapTlsV12v0Group,
           tmnxSapTlsV7v0Group,
           tmnxSapTlsV8v0Group,
           tmnxSapV11v0Group,
           tmnxSapV14v0Group,
           tmnxSapV9v0Group,
           tmnxSapVplsV14v0Group,
           tmnxSapVprnLoopbackV14v0Group,
           tmnxTlsMsapPppoeV6v0Group
        }

        VARIATION   bridgedTLS
            ACCESS  not-implemented
            DESCRIPTION
                 "bridgedTLS is not implemented on Nokia 7750 c4 in release
                  14.0."

        VARIATION   msapPlcySubMgmtDefFilterProfile
            ACCESS  not-implemented
            DESCRIPTION
                 "msapPlcySubMgmtDefFilterProfile is not implemented on Nokia
                  7750 c4 in release 14.0."

        VARIATION   sapAntiSpoofing
            SYNTAX  INTEGER {
                       disabled             (0),
                       sourceIpAddr         (1),
                       sourceMacAddr        (2),
                       sourceIpAndMacAddr   (3)
                    -- nextHopIpAndMacAddr  (4)
                    }
            DESCRIPTION
                 "sapAntiSpoofing does not support the value
                  'nextHopIpAndMacAddr (4)' on Nokia 7750 c4."

        VARIATION   sapCflowd
            DESCRIPTION
                 "sapCflowd is not accessible on cards that do not have SMP
                  processors."

        VARIATION   sapCpmProtMonitorIP
            DESCRIPTION
                 "sapCpmProtMonitorIP is supported on 7750 SR-7, 7750 SR-12,
                  7450 ESS-6, 7450 ESS-7, and 7450 ESS-12 only."

        VARIATION   sapCreated
            ACCESS  not-implemented
            DESCRIPTION
                 "sapCreated is not implemented on Nokia 7750 c4 in release
                  14.0.

                  This NOTIFICATION-TYPE is replaced with the
                  TIMETRA-SYSTEM-MIB.tmnxConfigModify notification"

        VARIATION   sapDeleted
            ACCESS  not-implemented
            DESCRIPTION
                 "sapDeleted is not implemented on Nokia 7750 c4 in release
                  14.0.

                  This NOTIFICATION-TYPE is replaced with the
                  TIMETRA-SYSTEM-MIB.tmnxConfigModify notification"

        VARIATION   sapEthLoopbackEntry
            CREATION-REQUIRES {
                       sapEthLoopbackRowStatus,
                       sapEthLoopbackMode
                    }
            DESCRIPTION
                 "Objects sapEthLoopbackRowStatus and sapEthLoopbackMode must be
                  set for row creation to succeed."

        VARIATION   sapEthLoopbackRowStatus
            SYNTAX  RowStatus {
                       active               (1),
                    -- notInService         (2)
                    -- notReady             (3)
                       createAndGo          (4),
                    -- createAndWait        (5)
                       destroy              (6)
                    }
            DESCRIPTION
                 "sapEthLoopbackRowStatus supports only 'active (1)',
                  'createAndGo (4)', and 'destroy (6)'."

        VARIATION   sapFPropBMacAddrRowStatus
            SYNTAX  RowStatus {
                       active               (1),
                    -- notInService         (2)
                    -- notReady             (3)
                       createAndGo          (4),
                    -- createAndWait        (5)
                       destroy              (6)
                    }
            DESCRIPTION
                 "sapFPropBMacAddrRowStatus supports only 'active (1)',
                  'createAndGo (4)', and 'destroy (6)'.

                  At most four rows with the same <svcId, sapPortId,
                  sapEncapValue> index triple are allowed."

        VARIATION   sapReceiveOwnBpdu
            ACCESS  not-implemented
            DESCRIPTION
                 "sapReceiveOwnBpdu is not implemented on Nokia 7750 c4 in
                  release 14.0."

        VARIATION   sapStaticHostFilterProfile
            ACCESS  not-implemented
            DESCRIPTION
                 "sapStaticHostFilterProfile is not implemented on Nokia 7750 c4
                  in release 14.0."

        VARIATION   sapStaticHostMRtRowStatus
            SYNTAX  RowStatus {
                       active               (1),
                    -- notInService         (2)
                    -- notReady             (3)
                       createAndGo          (4),
                    -- createAndWait        (5)
                       destroy              (6)
                    }
            DESCRIPTION
                 "sapStaticHostMRtRowStatus supports only 'active (1)',
                  'createAndGo (4)', and 'destroy (6)'."

        VARIATION   sapSubMgmtDefFilterProfile
            ACCESS  not-implemented
            DESCRIPTION
                 "sapSubMgmtDefFilterProfile is not implemented on Nokia 7750 c4
                  in release 14.0."

        VARIATION   sapTlsStpBpduEncap
            SYNTAX  INTEGER {
                       dynamic              (1)
                    }
            DESCRIPTION
                 "The only value that can be assigned to sapTlsStpBpduEncap is
                  'dynamic (1)'. Additional values may be supported in a later
                  release."

        VARIATION   sapTmplTlsStpBpduEncap
            SYNTAX  INTEGER {
                       dynamic              (1)
                    }
            DESCRIPTION
                 "The only value that can be assigned to sapTmplTlsStpBpduEncap
                  is 'dynamic (1)'. Additional values may be supported in a
                  later release."

    ::= { tmnx7750c4AgentV14v0  64 }

--
-- 7450 SAP CAPABILITIES
--
tmnx7450SapV14v0                  AGENT-CAPABILITIES
    PRODUCT-RELEASE "Nokia SROS"
    STATUS          current
    DESCRIPTION
         "Implementation of SAP capabilities for Nokia 7450 systems release
          14.0."

    SUPPORTS        TIMETRA-SAP-MIB
        INCLUDES {
           sapBgpEvpnMplsMhGroup,
           sapEthLoopbackV14v0Group,
           sapL3LoopbackNotifGroup,
           sapLagV12v0Group,
           sapTlsEtreeGroup,
           sapTlsFdbMacStatsGroup,
           sapV14v0NotifyObjsGroup,
           tmnxEvpnMplsMacMovNotifGroup,
           tmnxIPTunnelGreKeyV12v0Group,
           tmnxIpTnlOperChgGroup,
           tmnxIpTunnelEncaNotifyObjsGroup,
           tmnxIpTunnelEncapNotifyGroup,
           tmnxIpTunnelFragStatV12v0Group,
           tmnxIpTunnelV12v0Group,
           tmnxMsapPlcyCpmProtV12v0Group,
           tmnxMsapQosV12v0Group,
           tmnxSapArpHostGroup,
           tmnxSapAtmV6v0Group,
           tmnxSapAtmV9v0Group,
           tmnxSapBaseStatsV13v0Group,
           tmnxSapBaseV6v0Group,
           tmnxSapBgpEvpnAlmpGroup,
           tmnxSapBsxV10v0Group,
           tmnxSapBsxV7v0Group,
           tmnxSapBsxV9v0Group,
-- EXCLUDE tmnxSapCemNotificationV6v0Group
-- EXCLUDE tmnxSapCemV6v0Group
           tmnxSapCflowdGroupV11v0,
           tmnxSapDCpuProtV11v0Group,
           tmnxSapDcpNotifyObjsV11v0Group,
           tmnxSapDcpNotifyV11v0Group,
           tmnxSapDefHostV14v0Group,
           tmnxSapDefHostV9v0Group,
           tmnxSapDhcpV11v0Group,
           tmnxSapDhcpV13v0Group,
           tmnxSapDhcpV8v0Group,
           tmnxSapDiamNasreqGroup,
           tmnxSapDnGroup,
           tmnxSapEgrEncapGrpV13v0Group,
           tmnxSapEgrPortQGrpV11v0Group,
           tmnxSapEgrQosStatsGroup,
           tmnxSapEthCfmGroup,
           tmnxSapEthCfmMonitorGroup,
           tmnxSapEthCfmV12v0Group,
           tmnxSapEthLoopbackV11v0Group,
           tmnxSapEthLpbkNotifyV11v0Group,
           tmnxSapEthRingGroup,
           tmnxSapFPropBMacV8v0Group,
-- EXCLUDE tmnxSapFilterProfileV9v0Group
           tmnxSapFlowSPecV11v0Group,
           tmnxSapFrGroupV8v0,
           tmnxSapGreObsoletedGroup,
           tmnxSapGreV11v0Group,
           tmnxSapHsmdaV10v0Group,
           tmnxSapHsmdaV9v0Group,
           tmnxSapIgmpTrkGroup,
           tmnxSapIgmpTrkV11v0Group,
           tmnxSapIgmpTrkV8v0Group,
           tmnxSapInfoV14v0Group,
           tmnxSapIpTnlGroup,
           tmnxSapIpV6FilterV14v0Group,
           tmnxSapIpipeFaultPropGroup,
           tmnxSapIpipeNotificationGroup,
           tmnxSapIpipeV8v0Group,
           tmnxSapIpoeV13v0Group,
           tmnxSapL2ptV6v0Group,
           tmnxSapL2tpv3V14v0Group,
           tmnxSapLagV11v0Group,
           tmnxSapMonitorIPGroup,
           tmnxSapMrpV8v0Group,
           tmnxSapMsapV11v0Group,
           tmnxSapMsapV12v0Group,
           tmnxSapMsapV14v0Group,
           tmnxSapMsapV6v1Group,
           tmnxSapMsapV8v0Group,
           tmnxSapMsapV9v0Group,
           tmnxSapMstiV6v0Group,
           tmnxSapMvrpNotificationV8v0Group,
           tmnxSapMvrpV13v0Group,
           tmnxSapNotifObsoletedGroup,
           tmnxSapNotificationV10v0Group,
           tmnxSapNotificationV11v0Group,
           tmnxSapNotificationV13v0Group,
           tmnxSapNotificationV9v0Group,
           tmnxSapNotifyGroup,
           tmnxSapOverrideV8v0Group,
           tmnxSapOverrideV9v0Group,
           tmnxSapPbbGroup,
           tmnxSapPbbV12v0Group,
           tmnxSapPlcrV8v0Group,
           tmnxSapPlcrV9v0Group,
           tmnxSapPortIdV6v0Group,
           tmnxSapQosRateV13v0Group,
           tmnxSapQosSchedV13v0Group,
           tmnxSapQosStatsGroup,
           tmnxSapQosV12v0Group,
           tmnxSapQosV14v0Group,
           tmnxSapQueueOvrV13v0Group,
           tmnxSapRadiusFallbackGroup,
           tmnxSapRipNotifyGroup,
           tmnxSapSchedulerRateV11v0Group,
           tmnxSapShcvPolicyGroup,
           tmnxSapSpbGroup,
           tmnxSapSpbV11v0Group,
           tmnxSapStatHost6Group,
           tmnxSapStatHost6V13v0Group,
           tmnxSapStaticHostRipV13v0Group,
           tmnxSapStaticHostV11v0Group,
           tmnxSapStaticHostV9v0Group,
           tmnxSapStatsV10v0Group,
           tmnxSapStickyMsapGroup,
           tmnxSapSubMgmtV9v0Group,
           tmnxSapTlsPbbV14v0Group,
           tmnxSapTlsV12v0Group,
           tmnxSapTlsV7v0Group,
           tmnxSapTlsV8v0Group,
           tmnxSapV11v0Group,
           tmnxSapV14v0Group,
           tmnxSapV9v0Group,
           tmnxSapVplsV14v0Group,
           tmnxSapVprnLoopbackV14v0Group,
           tmnxTlsMsapPppoeV6v0Group
        }

        VARIATION   bridgedTLS
            ACCESS  not-implemented
            DESCRIPTION
                 "bridgedTLS is not implemented on Nokia 7450 in release 14.0."

        VARIATION   msapPlcySubMgmtDefFilterProfile
            ACCESS  not-implemented
            DESCRIPTION
                 "msapPlcySubMgmtDefFilterProfile is not implemented on Nokia
                  7450 in release 14.0."

        VARIATION   sapAntiSpoofing
            SYNTAX  INTEGER {
                       disabled             (0),
                       sourceIpAddr         (1),
                       sourceMacAddr        (2),
                       sourceIpAndMacAddr   (3)
                    -- nextHopIpAndMacAddr  (4)
                    }
            DESCRIPTION
                 "sapAntiSpoofing does not support the value
                  'nextHopIpAndMacAddr (4)' on Nokia 7450."

        VARIATION   sapCflowd
            DESCRIPTION
                 "sapCflowd is not accessible on cards that do not have SMP
                  processors."

        VARIATION   sapCpmProtMonitorIP
            DESCRIPTION
                 "sapCpmProtMonitorIP is supported on 7750 SR-7, 7750 SR-12,
                  7450 ESS-6, 7450 ESS-7, and 7450 ESS-12 only."

        VARIATION   sapCreated
            ACCESS  not-implemented
            DESCRIPTION
                 "sapCreated is not implemented on Nokia 7450 in release 14.0.

                  This NOTIFICATION-TYPE is replaced with the
                  TIMETRA-SYSTEM-MIB.tmnxConfigModify notification"

        VARIATION   sapDeleted
            ACCESS  not-implemented
            DESCRIPTION
                 "sapDeleted is not implemented on Nokia 7450 in release 14.0.

                  This NOTIFICATION-TYPE is replaced with the
                  TIMETRA-SYSTEM-MIB.tmnxConfigModify notification"

        VARIATION   sapEthLoopbackEntry
            CREATION-REQUIRES {
                       sapEthLoopbackRowStatus,
                       sapEthLoopbackMode
                    }
            DESCRIPTION
                 "Objects sapEthLoopbackRowStatus and sapEthLoopbackMode must be
                  set for row creation to succeed."

        VARIATION   sapEthLoopbackRowStatus
            SYNTAX  RowStatus {
                       active               (1),
                    -- notInService         (2)
                    -- notReady             (3)
                       createAndGo          (4),
                    -- createAndWait        (5)
                       destroy              (6)
                    }
            DESCRIPTION
                 "sapEthLoopbackRowStatus supports only 'active (1)',
                  'createAndGo (4)', and 'destroy (6)'."

        VARIATION   sapFPropBMacAddrRowStatus
            SYNTAX  RowStatus {
                       active               (1),
                    -- notInService         (2)
                    -- notReady             (3)
                       createAndGo          (4),
                    -- createAndWait        (5)
                       destroy              (6)
                    }
            DESCRIPTION
                 "sapFPropBMacAddrRowStatus supports only 'active (1)',
                  'createAndGo (4)', and 'destroy (6)'.

                  At most four rows with the same <svcId, sapPortId,
                  sapEncapValue> index triple are allowed."

        VARIATION   sapReceiveOwnBpdu
            ACCESS  not-implemented
            DESCRIPTION
                 "sapReceiveOwnBpdu is not implemented on Nokia 7450 in release
                  14.0."

        VARIATION   sapStaticHostFilterProfile
            ACCESS  not-implemented
            DESCRIPTION
                 "sapStaticHostFilterProfile is not implemented on Nokia 7450 in
                  release 14.0."

        VARIATION   sapStaticHostMRtRowStatus
            SYNTAX  RowStatus {
                       active               (1),
                    -- notInService         (2)
                    -- notReady             (3)
                       createAndGo          (4),
                    -- createAndWait        (5)
                       destroy              (6)
                    }
            DESCRIPTION
                 "sapStaticHostMRtRowStatus supports only 'active (1)',
                  'createAndGo (4)', and 'destroy (6)'."

        VARIATION   sapSubMgmtDefFilterProfile
            ACCESS  not-implemented
            DESCRIPTION
                 "sapSubMgmtDefFilterProfile is not implemented on Nokia 7450 in
                  release 14.0."

        VARIATION   sapTlsStpBpduEncap
            SYNTAX  INTEGER {
                       dynamic              (1)
                    }
            DESCRIPTION
                 "The only value that can be assigned to sapTlsStpBpduEncap is
                  'dynamic (1)'. Additional values may be supported in a later
                  release."

        VARIATION   sapTmplTlsStpBpduEncap
            SYNTAX  INTEGER {
                       dynamic              (1)
                    }
            DESCRIPTION
                 "The only value that can be assigned to sapTmplTlsStpBpduEncap
                  is 'dynamic (1)'. Additional values may be supported in a
                  later release."

    ::= { tmnx7450AgentV14v0  64 }

--
-- 7710 SAP CAPABILITIES
--
tmnx7710SapV14v0                  AGENT-CAPABILITIES
    PRODUCT-RELEASE "Nokia SROS"
    STATUS          current
    DESCRIPTION
         "Implementation of SAP capabilities for Nokia 7710 systems release
          14.0."

    SUPPORTS        TIMETRA-SAP-MIB
        INCLUDES {
           sapBgpEvpnMplsMhGroup,
           sapEthLoopbackV14v0Group,
           sapL3LoopbackNotifGroup,
           sapLagV12v0Group,
           sapTlsEtreeGroup,
           sapTlsFdbMacStatsGroup,
           sapV14v0NotifyObjsGroup,
           tmnxEvpnMplsMacMovNotifGroup,
           tmnxIPTunnelGreKeyV12v0Group,
           tmnxIpTnlOperChgGroup,
           tmnxIpTunnelEncaNotifyObjsGroup,
           tmnxIpTunnelEncapNotifyGroup,
           tmnxIpTunnelFragStatV12v0Group,
           tmnxIpTunnelV12v0Group,
-- EXCLUDE tmnxMsapPlcyCpmProtV12v0Group
           tmnxMsapQosV12v0Group,
           tmnxSapArpHostGroup,
           tmnxSapAtmV6v0Group,
           tmnxSapAtmV9v0Group,
           tmnxSapBaseStatsV13v0Group,
           tmnxSapBaseV6v0Group,
           tmnxSapBgpEvpnAlmpGroup,
-- EXCLUDE tmnxSapBsxV10v0Group
-- EXCLUDE tmnxSapBsxV7v0Group
-- EXCLUDE tmnxSapBsxV9v0Group
           tmnxSapCemNotificationV6v0Group,
           tmnxSapCemV6v0Group,
           tmnxSapCflowdGroupV11v0,
           tmnxSapDCpuProtV11v0Group,
           tmnxSapDcpNotifyObjsV11v0Group,
           tmnxSapDcpNotifyV11v0Group,
           tmnxSapDefHostV14v0Group,
           tmnxSapDefHostV9v0Group,
           tmnxSapDhcpV11v0Group,
           tmnxSapDhcpV13v0Group,
           tmnxSapDhcpV8v0Group,
           tmnxSapDiamNasreqGroup,
           tmnxSapDnGroup,
           tmnxSapEgrEncapGrpV13v0Group,
           tmnxSapEgrPortQGrpV11v0Group,
           tmnxSapEgrQosStatsGroup,
           tmnxSapEthCfmGroup,
-- EXCLUDE tmnxSapEthCfmMonitorGroup
           tmnxSapEthCfmV12v0Group,
           tmnxSapEthLoopbackV11v0Group,
           tmnxSapEthLpbkNotifyV11v0Group,
           tmnxSapEthRingGroup,
           tmnxSapFPropBMacV8v0Group,
-- EXCLUDE tmnxSapFilterProfileV9v0Group
           tmnxSapFlowSPecV11v0Group,
           tmnxSapFrGroupV8v0,
           tmnxSapGreObsoletedGroup,
           tmnxSapGreV11v0Group,
-- EXCLUDE tmnxSapHsmdaV10v0Group
-- EXCLUDE tmnxSapHsmdaV9v0Group
           tmnxSapIgmpTrkGroup,
           tmnxSapIgmpTrkV11v0Group,
           tmnxSapIgmpTrkV8v0Group,
           tmnxSapInfoV14v0Group,
           tmnxSapIpTnlGroup,
           tmnxSapIpV6FilterV14v0Group,
           tmnxSapIpipeFaultPropGroup,
           tmnxSapIpipeNotificationGroup,
           tmnxSapIpipeV8v0Group,
           tmnxSapIpoeV13v0Group,
           tmnxSapL2ptV6v0Group,
           tmnxSapL2tpv3V14v0Group,
           tmnxSapLagV11v0Group,
           tmnxSapMonitorIPGroup,
           tmnxSapMrpV8v0Group,
           tmnxSapMsapV11v0Group,
           tmnxSapMsapV12v0Group,
           tmnxSapMsapV14v0Group,
           tmnxSapMsapV6v1Group,
           tmnxSapMsapV8v0Group,
           tmnxSapMsapV9v0Group,
           tmnxSapMstiV6v0Group,
           tmnxSapMvrpNotificationV8v0Group,
           tmnxSapMvrpV13v0Group,
           tmnxSapNotifObsoletedGroup,
           tmnxSapNotificationV10v0Group,
           tmnxSapNotificationV11v0Group,
           tmnxSapNotificationV13v0Group,
           tmnxSapNotificationV9v0Group,
           tmnxSapNotifyGroup,
           tmnxSapOverrideV8v0Group,
           tmnxSapOverrideV9v0Group,
           tmnxSapPbbGroup,
           tmnxSapPbbV12v0Group,
-- EXCLUDE tmnxSapPlcrV8v0Group
           tmnxSapPlcrV9v0Group,
           tmnxSapPortIdV6v0Group,
           tmnxSapQosRateV13v0Group,
           tmnxSapQosSchedV13v0Group,
           tmnxSapQosStatsGroup,
           tmnxSapQosV12v0Group,
           tmnxSapQosV14v0Group,
           tmnxSapQueueOvrV13v0Group,
           tmnxSapRadiusFallbackGroup,
           tmnxSapRipNotifyGroup,
           tmnxSapSchedulerRateV11v0Group,
           tmnxSapShcvPolicyGroup,
           tmnxSapSpbGroup,
           tmnxSapSpbV11v0Group,
           tmnxSapStatHost6Group,
           tmnxSapStatHost6V13v0Group,
           tmnxSapStaticHostRipV13v0Group,
           tmnxSapStaticHostV11v0Group,
           tmnxSapStaticHostV9v0Group,
           tmnxSapStatsV10v0Group,
           tmnxSapStickyMsapGroup,
           tmnxSapSubMgmtV9v0Group,
           tmnxSapTlsPbbV14v0Group,
           tmnxSapTlsV12v0Group,
           tmnxSapTlsV7v0Group,
           tmnxSapTlsV8v0Group,
           tmnxSapV11v0Group,
           tmnxSapV14v0Group,
           tmnxSapV9v0Group,
           tmnxSapVplsV14v0Group,
           tmnxSapVprnLoopbackV14v0Group,
           tmnxTlsMsapPppoeV6v0Group
        }

        VARIATION   bridgedTLS
            ACCESS  not-implemented
            DESCRIPTION
                 "bridgedTLS is not implemented on Nokia 7710 in release 14.0."

        VARIATION   msapPlcySubMgmtDefFilterProfile
            ACCESS  not-implemented
            DESCRIPTION
                 "msapPlcySubMgmtDefFilterProfile is not implemented on Nokia
                  7710 in release 14.0."

        VARIATION   sapAntiSpoofing
            SYNTAX  INTEGER {
                       disabled             (0),
                       sourceIpAddr         (1),
                       sourceMacAddr        (2),
                       sourceIpAndMacAddr   (3)
                    -- nextHopIpAndMacAddr  (4)
                    }
            DESCRIPTION
                 "sapAntiSpoofing does not support the value
                  'nextHopIpAndMacAddr (4)' on Nokia 7710."

        VARIATION   sapCflowd
            DESCRIPTION
                 "sapCflowd is not accessible on cards that do not have SMP
                  processors."

        VARIATION   sapCpmProtMonitorIP
            DESCRIPTION
                 "sapCpmProtMonitorIP is supported on 7750 SR-7, 7750 SR-12,
                  7450 ESS-6, 7450 ESS-7, and 7450 ESS-12 only."

        VARIATION   sapCreated
            ACCESS  not-implemented
            DESCRIPTION
                 "sapCreated is not implemented on Nokia 7710 in release 14.0.

                  This NOTIFICATION-TYPE is replaced with the
                  TIMETRA-SYSTEM-MIB.tmnxConfigModify notification"

        VARIATION   sapDeleted
            ACCESS  not-implemented
            DESCRIPTION
                 "sapDeleted is not implemented on Nokia 7710 in release 14.0.

                  This NOTIFICATION-TYPE is replaced with the
                  TIMETRA-SYSTEM-MIB.tmnxConfigModify notification"

        VARIATION   sapEgrPolicerPolicy
            ACCESS  not-implemented
            DESCRIPTION
                 "sapEgrPolicerPolicy is not implemented on Nokia 7710 in
                  release 14.0."

        VARIATION   sapEthLoopbackEntry
            CREATION-REQUIRES {
                       sapEthLoopbackRowStatus,
                       sapEthLoopbackMode
                    }
            DESCRIPTION
                 "Objects sapEthLoopbackRowStatus and sapEthLoopbackMode must be
                  set for row creation to succeed."

        VARIATION   sapEthLoopbackRowStatus
            SYNTAX  RowStatus {
                       active               (1),
                    -- notInService         (2)
                    -- notReady             (3)
                       createAndGo          (4),
                    -- createAndWait        (5)
                       destroy              (6)
                    }
            DESCRIPTION
                 "sapEthLoopbackRowStatus supports only 'active (1)',
                  'createAndGo (4)', and 'destroy (6)'."

        VARIATION   sapFPropBMacAddrRowStatus
            SYNTAX  RowStatus {
                       active               (1),
                    -- notInService         (2)
                    -- notReady             (3)
                       createAndGo          (4),
                    -- createAndWait        (5)
                       destroy              (6)
                    }
            DESCRIPTION
                 "sapFPropBMacAddrRowStatus supports only 'active (1)',
                  'createAndGo (4)', and 'destroy (6)'.

                  At most four rows with the same <svcId, sapPortId,
                  sapEncapValue> index triple are allowed."

        VARIATION   sapIngPolicerPolicy
            ACCESS  not-implemented
            DESCRIPTION
                 "sapIngPolicerPolicy is not implemented on Nokia 7710 in
                  release 14.0."

        VARIATION   sapReceiveOwnBpdu
            ACCESS  not-implemented
            DESCRIPTION
                 "sapReceiveOwnBpdu is not implemented on Nokia 7710 in release
                  14.0."

        VARIATION   sapStaticHostFilterProfile
            ACCESS  not-implemented
            DESCRIPTION
                 "sapStaticHostFilterProfile is not implemented on Nokia 7710 in
                  release 14.0."

        VARIATION   sapStaticHostMRtRowStatus
            SYNTAX  RowStatus {
                       active               (1),
                    -- notInService         (2)
                    -- notReady             (3)
                       createAndGo          (4),
                    -- createAndWait        (5)
                       destroy              (6)
                    }
            DESCRIPTION
                 "sapStaticHostMRtRowStatus supports only 'active (1)',
                  'createAndGo (4)', and 'destroy (6)'."

        VARIATION   sapSubMgmtDefFilterProfile
            ACCESS  not-implemented
            DESCRIPTION
                 "sapSubMgmtDefFilterProfile is not implemented on Nokia 7710 in
                  release 14.0."

        VARIATION   sapTlsStpBpduEncap
            SYNTAX  INTEGER {
                       dynamic              (1)
                    }
            DESCRIPTION
                 "The only value that can be assigned to sapTlsStpBpduEncap is
                  'dynamic (1)'. Additional values may be supported in a later
                  release."

        VARIATION   sapTmplTlsStpBpduEncap
            SYNTAX  INTEGER {
                       dynamic              (1)
                    }
            DESCRIPTION
                 "The only value that can be assigned to sapTmplTlsStpBpduEncap
                  is 'dynamic (1)'. Additional values may be supported in a
                  later release."

    ::= { tmnx7710AgentV14v0  64 }

--
-- 7950 SAP CAPABILITIES
--
tmnx7950SapV14v0                  AGENT-CAPABILITIES
    PRODUCT-RELEASE "Nokia SROS"
    STATUS          current
    DESCRIPTION
         "Implementation of SAP capabilities for Nokia 7950 systems release
          14.0."

    SUPPORTS        TIMETRA-SAP-MIB
        INCLUDES {
           sapBgpEvpnMplsMhGroup,
           sapEthLoopbackV14v0Group,
           sapL3LoopbackNotifGroup,
           sapLagV12v0Group,
           sapTlsEtreeGroup,
           sapTlsFdbMacStatsGroup,
           sapV14v0NotifyObjsGroup,
           tmnxEvpnMplsMacMovNotifGroup,
           tmnxIPTunnelGreKeyV12v0Group,
           tmnxIpTnlOperChgGroup,
           tmnxIpTunnelEncaNotifyObjsGroup,
           tmnxIpTunnelEncapNotifyGroup,
           tmnxIpTunnelFragStatV12v0Group,
           tmnxIpTunnelV12v0Group,
           tmnxMsapPlcyCpmProtV12v0Group,
           tmnxMsapQosV12v0Group,
           tmnxSapArpHostGroup,
-- EXCLUDE tmnxSapAtmV6v0Group
-- EXCLUDE tmnxSapAtmV9v0Group
           tmnxSapBaseStatsV13v0Group,
           tmnxSapBaseV6v0Group,
           tmnxSapBgpEvpnAlmpGroup,
-- EXCLUDE tmnxSapBsxV10v0Group
-- EXCLUDE tmnxSapBsxV7v0Group
-- EXCLUDE tmnxSapBsxV9v0Group
           tmnxSapCemNotificationV6v0Group,
           tmnxSapCemV6v0Group,
           tmnxSapCflowdGroupV11v0,
           tmnxSapDCpuProtV11v0Group,
           tmnxSapDcpNotifyObjsV11v0Group,
           tmnxSapDcpNotifyV11v0Group,
           tmnxSapDefHostV14v0Group,
           tmnxSapDefHostV9v0Group,
           tmnxSapDhcpV11v0Group,
           tmnxSapDhcpV13v0Group,
           tmnxSapDhcpV8v0Group,
           tmnxSapDiamNasreqGroup,
           tmnxSapDnGroup,
           tmnxSapEgrEncapGrpV13v0Group,
           tmnxSapEgrPortQGrpV11v0Group,
           tmnxSapEgrQosStatsGroup,
           tmnxSapEthCfmGroup,
           tmnxSapEthCfmMonitorGroup,
           tmnxSapEthCfmV12v0Group,
           tmnxSapEthLoopbackV11v0Group,
           tmnxSapEthLpbkNotifyV11v0Group,
           tmnxSapEthRingGroup,
           tmnxSapFPropBMacV8v0Group,
-- EXCLUDE tmnxSapFilterProfileV9v0Group
           tmnxSapFlowSPecV11v0Group,
           tmnxSapFrGroupV8v0,
           tmnxSapGreObsoletedGroup,
           tmnxSapGreV11v0Group,
-- EXCLUDE tmnxSapHsmdaV10v0Group
-- EXCLUDE tmnxSapHsmdaV9v0Group
           tmnxSapIgmpTrkGroup,
           tmnxSapIgmpTrkV11v0Group,
           tmnxSapIgmpTrkV8v0Group,
           tmnxSapInfoV14v0Group,
           tmnxSapIpTnlGroup,
           tmnxSapIpV6FilterV14v0Group,
           tmnxSapIpipeFaultPropGroup,
           tmnxSapIpipeNotificationGroup,
           tmnxSapIpipeV8v0Group,
           tmnxSapIpoeV13v0Group,
           tmnxSapL2ptV6v0Group,
           tmnxSapL2tpv3V14v0Group,
           tmnxSapLagV11v0Group,
           tmnxSapMonitorIPGroup,
           tmnxSapMrpV8v0Group,
           tmnxSapMsapV11v0Group,
           tmnxSapMsapV12v0Group,
           tmnxSapMsapV14v0Group,
           tmnxSapMsapV6v1Group,
           tmnxSapMsapV8v0Group,
           tmnxSapMsapV9v0Group,
           tmnxSapMstiV6v0Group,
           tmnxSapMvrpNotificationV8v0Group,
           tmnxSapMvrpV13v0Group,
           tmnxSapNotifObsoletedGroup,
           tmnxSapNotificationV10v0Group,
           tmnxSapNotificationV11v0Group,
           tmnxSapNotificationV13v0Group,
           tmnxSapNotificationV9v0Group,
           tmnxSapNotifyGroup,
           tmnxSapOverrideV8v0Group,
           tmnxSapOverrideV9v0Group,
           tmnxSapPbbGroup,
           tmnxSapPbbV12v0Group,
           tmnxSapPlcrV8v0Group,
           tmnxSapPlcrV9v0Group,
           tmnxSapPortIdV6v0Group,
           tmnxSapQosRateV13v0Group,
           tmnxSapQosSchedV13v0Group,
           tmnxSapQosStatsGroup,
           tmnxSapQosV12v0Group,
           tmnxSapQosV14v0Group,
           tmnxSapQueueOvrV13v0Group,
           tmnxSapRadiusFallbackGroup,
           tmnxSapRipNotifyGroup,
           tmnxSapSchedulerRateV11v0Group,
           tmnxSapShcvPolicyGroup,
           tmnxSapSpbGroup,
           tmnxSapSpbV11v0Group,
           tmnxSapStatHost6Group,
           tmnxSapStatHost6V13v0Group,
           tmnxSapStaticHostRipV13v0Group,
           tmnxSapStaticHostV11v0Group,
           tmnxSapStaticHostV9v0Group,
           tmnxSapStatsV10v0Group,
           tmnxSapStickyMsapGroup,
           tmnxSapSubMgmtV9v0Group,
           tmnxSapTlsPbbV14v0Group,
           tmnxSapTlsV12v0Group,
           tmnxSapTlsV7v0Group,
           tmnxSapTlsV8v0Group,
           tmnxSapV11v0Group,
           tmnxSapV14v0Group,
           tmnxSapV9v0Group,
           tmnxSapVplsV14v0Group,
           tmnxSapVprnLoopbackV14v0Group,
           tmnxTlsMsapPppoeV6v0Group
        }

        VARIATION   bridgedTLS
            ACCESS  not-implemented
            DESCRIPTION
                 "bridgedTLS is not implemented on Nokia 7950 in release 14.0."

        VARIATION   msapPlcySubMgmtDefFilterProfile
            ACCESS  not-implemented
            DESCRIPTION
                 "msapPlcySubMgmtDefFilterProfile is not implemented on Nokia
                  7950 in release 14.0."

        VARIATION   sapCflowd
            DESCRIPTION
                 "sapCflowd is not accessible on cards that do not have SMP
                  processors."

        VARIATION   sapCpmProtMonitorIP
            DESCRIPTION
                 "sapCpmProtMonitorIP is supported on 7750 SR-7, 7750 SR-12,
                  7450 ESS-6, 7450 ESS-7, and 7450 ESS-12 only."

        VARIATION   sapCreated
            ACCESS  not-implemented
            DESCRIPTION
                 "sapCreated is not implemented on Nokia 7950 in release 14.0.

                  This NOTIFICATION-TYPE is replaced with the
                  TIMETRA-SYSTEM-MIB.tmnxConfigModify notification"

        VARIATION   sapDeleted
            ACCESS  not-implemented
            DESCRIPTION
                 "sapDeleted is not implemented on Nokia 7950 in release 14.0.

                  This NOTIFICATION-TYPE is replaced with the
                  TIMETRA-SYSTEM-MIB.tmnxConfigModify notification"

        VARIATION   sapEthLoopbackEntry
            CREATION-REQUIRES {
                       sapEthLoopbackRowStatus,
                       sapEthLoopbackMode
                    }
            DESCRIPTION
                 "Objects sapEthLoopbackRowStatus and sapEthLoopbackMode must be
                  set for row creation to succeed."

        VARIATION   sapEthLoopbackRowStatus
            SYNTAX  RowStatus {
                       active               (1),
                    -- notInService         (2)
                    -- notReady             (3)
                       createAndGo          (4),
                    -- createAndWait        (5)
                       destroy              (6)
                    }
            DESCRIPTION
                 "sapEthLoopbackRowStatus supports only 'active (1)',
                  'createAndGo (4)', and 'destroy (6)'."

        VARIATION   sapFPropBMacAddrRowStatus
            SYNTAX  RowStatus {
                       active               (1),
                    -- notInService         (2)
                    -- notReady             (3)
                       createAndGo          (4),
                    -- createAndWait        (5)
                       destroy              (6)
                    }
            DESCRIPTION
                 "sapFPropBMacAddrRowStatus supports only 'active (1)',
                  'createAndGo (4)', and 'destroy (6)'.

                  At most four rows with the same <svcId, sapPortId,
                  sapEncapValue> index triple are allowed."

        VARIATION   sapReceiveOwnBpdu
            ACCESS  not-implemented
            DESCRIPTION
                 "sapReceiveOwnBpdu is not implemented on Nokia 7950 in release
                  14.0."

        VARIATION   sapStaticHostFilterProfile
            ACCESS  not-implemented
            DESCRIPTION
                 "sapStaticHostFilterProfile is not implemented on Nokia 7950 in
                  release 14.0."

        VARIATION   sapStaticHostMRtRowStatus
            SYNTAX  RowStatus {
                       active               (1),
                    -- notInService         (2)
                    -- notReady             (3)
                       createAndGo          (4),
                    -- createAndWait        (5)
                       destroy              (6)
                    }
            DESCRIPTION
                 "sapStaticHostMRtRowStatus supports only 'active (1)',
                  'createAndGo (4)', and 'destroy (6)'."

        VARIATION   sapSubMgmtDefFilterProfile
            ACCESS  not-implemented
            DESCRIPTION
                 "sapSubMgmtDefFilterProfile is not implemented on Nokia 7950 in
                  release 14.0."

        VARIATION   sapTlsRestProtSrcMacAction
            SYNTAX  INTEGER {
                       disabled             (1),
                    -- alarm-only           (2)
                       discardFrame         (3)
                    }
            DESCRIPTION
                 "sapTlsRestProtSrcMacAction does not support 'alarm-only' on
                  Nokia 7950."

        VARIATION   sapTlsStpBpduEncap
            SYNTAX  INTEGER {
                       dynamic              (1)
                    }
            DESCRIPTION
                 "The only value that can be assigned to sapTlsStpBpduEncap is
                  'dynamic (1)'. Additional values may be supported in a later
                  release."

        VARIATION   sapTmplTlsStpBpduEncap
            SYNTAX  INTEGER {
                       dynamic              (1)
                    }
            DESCRIPTION
                 "The only value that can be assigned to sapTmplTlsStpBpduEncap
                  is 'dynamic (1)'. Additional values may be supported in a
                  later release."

    ::= { tmnx7950AgentV14v0  64 }

--
-- SROS SATELLITE CAPABILITIES
--
tmnxSROSSatelliteV14v0            AGENT-CAPABILITIES
    PRODUCT-RELEASE "Nokia SROS"
    STATUS          current
    DESCRIPTION
         "Implementation of satellite capabilities for Nokia SROS systems
          release 14.0."

    SUPPORTS        TIMETRA-SATELLITE-MIB
        INCLUDES {
           tmnxSatelliteGroupV14v0,
           tmnxSatelliteNotifGroupV14v0,
           tmnxSatelliteNotifyObjsGrpV14v0,
           tmnxSatellitePortMapGroupV14v0,
           tmnxSatelliteSyncIfTimGroupV14v0,
           tmnxSatelliteTypeGroupV14v0
        }

        VARIATION   tmnxSatRowStatus
            SYNTAX  RowStatus {
                       active               (1),
                    -- notInService         (2)
                    -- notReady             (3)
                       createAndGo          (4),
                    -- createAndWait        (5)
                       destroy              (6)
                    }
            DESCRIPTION
                 "tmnxSatRowStatus supports only 'active (1)', 'createAndGo
                  (4)', and 'destroy (6)'."

    ::= { tmnxSROSAgentV14v0  38 }

--
-- SROS SCHEDULER CAPABILITIES
--
tmnxSROSSchedulerV14v0            AGENT-CAPABILITIES
    PRODUCT-RELEASE "Nokia SROS"
    STATUS          current
    DESCRIPTION
         "Implementation of CRON schedulers for Nokia SROS systems release
          14.0."

    SUPPORTS        TIMETRA-SCHEDULER-MIB
        INCLUDES {
           tmnxCronSchedV5v0Group
        }

    ::= { tmnxSROSAgentV14v0  49 }

--
-- SROS SDP CAPABILITIES
--
tmnxSROSSdpV14v0                  AGENT-CAPABILITIES
    PRODUCT-RELEASE "Nokia SROS"
    STATUS          current
    DESCRIPTION
         "Implementation of SDP capabilities for Nokia SROS systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
           tmnxSdpBindCpipeV6v0Group,
-- EXCLUDE tmnxSdpBindCpmProtGroup
           tmnxSdpBindCpmProtV12v0Group,
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia SROS in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia SROS in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - satopE3 (14), - satopT3 (15) are not supported
                  on Nokia SROS, as they are not implemented."

        VARIATION   sdpCreated
            ACCESS  not-implemented
            DESCRIPTION
                 "sdpCreated is not implemented on Nokia SROS in release 14.0.

                  This NOTIFICATION-TYPE is replaced with the
                  TIMETRA-SYSTEM-MIB.tmnxConfigModify notification."

        VARIATION   sdpDeleted
            ACCESS  not-implemented
            DESCRIPTION
                 "sdpDeleted is not implemented on Nokia SROS in release 14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia SROS in
                  release 14.0."

    ::= { tmnxSROSAgentV14v0  65 }

--
-- 7750 SDP CAPABILITIES
--
tmnx7750SdpV14v0                  AGENT-CAPABILITIES
    PRODUCT-RELEASE "Nokia SROS"
    STATUS          current
    DESCRIPTION
         "Implementation of SDP capabilities for Nokia 7750 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
           tmnxSdpBindCpipeV6v0Group,
           tmnxSdpBindCpmProtGroup,
           tmnxSdpBindCpmProtV12v0Group,
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia 7750 in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7750 in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - satopE3 (14), - satopT3 (15) are not supported
                  on Nokia 7750, as they are not implemented."

        VARIATION   sdpCreated
            ACCESS  not-implemented
            DESCRIPTION
                 "sdpCreated is not implemented on Nokia 7750 in release 14.0.

                  This NOTIFICATION-TYPE is replaced with the
                  TIMETRA-SYSTEM-MIB.tmnxConfigModify notification."

        VARIATION   sdpDeleted
            ACCESS  not-implemented
            DESCRIPTION
                 "sdpDeleted is not implemented on Nokia 7750 in release 14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7750 in
                  release 14.0."

    ::= { tmnx7750AgentV14v0  65 }

--
-- 7750SR-1 SDP CAPABILITIES
--
tmnx7750SR1SdpV14v0               AGENT-CAPABILITIES
    PRODUCT-RELEASE "Nokia SROS"
    STATUS          current
    DESCRIPTION
         "Implementation of SDP capabilities for Nokia 7750 SR-1 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
           tmnxSdpBindCpipeV6v0Group,
           tmnxSdpBindCpmProtGroup,
           tmnxSdpBindCpmProtV12v0Group,
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCpmProtEthCfmMonitorFlags
            ACCESS  not-implemented
            DESCRIPTION
                 "sdpBindCpmProtEthCfmMonitorFlags is not implemented on Nokia
                  7750 SR-1 in release 14.0."

        VARIATION   sdpBindCpmProtMonitorMac
            ACCESS  not-implemented
            DESCRIPTION
                 "sdpBindCpmProtMonitorMac is not implemented on Nokia 7750 SR-1
                  in release 14.0."

        VARIATION   sdpBindCpmProtPolicyId
            ACCESS  not-implemented
            DESCRIPTION
                 "sdpBindCpmProtPolicyId is not implemented on Nokia 7750 SR-1
                  in release 14.0."

        VARIATION   sdpBindCreated
            ACCESS  not-implemented
            DESCRIPTION
                 "sdpBindCreated is not implemented on Nokia 7750 SR-1 in
                  release 14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7750 SR-1 in
                  release 14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - satopE3 (14), - satopT3 (15) are not supported
                  on Nokia 7750 SR-1, as they are not implemented."

        VARIATION   sdpCreated
            ACCESS  not-implemented
            DESCRIPTION
                 "sdpCreated is not implemented on Nokia 7750 SR-1 in release
                  14.0.

                  This NOTIFICATION-TYPE is replaced with the
                  TIMETRA-SYSTEM-MIB.tmnxConfigModify notification."

        VARIATION   sdpDeleted
            ACCESS  not-implemented
            DESCRIPTION
                 "sdpDeleted is not implemented on Nokia 7750 SR-1 in release
                  14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7750
                  SR-1 in release 14.0."

    ::= { tmnx7750SR1AgentV14v0  65 }

--
-- 7750c12 SDP CAPABILITIES
--
tmnx7750c12SdpV14v0               AGENT-CAPABILITIES
    PRODUCT-RELEASE "Nokia SROS"
    STATUS          current
    DESCRIPTION
         "Implementation of SDP capabilities for Nokia 7750 c12 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
           tmnxSdpBindCpipeV6v0Group,
           tmnxSdpBindCpmProtGroup,
-- EXCLUDE tmnxSdpBindCpmProtV12v0Group
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia 7750 c12 in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7750 c12 in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - satopE3 (14), - satopT3 (15) are not supported
                  on Nokia 7750 c12, as they are not implemented."

        VARIATION   sdpCreated
            ACCESS  not-implemented
            DESCRIPTION
                 "sdpCreated is not implemented on Nokia 7750 c12 in release
                  14.0.

                  This NOTIFICATION-TYPE is replaced with the
                  TIMETRA-SYSTEM-MIB.tmnxConfigModify notification."

        VARIATION   sdpDeleted
            ACCESS  not-implemented
            DESCRIPTION
                 "sdpDeleted is not implemented on Nokia 7750 c12 in release
                  14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7750
                  c12 in release 14.0."

    ::= { tmnx7750c12AgentV14v0  65 }

--
-- 7750c4 SDP CAPABILITIES
--
tmnx7750c4SdpV14v0                AGENT-CAPABILITIES
    PRODUCT-RELEASE "Nokia SROS"
    STATUS          current
    DESCRIPTION
         "Implementation of SDP capabilities for Nokia 7750 c4 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
           tmnxSdpBindCpipeV6v0Group,
           tmnxSdpBindCpmProtGroup,
-- EXCLUDE tmnxSdpBindCpmProtV12v0Group
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia 7750 c4 in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7750 c4 in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - satopE3 (14), - satopT3 (15) are not supported
                  on Nokia 7750 c4, as they are not implemented."

        VARIATION   sdpCreated
            ACCESS  not-implemented
            DESCRIPTION
                 "sdpCreated is not implemented on Nokia 7750 c4 in release
                  14.0.

                  This NOTIFICATION-TYPE is replaced with the
                  TIMETRA-SYSTEM-MIB.tmnxConfigModify notification."

        VARIATION   sdpDeleted
            ACCESS  not-implemented
            DESCRIPTION
                 "sdpDeleted is not implemented on Nokia 7750 c4 in release
                  14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7750 c4
                  in release 14.0."

    ::= { tmnx7750c4AgentV14v0  65 }

--
-- 7450 SDP CAPABILITIES
--
tmnx7450SdpV14v0                  AGENT-CAPABILITIES
    PRODUCT-RELEASE "Nokia SROS"
    STATUS          current
    DESCRIPTION
         "Implementation of SDP capabilities for Nokia 7450 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
-- EXCLUDE tmnxSdpBindCpipeV6v0Group
           tmnxSdpBindCpmProtGroup,
           tmnxSdpBindCpmProtV12v0Group,
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia 7450 in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7450 in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11)
                    -- satopE1              (12)
                    -- satopT1              (13)
                    -- satopE3              (14)
                    -- satopT3              (15)
                    -- cesopsn              (16)
                    -- cesopsnCas           (17)
                    }
            DESCRIPTION
                 "The enumeration 'vpls (3)' is no longer supported. The values
                  - 'satopE1 (12)', - 'satopT1 (13)', - 'satopE3 (14)', -
                  'satopT3 (15)', - 'cesopsn (16)', - 'cesopsnCas (17)' are not
                  supported on Nokia 7450, because CEM is not implemented."

        VARIATION   sdpCreated
            ACCESS  not-implemented
            DESCRIPTION
                 "sdpCreated is not implemented on Nokia 7450 in release 14.0.

                  This NOTIFICATION-TYPE is replaced with the
                  TIMETRA-SYSTEM-MIB.tmnxConfigModify notification."

        VARIATION   sdpDeleted
            ACCESS  not-implemented
            DESCRIPTION
                 "sdpDeleted is not implemented on Nokia 7450 in release 14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7450 in
                  release 14.0."

    ::= { tmnx7450AgentV14v0  65 }

--
-- 7450ESS-1 SDP CAPABILITIES
--
tmnx7450ESS1SdpV14v0              AGENT-CAPABILITIES
    PRODUCT-RELEASE "Nokia SROS"
    STATUS          current
    DESCRIPTION
         "Implementation of SDP capabilities for Nokia 7450 ESS-1 systems
          release 14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
           tmnxSdpBindBsxV10v0Group,
           tmnxSdpBindBsxV9v0Group,
-- EXCLUDE tmnxSdpBindCpipeV6v0Group
           tmnxSdpBindCpmProtGroup,
           tmnxSdpBindCpmProtV12v0Group,
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCpmProtEthCfmMonitorFlags
            ACCESS  not-implemented
            DESCRIPTION
                 "sdpBindCpmProtEthCfmMonitorFlags is not implemented on Nokia
                  7450 ESS-1 in release 14.0."

        VARIATION   sdpBindCpmProtMonitorMac
            ACCESS  not-implemented
            DESCRIPTION
                 "sdpBindCpmProtMonitorMac is not implemented on Nokia 7450
                  ESS-1 in release 14.0."

        VARIATION   sdpBindCpmProtPolicyId
            ACCESS  not-implemented
            DESCRIPTION
                 "sdpBindCpmProtPolicyId is not implemented on Nokia 7450 ESS-1
                  in release 14.0."

        VARIATION   sdpBindCreated
            ACCESS  not-implemented
            DESCRIPTION
                 "sdpBindCreated is not implemented on Nokia 7450 ESS-1 in
                  release 14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7450 ESS-1 in
                  release 14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11)
                    -- satopE1              (12)
                    -- satopT1              (13)
                    -- satopE3              (14)
                    -- satopT3              (15)
                    -- cesopsn              (16)
                    -- cesopsnCas           (17)
                    }
            DESCRIPTION
                 "The enumeration 'vpls (3)' is no longer supported. The values
                  - 'satopE1 (12)', - 'satopT1 (13)', - 'satopE3 (14)', -
                  'satopT3 (15)', - 'cesopsn (16)', - 'cesopsnCas (17)' are not
                  supported on Nokia 7450 ESS-1, because CEM is not
                  implemented."

        VARIATION   sdpCreated
            ACCESS  not-implemented
            DESCRIPTION
                 "sdpCreated is not implemented on Nokia 7450 ESS-1 in release
                  14.0.

                  This NOTIFICATION-TYPE is replaced with the
                  TIMETRA-SYSTEM-MIB.tmnxConfigModify notification."

        VARIATION   sdpDeleted
            ACCESS  not-implemented
            DESCRIPTION
                 "sdpDeleted is not implemented on Nokia 7450 ESS-1 in release
                  14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7450
                  ESS-1 in release 14.0."

    ::= { tmnx7450ESS1AgentV14v0  65 }

--
-- 7710 SDP CAPABILITIES
--
tmnx7710SdpV14v0                  AGENT-CAPABILITIES
    PRODUCT-RELEASE "Nokia SROS"
    STATUS          current
    DESCRIPTION
         "Implementation of SDP capabilities for Nokia 7710 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
           tmnxSdpApipeV6v0Group,
           tmnxSdpAutoBindV7v0Group,
           tmnxSdpAutoBindV8v0Group,
           tmnxSdpBfdV12v0Group,
           tmnxSdpBgpVplsV8v0Group,
           tmnxSdpBindBlockOnPeerFaultGroup,
-- EXCLUDE tmnxSdpBindBsxV10v0Group
-- EXCLUDE tmnxSdpBindBsxV9v0Group
           tmnxSdpBindCpipeV6v0Group,
-- EXCLUDE tmnxSdpBindCpmProtGroup
-- EXCLUDE tmnxSdpBindCpmProtV12v0Group
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia 7710 in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7710 in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                       atmSdu               (6),
                       atmCell              (7),
                       atmVcc               (8),
                       atmVpc               (9),
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - satopE3 (14), - satopT3 (15) are not supported
                  on Nokia 7710, as they are not implemented."

        VARIATION   sdpCreated
            ACCESS  not-implemented
            DESCRIPTION
                 "sdpCreated is not implemented on Nokia 7710 in release 14.0.

                  This NOTIFICATION-TYPE is replaced with the
                  TIMETRA-SYSTEM-MIB.tmnxConfigModify notification."

        VARIATION   sdpDeleted
            ACCESS  not-implemented
            DESCRIPTION
                 "sdpDeleted is not implemented on Nokia 7710 in release 14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7710 in
                  release 14.0."

    ::= { tmnx7710AgentV14v0  65 }

--
-- 7950 SDP CAPABILITIES
--
tmnx7950SdpV14v0                  AGENT-CAPABILITIES
    PRODUCT-RELEASE "Nokia SROS"
    STATUS          current
    DESCRIPTION
         "Implementation of SDP capabilities for Nokia 7950 systems release
          14.0."

    SUPPORTS        TIMETRA-SDP-MIB
        INCLUDES {
           sdpBgpEvpnMplsMhGroup,
           sdpBindBgpEvpnAlmpGroup,
           sdpBindTlsEtreeGroup,
           sdpBindTlsFdbMacStatsGroup,
           sdpBindV14v0Group,
           sdpFpeV14v0Group,
           sdpGreExtGroup,
           sdpPwStaticLabelGroup,
           svcPwTmplExt14v0Group,
           tmnxPwTemplateAugGroup,
-- EXCLUDE tmnxSdpApipeV6v0Group
           tmnxSdpAutoBindV7v0Group,
           tmnxSdpAutoBindV8v0Group,
           tmnxSdpBfdV12v0Group,
           tmnxSdpBgpVplsV8v0Group,
           tmnxSdpBindBlockOnPeerFaultGroup,
-- EXCLUDE tmnxSdpBindBsxV10v0Group
-- EXCLUDE tmnxSdpBindBsxV9v0Group
           tmnxSdpBindCpipeV6v0Group,
-- EXCLUDE tmnxSdpBindCpmProtGroup
           tmnxSdpBindCpmProtV12v0Group,
           tmnxSdpBindCtrlChanAckGroup,
           tmnxSdpBindCtrlChanGroup,
           tmnxSdpBindCtrlChanReqGroup,
           tmnxSdpBindDhcpV11v0Group,
           tmnxSdpBindDhcpV13v0Group,
           tmnxSdpBindDhcpV6v0Group,
           tmnxSdpBindEthCfmGroup,
           tmnxSdpBindEthCfmV12v0Group,
           tmnxSdpBindEthLoopbackV11v0Group,
           tmnxSdpBindEthLpbkNtfyV11v0Group,
           tmnxSdpBindFlowSpecGroup,
           tmnxSdpBindGenGroup,
           tmnxSdpBindIpipeNotifyGroup,
           tmnxSdpBindIpipeV8v0Group,
           tmnxSdpBindMeshV6v0Group,
           tmnxSdpBindObsoletedV13v0Group,
           tmnxSdpBindPwPortGroup,
           tmnxSdpBindQGrpObjsV10v0Group,
           tmnxSdpBindSpbV11v0Group,
           tmnxSdpBindTlsL2ptV6v0Group,
           tmnxSdpBindTlsMrpV8v0Group,
           tmnxSdpBindTlsV6v0Group,
           tmnxSdpBindTlsV8v0Group,
           tmnxSdpBindV11v0Group,
           tmnxSdpBindV14v0Group,
           tmnxSdpBindV6v0Group,
           tmnxSdpBindV8v0Group,
           tmnxSdpBindV9v0Group,
           tmnxSdpCtrlPwNotifV12v0Group,
           tmnxSdpEvalPwTempV7v0Group,
           tmnxSdpFCV6v0Group,
           tmnxSdpGrpGroup,
           tmnxSdpL2V6v0Group,
           tmnxSdpL2V7v0Group,
           tmnxSdpL2V8v0Group,
           tmnxSdpL2tpv3CookieGroup,
           tmnxSdpL2tpv3Group,
           tmnxSdpLdpIpv6Group,
           tmnxSdpMixedLspModeV9v0Group,
           tmnxSdpNotifyObjsV8v0Group,
           tmnxSdpNotifyV10v0Group,
           tmnxSdpNotifyV11v0Group,
           tmnxSdpNotifyV6v0Group,
           tmnxSdpNotifyV8v0Group,
           tmnxSdpPBBEpipePWRedV12v0Group,
           tmnxSdpPbbEpipeNotifV12v0Group,
           tmnxSdpPbbEpipeNotifyObjsGroup,
           tmnxSdpPbbGroup,
           tmnxSdpPbbV12v0Group,
           tmnxSdpPwLoopbackGroup,
           tmnxSdpPwPortOperGrpGroup,
           tmnxSdpPwPortV11v0Group,
           tmnxSdpPwSecShaperGroup,
           tmnxSdpPwTempBindV12v0Group,
           tmnxSdpPwV8v0Group,
           tmnxSdpSegRouteGroup,
           tmnxSdpSegRouteTeGroup,
           tmnxSdpSpbGroup,
           tmnxSdpTlsBgpV6v0Group,
           tmnxSdpV10v0Group,
           tmnxSdpV13v0Group,
           tmnxSdpV9v0Group,
           tmnxSdpVllBgpV11v0Group
        }

        VARIATION   pwTemplateMfibMdaRowStatus
            SYNTAX  RowStatus {
                       active               (1),
                    -- notInService         (2)
                    -- notReady             (3)
                       createAndGo          (4),
                    -- createAndWait        (5)
                       destroy              (6)
                    }
            DESCRIPTION
                 "pwTemplateMfibMdaRowStatus supports only 'active (1)',
                  'createAndGo (4)', and 'destroy (6)'."

        VARIATION   sdpBindCreated
            ACCESS  not-implemented
            DESCRIPTION
                 "sdpBindCreated is not implemented on Nokia 7950 in release
                  14.0.

                  This NOTIFICATION-TYPE is replaced with the
                  TIMETRA-SYSTEM-MIB.tmnxConfigModify notification."

        VARIATION   sdpBindDeleted
            ACCESS  not-implemented
            DESCRIPTION
                 "sdpBindDeleted is not implemented on Nokia 7950 in release
                  14.0.

                  This NOTIFICATION-TYPE is replaced with the
                  TIMETRA-SYSTEM-MIB.tmnxConfigModify notification."

        VARIATION   sdpBindEthLoopbackEntry
            CREATION-REQUIRES {
                       sdpBindEthLoopbackRowStatus,
                       sdpBindEthLoopbackMode
                    }
            DESCRIPTION
                 "Objects sdpBindEthLoopbackRowStatus and sdpBindEthLoopbackMode
                  must be set for row creation to succeed."

        VARIATION   sdpBindEthLoopbackRowStatus
            SYNTAX  RowStatus {
                       active               (1),
                    -- notInService         (2)
                    -- notReady             (3)
                       createAndGo          (4),
                    -- createAndWait        (5)
                       destroy              (6)
                    }
            DESCRIPTION
                 "sdpBindEthLoopbackRowStatus supports only 'active (1)',
                  'createAndGo (4)', and 'destroy (6)'."

        VARIATION   sdpBindFPropBMacAddrRowStatus
            SYNTAX  RowStatus {
                       active               (1),
                    -- notInService         (2)
                    -- notReady             (3)
                       createAndGo          (4),
                    -- createAndWait        (5)
                       destroy              (6)
                    }
            DESCRIPTION
                 "sdpBindFPropBMacAddrRowStatus supports only 'active (1)',
                  'createAndGo (4)', and 'destroy (6)'.

                  At most four rows with the same <svcId, sdpBindId> index pair
                  are allowed."

        VARIATION   sdpBindIsaAaApplicationProfile
            DESCRIPTION
                 "The sdpBindIsaAaApplicationProfile object only applies to
                  spoke SDP bindings under epipe(1), tls(3), vprn(4), and ies(5)
                  services."

        VARIATION   sdpBindVcType
            SYNTAX  INTEGER {
                       undef                (1),
                       ether                (2),
                    -- vpls                 (3)
                       vlan                 (4),
                       mirror               (5),
                    -- atmSdu               (6)
                    -- atmCell              (7)
                    -- atmVcc               (8)
                    -- atmVpc               (9)
                       frDlci               (10),
                       ipipe                (11),
                       satopE1              (12),
                       satopT1              (13),
                    -- satopE3              (14)
                    -- satopT3              (15)
                       cesopsn              (16),
                       cesopsnCas           (17)
                    }
            DESCRIPTION
                 "The enumeration 'vpls (3)' is no longer supported. The
                  enumerations - atmSdu (6), - atmCell (7), - atmVcc (8), -
                  atmVpc (9), - satopE3 (14), - satopT3 (15) are not supported
                  on the SROS, as they are not implemented."

        VARIATION   sdpCreated
            ACCESS  not-implemented
            DESCRIPTION
                 "sdpCreated is not implemented on Nokia 7950 in release 14.0.

                  This NOTIFICATION-TYPE is replaced with the
                  TIMETRA-SYSTEM-MIB.tmnxConfigModify notification."

        VARIATION   sdpDeleted
            ACCESS  not-implemented
            DESCRIPTION
                 "sdpDeleted is not implemented on Nokia 7950 in release 14.0.

                  This NOTIFICATION-TYPE is replaced with the
                  TIMETRA-SYSTEM-MIB.tmnxConfigModify notification."

        VARIATION   svcVllBgpADPWTempBindEndPt
            ACCESS  not-implemented
            DESCRIPTION
                 "svcVllBgpADPWTempBindEndPt is not implemented on Nokia 7950 in
                  release 14.0."

    ::= { tmnx7950AgentV14v0  65 }

--
-- SROS SECURITY CAPABILITIES
--
tmnxSROSSecurityV14v0             AGENT-CAPABILITIES
    PRODUCT-RELEASE "Nokia SROS"
    STATUS          current
    DESCRIPTION
         "Implementation of Security capabilities for Nokia SROS systems release
          14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
           tmnxCpmProtEthCfmPolV8v0Grp,
           tmnxCpmProtExcdSapIpV9v0Group,
           tmnxCpmProtPolNotifyV8v0Grp,
           tmnxCpmProtPolNotifyV9v0Group,
           tmnxCpmProtPolV8v0Grp,
           tmnxCpmProtectionV11v0Group,
           tmnxDistCpuProtectionV11v0Group,
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
           tmnxSecCpmProtNotifyObjsV12v0Grp,
           tmnxSecCpmProtNotifyV12v0Grp,
           tmnxSecCpmProtProtocolV12v0Group,
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
           tmnxSecurityCpmIPv6FltrV11v0Grp,
           tmnxSecurityCpmIpFilterV11v0Grp,
           tmnxSecurityCpmMacFilterGroup,
           tmnxSecurityCpmProtNotificationGroup,
           tmnxSecurityCpmProtNotifyV7v0Grp,
           tmnxSecurityCpmProtV12v0Group,
           tmnxSecurityCpmProtectGroup,
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
           tmnxSecurityV7v0Group,
           tmnxSessLimNotifyV13v0Grp
        }

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolRowStatus
            SYNTAX  RowStatus {
                       active               (1),
                    -- notInService         (2)
                    -- notReady             (3)
                       createAndGo          (4),
                    -- createAndWait        (5)
                       destroy              (6)
                    }
            DESCRIPTION
                 "tmnxCpmProtEthCfmPolRowStatus supports only 'active (1)',
                  'createAndGo (4)', and 'destroy (6)'."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia SROS
                  in release 14.0.

                  verify-cert is not currently supported."

        VARIATION   tmnxPkiCAProfOcspVerifyCertFile
            ACCESS  not-implemented
            DESCRIPTION
                 "tmnxPkiCAProfOcspVerifyCertFile is not implemented on Nokia
                  SROS in release 14.0.

                  verify-cert is not currently supported."

        VARIATION   tmnxPkiCAProfOcspVerifyCertOvr
            ACCESS  not-implemented
            DESCRIPTION
                 "tmnxPkiCAProfOcspVerifyCertOvr is not implemented on Nokia
                  SROS in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnxSROSAgentV14v0  39 }

--
-- 7750SR-1 SECURITY CAPABILITIES
--
tmnx7750SR1SecurityV14v0          AGENT-CAPABILITIES
    PRODUCT-RELEASE "Nokia SROS"
    STATUS          current
    DESCRIPTION
         "Implementation of Security capabilities for Nokia 7750 SR-1 systems
          release 14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
           tmnxCpmProtEthCfmPolV8v0Grp,
           tmnxCpmProtExcdSapIpV9v0Group,
           tmnxCpmProtPolNotifyV8v0Grp,
           tmnxCpmProtPolNotifyV9v0Group,
           tmnxCpmProtPolV8v0Grp,
           tmnxCpmProtectionV11v0Group,
-- EXCLUDE tmnxDistCpuProtectionV11v0Group
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
           tmnxSecCpmProtNotifyObjsV12v0Grp,
           tmnxSecCpmProtNotifyV12v0Grp,
           tmnxSecCpmProtProtocolV12v0Group,
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
           tmnxSecurityCpmIPv6FltrV11v0Grp,
           tmnxSecurityCpmIpFilterV11v0Grp,
           tmnxSecurityCpmMacFilterGroup,
           tmnxSecurityCpmProtNotificationGroup,
           tmnxSecurityCpmProtNotifyV7v0Grp,
           tmnxSecurityCpmProtV12v0Group,
           tmnxSecurityCpmProtectGroup,
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
           tmnxSecurityV7v0Group,
           tmnxSessLimNotifyV13v0Grp
        }

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolLastChanged
            ACCESS  not-implemented
            DESCRIPTION
                 "tmnxCpmProtEthCfmPolLastChanged is not implemented on Nokia
                  7750 SR-1 in release 14.0."

        VARIATION   tmnxCpmProtEthCfmPolLevelSet
            ACCESS  not-implemented
            DESCRIPTION
                 "tmnxCpmProtEthCfmPolLevelSet is not implemented on Nokia 7750
                  SR-1 in release 14.0."

        VARIATION   tmnxCpmProtEthCfmPolOpCodeSet
            ACCESS  not-implemented
            DESCRIPTION
                 "tmnxCpmProtEthCfmPolOpCodeSet is not implemented on Nokia 7750
                  SR-1 in release 14.0."

        VARIATION   tmnxCpmProtEthCfmPolRateLimit
            ACCESS  not-implemented
            DESCRIPTION
                 "tmnxCpmProtEthCfmPolRateLimit is not implemented on Nokia 7750
                  SR-1 in release 14.0."

        VARIATION   tmnxCpmProtEthCfmPolRowStatus
            ACCESS  not-implemented
            DESCRIPTION
                 "tmnxCpmProtEthCfmPolRowStatus is not implemented on Nokia 7750
                  SR-1 in release 14.0."

        VARIATION   tmnxCpmProtEthCfmPolTableLastChg
            ACCESS  not-implemented
            DESCRIPTION
                 "tmnxCpmProtEthCfmPolTableLastChg is not implemented on Nokia
                  7750 SR-1 in release 14.0."

        VARIATION   tmnxCpmProtExcdSapEcmPeriods
            ACCESS  not-implemented
            DESCRIPTION
                 "tmnxCpmProtExcdSapEcmPeriods is not implemented on Nokia 7750
                  SR-1 in release 14.0."

        VARIATION   tmnxCpmProtExcdSapEcmStarted
            ACCESS  not-implemented
            DESCRIPTION
                 "tmnxCpmProtExcdSapEcmStarted is not implemented on Nokia 7750
                  SR-1 in release 14.0."

        VARIATION   tmnxCpmProtExcdSapEcmTblLChg
            ACCESS  not-implemented
            DESCRIPTION
                 "tmnxCpmProtExcdSapEcmTblLChg is not implemented on Nokia 7750
                  SR-1 in release 14.0."

        VARIATION   tmnxCpmProtExcdSapEcmTime
            ACCESS  not-implemented
            DESCRIPTION
                 "tmnxCpmProtExcdSapEcmTime is not implemented on Nokia 7750
                  SR-1 in release 14.0."

        VARIATION   tmnxCpmProtExcdSdpBindEcmPeriods
            ACCESS  not-implemented
            DESCRIPTION
                 "tmnxCpmProtExcdSdpBindEcmPeriods is not implemented on Nokia
                  7750 SR-1 in release 14.0."

        VARIATION   tmnxCpmProtExcdSdpBindEcmStarted
            ACCESS  not-implemented
            DESCRIPTION
                 "tmnxCpmProtExcdSdpBindEcmStarted is not implemented on Nokia
                  7750 SR-1 in release 14.0."

        VARIATION   tmnxCpmProtExcdSdpBindEcmTblLChg
            ACCESS  not-implemented
            DESCRIPTION
                 "tmnxCpmProtExcdSdpBindEcmTblLChg is not implemented on Nokia
                  7750 SR-1 in release 14.0."

        VARIATION   tmnxCpmProtExcdSdpBindEcmTime
            ACCESS  not-implemented
            DESCRIPTION
                 "tmnxCpmProtExcdSdpBindEcmTime is not implemented on Nokia 7750
                  SR-1 in release 14.0."

        VARIATION   tmnxCpmProtExcdSdpBindPeriods
            ACCESS  not-implemented
            DESCRIPTION
                 "tmnxCpmProtExcdSdpBindPeriods is not implemented on Nokia 7750
                  SR-1 in release 14.0."

        VARIATION   tmnxCpmProtExcdSdpBindTblLastChg
            ACCESS  not-implemented
            DESCRIPTION
                 "tmnxCpmProtExcdSdpBindTblLastChg is not implemented on Nokia
                  7750 SR-1 in release 14.0."

        VARIATION   tmnxCpmProtExcdSdpBindTime
            ACCESS  not-implemented
            DESCRIPTION
                 "tmnxCpmProtExcdSdpBindTime is not implemented on Nokia 7750
                  SR-1 in release 14.0."

        VARIATION   tmnxCpmProtExcdSdpBindTimeStartd
            ACCESS  not-implemented
            DESCRIPTION
                 "tmnxCpmProtExcdSdpBindTimeStartd is not implemented on Nokia
                  7750 SR-1 in release 14.0."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxCpmProtViolSdpBindPeriods
            ACCESS  not-implemented
            DESCRIPTION
                 "tmnxCpmProtViolSdpBindPeriods is not implemented on Nokia 7750
                  SR-1 in release 14.0."

        VARIATION   tmnxCpmProtViolSdpBindTblLastChg
            ACCESS  not-implemented
            DESCRIPTION
                 "tmnxCpmProtViolSdpBindTblLastChg is not implemented on Nokia
                  7750 SR-1 in release 14.0."

        VARIATION   tmnxCpmProtViolSdpBindTime
            ACCESS  not-implemented
            DESCRIPTION
                 "tmnxCpmProtViolSdpBindTime is not implemented on Nokia 7750
                  SR-1 in release 14.0."

        VARIATION   tmnxCpmProtViolSdpBindTimeStartd
            ACCESS  not-implemented
            DESCRIPTION
                 "tmnxCpmProtViolSdpBindTimeStartd is not implemented on Nokia
                  7750 SR-1 in release 14.0."

        VARIATION   tmnxCpmProtViolVdoSvcClient
            ACCESS  not-implemented
            DESCRIPTION
                 "tmnxCpmProtViolVdoSvcClient is not implemented on Nokia 7750
                  SR-1 in release 14.0."

        VARIATION   tmnxCpmProtViolVdoSvcEntry
            ACCESS  not-implemented
            DESCRIPTION
                 "tmnxCpmProtViolVdoSvcEntry is not implemented on Nokia 7750
                  SR-1 in release 14.0."

        VARIATION   tmnxCpmProtViolVdoVrtrClient
            ACCESS  not-implemented
            DESCRIPTION
                 "tmnxCpmProtViolVdoVrtrClient is not implemented on Nokia 7750
                  SR-1 in release 14.0."

        VARIATION   tmnxCpmProtViolVdoVrtrEntry
            ACCESS  not-implemented
            DESCRIPTION
                 "tmnxCpmProtViolVdoVrtrEntry is not implemented on Nokia 7750
                  SR-1 in release 14.0."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia 7750
                  SR-1 in release 14.0.

                  verify-cert is not currently supported."

        VARIATION   tmnxPkiCAProfOcspVerifyCertFile
            ACCESS  not-implemented
            DESCRIPTION
                 "tmnxPkiCAProfOcspVerifyCertFile is not implemented on Nokia
                  7750 SR-1 in release 14.0.

                  verify-cert is not currently supported."

        VARIATION   tmnxPkiCAProfOcspVerifyCertOvr
            ACCESS  not-implemented
            DESCRIPTION
                 "tmnxPkiCAProfOcspVerifyCertOvr is not implemented on Nokia
                  7750 SR-1 in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnx7750SR1AgentV14v0  39 }

--
-- 7750c12 SECURITY CAPABILITIES
--
tmnx7750c12SecurityV14v0          AGENT-CAPABILITIES
    PRODUCT-RELEASE "Nokia SROS"
    STATUS          current
    DESCRIPTION
         "Implementation of Security capabilities for Nokia 7750 c12 systems
          release 14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
-- EXCLUDE tmnxCpmProtEthCfmPolV8v0Grp
-- EXCLUDE tmnxCpmProtExcdSapIpV9v0Group
-- EXCLUDE tmnxCpmProtPolNotifyV8v0Grp
-- EXCLUDE tmnxCpmProtPolNotifyV9v0Group
-- EXCLUDE tmnxCpmProtPolV8v0Grp
-- EXCLUDE tmnxCpmProtectionV11v0Group
           tmnxDistCpuProtectionV11v0Group,
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
-- EXCLUDE tmnxSecCpmProtNotifyObjsV12v0Grp
-- EXCLUDE tmnxSecCpmProtNotifyV12v0Grp
-- EXCLUDE tmnxSecCpmProtProtocolV12v0Group
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
           tmnxSecurityCpmIPv6FltrV11v0Grp,
           tmnxSecurityCpmIpFilterV11v0Grp,
           tmnxSecurityCpmMacFilterGroup,
-- EXCLUDE tmnxSecurityCpmProtNotificationGroup
-- EXCLUDE tmnxSecurityCpmProtNotifyV7v0Grp
-- EXCLUDE tmnxSecurityCpmProtV12v0Group
-- EXCLUDE tmnxSecurityCpmProtectGroup
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
-- EXCLUDE tmnxSecurityV7v0Group
           tmnxSessLimNotifyV13v0Grp
        }

        VARIATION   tCpmIpFilterEntryId
            SYNTAX  TEntryId (1..1536)
            DESCRIPTION
                 "tCpmIpFilterEntryId supports a maximum of only 1536 row
                  entries in the tCpmIpFilterTable on Nokia 7750 c12."

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolRowStatus
            SYNTAX  RowStatus {
                       active               (1),
                    -- notInService         (2)
                    -- notReady             (3)
                       createAndGo          (4),
                    -- createAndWait        (5)
                       destroy              (6)
                    }
            DESCRIPTION
                 "tmnxCpmProtEthCfmPolRowStatus supports only 'active (1)',
                  'createAndGo (4)', and 'destroy (6)'."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia 7750
                  c12 in release 14.0.

                  verify-cert is not currently supported."

        VARIATION   tmnxPkiCAProfOcspVerifyCertFile
            ACCESS  not-implemented
            DESCRIPTION
                 "tmnxPkiCAProfOcspVerifyCertFile is not implemented on Nokia
                  7750 c12 in release 14.0.

                  verify-cert is not currently supported."

        VARIATION   tmnxPkiCAProfOcspVerifyCertOvr
            ACCESS  not-implemented
            DESCRIPTION
                 "tmnxPkiCAProfOcspVerifyCertOvr is not implemented on Nokia
                  7750 c12 in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnx7750c12AgentV14v0  39 }

--
-- 7750c4 SECURITY CAPABILITIES
--
tmnx7750c4SecurityV14v0           AGENT-CAPABILITIES
    PRODUCT-RELEASE "Nokia SROS"
    STATUS          current
    DESCRIPTION
         "Implementation of Security capabilities for Nokia 7750 c4 systems
          release 14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
-- EXCLUDE tmnxCpmProtEthCfmPolV8v0Grp
-- EXCLUDE tmnxCpmProtExcdSapIpV9v0Group
-- EXCLUDE tmnxCpmProtPolNotifyV8v0Grp
-- EXCLUDE tmnxCpmProtPolNotifyV9v0Group
-- EXCLUDE tmnxCpmProtPolV8v0Grp
-- EXCLUDE tmnxCpmProtectionV11v0Group
           tmnxDistCpuProtectionV11v0Group,
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
-- EXCLUDE tmnxSecCpmProtNotifyObjsV12v0Grp
-- EXCLUDE tmnxSecCpmProtNotifyV12v0Grp
-- EXCLUDE tmnxSecCpmProtProtocolV12v0Group
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
           tmnxSecurityCpmIPv6FltrV11v0Grp,
           tmnxSecurityCpmIpFilterV11v0Grp,
           tmnxSecurityCpmMacFilterGroup,
-- EXCLUDE tmnxSecurityCpmProtNotificationGroup
-- EXCLUDE tmnxSecurityCpmProtNotifyV7v0Grp
-- EXCLUDE tmnxSecurityCpmProtV12v0Group
-- EXCLUDE tmnxSecurityCpmProtectGroup
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
-- EXCLUDE tmnxSecurityV7v0Group
           tmnxSessLimNotifyV13v0Grp
        }

        VARIATION   tCpmIpFilterEntryId
            SYNTAX  TEntryId (1..1536)
            DESCRIPTION
                 "tCpmIpFilterEntryId supports a maximum of only 1536 row
                  entries in the tCpmIpFilterTable on Nokia 7750 c4."

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolRowStatus
            SYNTAX  RowStatus {
                       active               (1),
                    -- notInService         (2)
                    -- notReady             (3)
                       createAndGo          (4),
                    -- createAndWait        (5)
                       destroy              (6)
                    }
            DESCRIPTION
                 "tmnxCpmProtEthCfmPolRowStatus supports only 'active (1)',
                  'createAndGo (4)', and 'destroy (6)'."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia 7750
                  c4 in release 14.0.

                  verify-cert is not currently supported."

        VARIATION   tmnxPkiCAProfOcspVerifyCertFile
            ACCESS  not-implemented
            DESCRIPTION
                 "tmnxPkiCAProfOcspVerifyCertFile is not implemented on Nokia
                  7750 c4 in release 14.0.

                  verify-cert is not currently supported."

        VARIATION   tmnxPkiCAProfOcspVerifyCertOvr
            ACCESS  not-implemented
            DESCRIPTION
                 "tmnxPkiCAProfOcspVerifyCertOvr is not implemented on Nokia
                  7750 c4 in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnx7750c4AgentV14v0  39 }

--
-- 7450 SECURITY CAPABILITIES
--
tmnx7450SecurityV14v0             AGENT-CAPABILITIES
    PRODUCT-RELEASE "Nokia SROS"
    STATUS          current
    DESCRIPTION
         "Implementation of Security capabilities for Nokia 7450 systems release
          14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
           tmnxCpmProtEthCfmPolV8v0Grp,
           tmnxCpmProtExcdSapIpV9v0Group,
           tmnxCpmProtPolNotifyV8v0Grp,
           tmnxCpmProtPolNotifyV9v0Group,
           tmnxCpmProtPolV8v0Grp,
           tmnxCpmProtectionV11v0Group,
           tmnxDistCpuProtectionV11v0Group,
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
           tmnxSecCpmProtNotifyObjsV12v0Grp,
           tmnxSecCpmProtNotifyV12v0Grp,
           tmnxSecCpmProtProtocolV12v0Group,
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
-- EXCLUDE tmnxSecurityCpmIPv6FltrV11v0Grp
           tmnxSecurityCpmIpFilterV11v0Grp,
           tmnxSecurityCpmMacFilterGroup,
           tmnxSecurityCpmProtNotificationGroup,
           tmnxSecurityCpmProtNotifyV7v0Grp,
           tmnxSecurityCpmProtV12v0Group,
           tmnxSecurityCpmProtectGroup,
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
           tmnxSecurityV7v0Group,
           tmnxSessLimNotifyV13v0Grp
        }

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolRowStatus
            SYNTAX  RowStatus {
                       active               (1),
                    -- notInService         (2)
                    -- notReady             (3)
                       createAndGo          (4),
                    -- createAndWait        (5)
                       destroy              (6)
                    }
            DESCRIPTION
                 "tmnxCpmProtEthCfmPolRowStatus supports only 'active (1)',
                  'createAndGo (4)', and 'destroy (6)'."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia 7450
                  in release 14.0.

                  verify-cert is not currently supported."

        VARIATION   tmnxPkiCAProfOcspVerifyCertFile
            ACCESS  not-implemented
            DESCRIPTION
                 "tmnxPkiCAProfOcspVerifyCertFile is not implemented on Nokia
                  7450 in release 14.0.

                  verify-cert is not currently supported."

        VARIATION   tmnxPkiCAProfOcspVerifyCertOvr
            ACCESS  not-implemented
            DESCRIPTION
                 "tmnxPkiCAProfOcspVerifyCertOvr is not implemented on Nokia
                  7450 in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnx7450AgentV14v0  39 }

--
-- 7450ESS-1 SECURITY CAPABILITIES
--
tmnx7450ESS1SecurityV14v0         AGENT-CAPABILITIES
    PRODUCT-RELEASE "Nokia SROS"
    STATUS          current
    DESCRIPTION
         "Implementation of Security capabilities for Nokia 7450 ESS-1 systems
          release 14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
           tmnxCpmProtEthCfmPolV8v0Grp,
           tmnxCpmProtExcdSapIpV9v0Group,
           tmnxCpmProtPolNotifyV8v0Grp,
           tmnxCpmProtPolNotifyV9v0Group,
           tmnxCpmProtPolV8v0Grp,
           tmnxCpmProtectionV11v0Group,
-- EXCLUDE tmnxDistCpuProtectionV11v0Group
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
           tmnxSecCpmProtNotifyObjsV12v0Grp,
           tmnxSecCpmProtNotifyV12v0Grp,
           tmnxSecCpmProtProtocolV12v0Group,
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
-- EXCLUDE tmnxSecurityCpmIPv6FltrV11v0Grp
           tmnxSecurityCpmIpFilterV11v0Grp,
           tmnxSecurityCpmMacFilterGroup,
           tmnxSecurityCpmProtNotificationGroup,
           tmnxSecurityCpmProtNotifyV7v0Grp,
           tmnxSecurityCpmProtV12v0Group,
           tmnxSecurityCpmProtectGroup,
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
           tmnxSecurityV7v0Group,
           tmnxSessLimNotifyV13v0Grp
        }

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolLastChanged
            ACCESS  not-implemented
            DESCRIPTION
                 "tmnxCpmProtEthCfmPolLastChanged is not implemented on Nokia
                  7450 ESS-1 in release 14.0."

        VARIATION   tmnxCpmProtEthCfmPolLevelSet
            ACCESS  not-implemented
            DESCRIPTION
                 "tmnxCpmProtEthCfmPolLevelSet is not implemented on Nokia 7450
                  ESS-1 in release 14.0."

        VARIATION   tmnxCpmProtEthCfmPolOpCodeSet
            ACCESS  not-implemented
            DESCRIPTION
                 "tmnxCpmProtEthCfmPolOpCodeSet is not implemented on Nokia 7450
                  ESS-1 in release 14.0."

        VARIATION   tmnxCpmProtEthCfmPolRateLimit
            ACCESS  not-implemented
            DESCRIPTION
                 "tmnxCpmProtEthCfmPolRateLimit is not implemented on Nokia 7450
                  ESS-1 in release 14.0."

        VARIATION   tmnxCpmProtEthCfmPolRowStatus
            ACCESS  not-implemented
            DESCRIPTION
                 "tmnxCpmProtEthCfmPolRowStatus is not implemented on Nokia 7450
                  ESS-1 in release 14.0."

        VARIATION   tmnxCpmProtEthCfmPolTableLastChg
            ACCESS  not-implemented
            DESCRIPTION
                 "tmnxCpmProtEthCfmPolTableLastChg is not implemented on Nokia
                  7450 ESS-1 in release 14.0."

        VARIATION   tmnxCpmProtExcdSapEcmPeriods
            ACCESS  not-implemented
            DESCRIPTION
                 "tmnxCpmProtExcdSapEcmPeriods is not implemented on Nokia 7450
                  ESS-1 in release 14.0."

        VARIATION   tmnxCpmProtExcdSapEcmStarted
            ACCESS  not-implemented
            DESCRIPTION
                 "tmnxCpmProtExcdSapEcmStarted is not implemented on Nokia 7450
                  ESS-1 in release 14.0."

        VARIATION   tmnxCpmProtExcdSapEcmTblLChg
            ACCESS  not-implemented
            DESCRIPTION
                 "tmnxCpmProtExcdSapEcmTblLChg is not implemented on Nokia 7450
                  ESS-1 in release 14.0."

        VARIATION   tmnxCpmProtExcdSapEcmTime
            ACCESS  not-implemented
            DESCRIPTION
                 "tmnxCpmProtExcdSapEcmTime is not implemented on Nokia 7450
                  ESS-1 in release 14.0."

        VARIATION   tmnxCpmProtExcdSdpBindEcmPeriods
            ACCESS  not-implemented
            DESCRIPTION
                 "tmnxCpmProtExcdSdpBindEcmPeriods is not implemented on Nokia
                  7450 ESS-1 in release 14.0."

        VARIATION   tmnxCpmProtExcdSdpBindEcmStarted
            ACCESS  not-implemented
            DESCRIPTION
                 "tmnxCpmProtExcdSdpBindEcmStarted is not implemented on Nokia
                  7450 ESS-1 in release 14.0."

        VARIATION   tmnxCpmProtExcdSdpBindEcmTblLChg
            ACCESS  not-implemented
            DESCRIPTION
                 "tmnxCpmProtExcdSdpBindEcmTblLChg is not implemented on Nokia
                  7450 ESS-1 in release 14.0."

        VARIATION   tmnxCpmProtExcdSdpBindEcmTime
            ACCESS  not-implemented
            DESCRIPTION
                 "tmnxCpmProtExcdSdpBindEcmTime is not implemented on Nokia 7450
                  ESS-1 in release 14.0."

        VARIATION   tmnxCpmProtExcdSdpBindPeriods
            ACCESS  not-implemented
            DESCRIPTION
                 "tmnxCpmProtExcdSdpBindPeriods is not implemented on Nokia 7450
                  ESS-1 in release 14.0."

        VARIATION   tmnxCpmProtExcdSdpBindTblLastChg
            ACCESS  not-implemented
            DESCRIPTION
                 "tmnxCpmProtExcdSdpBindTblLastChg is not implemented on Nokia
                  7450 ESS-1 in release 14.0."

        VARIATION   tmnxCpmProtExcdSdpBindTime
            ACCESS  not-implemented
            DESCRIPTION
                 "tmnxCpmProtExcdSdpBindTime is not implemented on Nokia 7450
                  ESS-1 in release 14.0."

        VARIATION   tmnxCpmProtExcdSdpBindTimeStartd
            ACCESS  not-implemented
            DESCRIPTION
                 "tmnxCpmProtExcdSdpBindTimeStartd is not implemented on Nokia
                  7450 ESS-1 in release 14.0."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxCpmProtViolSdpBindPeriods
            ACCESS  not-implemented
            DESCRIPTION
                 "tmnxCpmProtViolSdpBindPeriods is not implemented on Nokia 7450
                  ESS-1 in release 14.0."

        VARIATION   tmnxCpmProtViolSdpBindTblLastChg
            ACCESS  not-implemented
            DESCRIPTION
                 "tmnxCpmProtViolSdpBindTblLastChg is not implemented on Nokia
                  7450 ESS-1 in release 14.0."

        VARIATION   tmnxCpmProtViolSdpBindTime
            ACCESS  not-implemented
            DESCRIPTION
                 "tmnxCpmProtViolSdpBindTime is not implemented on Nokia 7450
                  ESS-1 in release 14.0."

        VARIATION   tmnxCpmProtViolSdpBindTimeStartd
            ACCESS  not-implemented
            DESCRIPTION
                 "tmnxCpmProtViolSdpBindTimeStartd is not implemented on Nokia
                  7450 ESS-1 in release 14.0."

        VARIATION   tmnxCpmProtViolVdoSvcClient
            ACCESS  not-implemented
            DESCRIPTION
                 "tmnxCpmProtViolVdoSvcClient is not implemented on Nokia 7450
                  ESS-1 in release 14.0."

        VARIATION   tmnxCpmProtViolVdoSvcEntry
            ACCESS  not-implemented
            DESCRIPTION
                 "tmnxCpmProtViolVdoSvcEntry is not implemented on Nokia 7450
                  ESS-1 in release 14.0."

        VARIATION   tmnxCpmProtViolVdoVrtrClient
            ACCESS  not-implemented
            DESCRIPTION
                 "tmnxCpmProtViolVdoVrtrClient is not implemented on Nokia 7450
                  ESS-1 in release 14.0."

        VARIATION   tmnxCpmProtViolVdoVrtrEntry
            ACCESS  not-implemented
            DESCRIPTION
                 "tmnxCpmProtViolVdoVrtrEntry is not implemented on Nokia 7450
                  ESS-1 in release 14.0."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia 7450
                  ESS-1 in release 14.0.

                  verify-cert is not currently supported."

        VARIATION   tmnxPkiCAProfOcspVerifyCertFile
            ACCESS  not-implemented
            DESCRIPTION
                 "tmnxPkiCAProfOcspVerifyCertFile is not implemented on Nokia
                  7450 ESS-1 in release 14.0.

                  verify-cert is not currently supported."

        VARIATION   tmnxPkiCAProfOcspVerifyCertOvr
            ACCESS  not-implemented
            DESCRIPTION
                 "tmnxPkiCAProfOcspVerifyCertOvr is not implemented on Nokia
                  7450 ESS-1 in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnx7450ESS1AgentV14v0  39 }

--
-- 7710 SECURITY CAPABILITIES
--
tmnx7710SecurityV14v0             AGENT-CAPABILITIES
    PRODUCT-RELEASE "Nokia SROS"
    STATUS          current
    DESCRIPTION
         "Implementation of Security capabilities for Nokia 7710 systems release
          14.0."

    SUPPORTS        TIMETRA-SECURITY-MIB
        INCLUDES {
           tCAProfCmpv2HttpVerV12v0Group,
           tCAProfCmpv2SetSndrV11v0Group,
           tmnxCAProfileV11v0Group,
           tmnxCertExpNotificationV13v0Grp,
           tmnxCertExpWarningV13v0Group,
           tmnxCertNotifyGroup,
           tmnxCertNotifyV14v0Group,
           tmnxCertRldNotificationV13v0Grp,
           tmnxCliScriptAuthUserV13v0Group,
           tmnxCliSessionGroupV13v0Group,
           tmnxCpmFltrPrefixListV11v0Group,
-- EXCLUDE tmnxCpmProtEthCfmPolV8v0Grp
-- EXCLUDE tmnxCpmProtExcdSapIpV9v0Group
-- EXCLUDE tmnxCpmProtPolNotifyV8v0Grp
-- EXCLUDE tmnxCpmProtPolNotifyV9v0Group
-- EXCLUDE tmnxCpmProtPolV8v0Grp
-- EXCLUDE tmnxCpmProtectionV11v0Group
-- EXCLUDE tmnxDistCpuProtectionV11v0Group
           tmnxLogMaxAttNotifyV14v0Grp,
           tmnxPkiCAProf13v0Group,
           tmnxPkiCAProfAtCrlUpdV13v0Group,
           tmnxPkiCAProfCrlSizeLimtV14v0Grp,
           tmnxPkiCAProfNotifyV11v0Group,
           tmnxPkiCAProfRevokeChkGroup,
           tmnxPkiCertDispFmtV12v0Group,
           tmnxRadiusUserExGroup,
           tmnxRadiusUserExV11v0Group,
           tmnxRadiusUserGroup,
           tmnxSSHServerV4v0Group,
           tmnxSecCertRldNotifyObjsV13v0Grp,
-- EXCLUDE tmnxSecCpmProtNotifyObjsV12v0Grp
-- EXCLUDE tmnxSecCpmProtNotifyV12v0Grp
-- EXCLUDE tmnxSecCpmProtProtocolV12v0Group
           tmnxSecNotifyObjsV14v0Group,
           tmnxSecPkiV9v0Grp,
           tmnxSecPwdHistNotifV12v0Grp,
           tmnxSecPwdHistNotifyObjsV12v0Grp,
           tmnxSecTechGroup,
           tmnxSecVsdGroup,
           tmnxSecurityCpmGroup,
           tmnxSecurityCpmIPv6FltrV11v0Grp,
           tmnxSecurityCpmIpFilterV11v0Grp,
-- EXCLUDE tmnxSecurityCpmMacFilterGroup
-- EXCLUDE tmnxSecurityCpmProtNotificationGroup
-- EXCLUDE tmnxSecurityCpmProtNotifyV7v0Grp
-- EXCLUDE tmnxSecurityCpmProtV12v0Group
-- EXCLUDE tmnxSecurityCpmProtectGroup
           tmnxSecurityKeyChainV12v0Group,
           tmnxSecurityKeyChainV13v0Group,
           tmnxSecurityKeyChainV5v0Group,
           tmnxSecurityLiGroup,
           tmnxSecurityMafMacFilterGroup,
           tmnxSecurityMafV6v0Group,
           tmnxSecurityNetconfLockV14v0Grp,
           tmnxSecurityNetconfV110Group,
           tmnxSecurityNotificationV12v0Grp,
           tmnxSecurityNotificationV5v0Group,
           tmnxSecurityNotificationV8v0Grp,
           tmnxSecurityNotifyObjsV12v0Group,
           tmnxSecurityNotifyObjsV13v0Group,
           tmnxSecurityNotifyObjsV8v0Group,
           tmnxSecurityNwExceptionsGroup,
           tmnxSecurityPasswordHashGroup,
           tmnxSecurityPasswordsV12v0Group,
           tmnxSecurityPasswordsV14v0Group,
           tmnxSecurityProfRateV12v0Group,
           tmnxSecurityPublicKeyGroup,
           tmnxSecurityRadiusAuthV5v0Group,
           tmnxSecurityRadiusV13v0Group,
           tmnxSecurityRadiusV14v0Group,
           tmnxSecuritySSHCipherGroup,
           tmnxSecuritySSHv2PubKeyV14v0Grp,
           tmnxSecurityServerCtlV4v0Group,
           tmnxSecuritySourceIpV4v0Group,
           tmnxSecurityTacPlusV11v0Group,
           tmnxSecurityTacPlusV14v0Group,
           tmnxSecurityUserActionGroup,
           tmnxSecurityUserV12v0Group,
-- EXCLUDE tmnxSecurityV7v0Group
           tmnxSessLimNotifyV13v0Grp
        }

        VARIATION   tCpmFilterQueueTable
            ACCESS  not-implemented
            DESCRIPTION
                 "tCpmFilterQueueTable is not implemented on Nokia 7710 in
                  release 14.0.

                  CPM-QUEUE is not supported on Nokia 7710."

        VARIATION   tCpmIPv6FilterEntryAction
            SYNTAX  INTEGER {
                       drop                 (1),
                       forward              (2),
                    -- queue                (3)
                       default              (4)
                    }
            DESCRIPTION
                 "The value 'queue (3)' is not supported because CPM-QUEUE is
                  not supported on Nokia 7710."

        VARIATION   tCpmIPv6FilterEntryQueueId
            ACCESS  not-implemented
            DESCRIPTION
                 "tCpmIPv6FilterEntryQueueId is not implemented on Nokia 7710 in
                  release 14.0.

                  CPM-QUEUE is not supported on Nokia 7710."

        VARIATION   tCpmIpFilterEntryAction
            SYNTAX  INTEGER {
                       drop                 (1),
                       forward              (2),
                    -- queue                (3)
                       default              (4)
                    }
            DESCRIPTION
                 "The value 'queue (3)' is not supported because CPM-QUEUE is
                  not supported on Nokia 7710."

        VARIATION   tCpmIpFilterEntryId
            SYNTAX  TEntryId (1..1536)
            DESCRIPTION
                 "tCpmIpFilterEntryId supports a maximum of only 1536 row
                  entries in the tCpmIpFilterTable on Nokia 7710."

        VARIATION   tCpmIpFilterEntryQueueId
            ACCESS  not-implemented
            DESCRIPTION
                 "tCpmIpFilterEntryQueueId is not implemented on Nokia 7710 in
                  release 14.0.

                  CPM-QUEUE is not supported on Nokia 7710."

        VARIATION   tmnxCliScriptAuthRowStatus
            SYNTAX  RowStatus {
                       active               (1),
                    -- notInService         (2)
                    -- notReady             (3)
                       createAndGo          (4),
                    -- createAndWait        (5)
                       destroy              (6)
                    }
            DESCRIPTION
                 "tmnxCliScriptAuthRowStatus supports only 'active (1)',
                  'createAndGo (4)', and 'destroy (6)'."

        VARIATION   tmnxCliSessionGroupRowStatus
            SYNTAX  RowStatus {
                       active               (1),
                    -- notInService         (2)
                    -- notReady             (3)
                       createAndGo          (4),
                    -- createAndWait        (5)
                       destroy              (6)
                    }
            DESCRIPTION
                 "tmnxCliSessionGroupRowStatus supports only 'active (1)',
                  'createAndGo (4)', and 'destroy (6)'."

        VARIATION   tmnxCpmProtEthCfmPolRowStatus
            SYNTAX  RowStatus {
                       active               (1),
                    -- notInService         (2)
                    -- notReady             (3)
                       createAndGo          (4),
                    -- createAndWait        (5)
                       destroy              (6)
                    }
            DESCRIPTION
                 "tmnxCpmProtEthCfmPolRowStatus supports only 'active (1)',
                  'createAndGo (4)', and 'destroy (6)'."

        VARIATION   tmnxCpmProtPolRowStatus
            SYNTAX  RowStatus {
                       active               (1),
                    -- notInService         (2)
                    -- notReady             (3)
                       createAndGo          (4),
                    -- createAndWait        (5)
                       destroy              (6)
                    }
            DESCRIPTION
                 "tmnxCpmProtPolRowStatus supports only 'active (1)',
                  'createAndGo (4)', and 'destroy (6)'."

        VARIATION   tmnxPkiCAProfAtCrlUpdRowStatus
            SYNTAX  RowStatus {
                       active               (1),
                    -- notInService         (2)
                    -- notReady             (3)
                       createAndGo          (4),
                    -- createAndWait        (5)
                       destroy              (6)
                    }
            DESCRIPTION
                 "tmnxPkiCAProfAtCrlUpdRowStatus supports only 'active (1)',
                  'createAndGo (4)', and 'destroy (6)'."

        VARIATION   tmnxPkiCAProfOcspVerifyCertCA
            ACCESS  not-implemented
            DESCRIPTION
                 "tmnxPkiCAProfOcspVerifyCertCA is not implemented on Nokia 7710
                  in release 14.0.

                  verify-cert is not currently supported."

        VARIATION   tmnxPkiCAProfOcspVerifyCertFile
            ACCESS  not-implemented
            DESCRIPTION
                 "tmnxPkiCAProfOcspVerifyCertFile is not implemented on Nokia
                  7710 in release 14.0.

                  verify-cert is not currently supported."

        VARIATION   tmnxPkiCAProfOcspVerifyCertOvr
            ACCESS  not-implemented
            DESCRIPTION
                 "tmnxPkiCAProfOcspVerifyCertOvr is not implemented on Nokia
                  7710 in release 14.0.

                  verify-cert is not currently supported."

        VARIATION   tmnxPkiCAProfUrlRowStatus
            SYNTAX  RowStatus {
                       active               (1),
                    -- notInService         (2)
                    -- notReady             (3)
                       createAndGo          (4),
                    -- createAndWait        (5)
                       destroy              (6)
                    }
            DESCRIPTION
                 "tmnxPkiCAProfUrlRowStatus supports only 'active (1)',
                  'createAndGo (4)', and 'destroy (6)'."

        VARIATION   tmnxRadiusServerInetAddress
            SYNTAX  InetAddress (SIZE(0|4|16))
            DESCRIPTION
                 "tmnxRadiusServerInetAddress supports only address of types
                  'ipv4 (1)' and 'ipv6 (2)'. tmnxRadiusServerInetAddress does
                  not support address of type 'ipv6z (4)'."

        VARIATION   tmnxRadiusServerInetAddressType
            SYNTAX  InetAddressType {
                       unknown              (0),
                       ipv4                 (1),
                       ipv6                 (2)
                    -- ipv4z                (3)
                    -- ipv6z                (4)
                    -- dns                  (16)
                    }
            DESCRIPTION
                 "tmnxRadiusServerInetAddressType supports only the
                  InetAddressType values 'unknown (0)', 'ipv4 (1)', and 'ipv6
                  (2)'."

        VARIATION   tmnxRadiusServerRowStatus
            SYNTAX  RowStatus {
                       active               (1),
                    -- notInService         (2)
                    -- notReady             (3)
                       createAndGo          (4),
                    -- createAndWait        (5)
                       destroy              (6)
                    }
            DESCRIPTION
                 "tmnxRadiusServerRowStatus supports only 'active (1)',
                  'createAndGo (4)', and 'destroy (6)'."

        VARIATION   tmnxTacPlusServerInetAddress
            SYNTAX  InetAddress (SIZE(0|4|16))
            DESCRIPTION
                 "tmnxTacPlusServerInetAddress supports only address of types
                  'ipv4 (1)' and 'ipv6 (2)'. tmnxTacPlusServerInetAddress does
                  not support address of type 'ipv6z (4)'."

        VARIATION   tmnxTacPlusServerInetAddressType
            SYNTAX  InetAddressType {
                       unknown              (0),
                       ipv4                 (1),
                       ipv6                 (2)
                    -- ipv4z                (3)
                    -- ipv6z                (4)
                    -- dns                  (16)
                    }
            DESCRIPTION
                 "tmnxTacPlusServerInetAddressType supports only the
                  InetAddressType values 'unknown (0)', 'ipv4 (1)', and 'ipv6
                  (2)'."

        VARIATION   tmnxTacPlusServerRowStatus
            SYNTAX  RowStatus {
                       active               (1),
                    -- notInService         (2)
                    -- notReady             (3)
                       createAndGo          (4),
                    -- createAndWait        (5)
                       destroy              (6)
                    }
            DESCRIPTION
                 "tmnxTacPlusServerRowStatus supports only 'active (1)',
                  'createAndGo (4)', and 'destroy (6)'."

        VARIATION   tmnxUserPubEcdsaKeyRowStatus
            SYNTAX  RowStatus {
                       active               (1),
                    -- notInService         (2)
                    -- notReady             (3)
                       createAndGo          (4),
                    -- createAndWait        (5)
                       destroy              (6)
                    }
            DESCRIPTION
                 "tmnxUserPubEcdsaKeyRowStatus supports only 'active (1)',
                  'createAndGo (4)', and 'destroy (6)'."

        VARIATION   tmnxUserPublicKeyRowStatus
            SYNTAX  RowStatus {
                       active               (1),
                    -- notInService         (2)
                    -- notReady             (3)
                       createAndGo          (4),
                    -- createAndWait        (5)
                       destroy              (6)
                    }
            DESCRIPTION
                 "tmnxUserPublicKeyRowStatus supports only 'active (1)',
                  'createAndGo (4)', and 'destroy (6)'."

    ::= { tmnx7710AgentV14v0  39 }

--
-- SROS SERVICES CAPABILITIES
--
tmnxSROSServicesV14v0             AGENT-CAPABILITIES
    PRODUCT-RELEASE "Nokia SROS"
    STATUS          current
    DESCRIPTION
         "Implementation of Services capabilities for Nokia SROS systems release
          14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
-- EXCLUDE tmnxSvcDhcpBgpV7v0Group
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia SROS
                  in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia SROS
                  in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia SROS, as they are not implemented."

        VARIATION   svcVsdDomainCreationOrigin
            ACCESS  read-only
            DESCRIPTION
                 "svcVsdDomainCreationOrigin is implemented as read-only on
                  Nokia SROS in release 14.0."

        VARIATION   tlsEgrMcGrpQinqFixedTagPosition
            ACCESS  read-only
            DESCRIPTION
                 "tlsEgrMcGrpQinqFixedTagPosition is supported as read-only."

    ::= { tmnxSROSAgentV14v0  40 }

--
-- 7750 SERVICES CAPABILITIES
--
tmnx7750ServicesV14v0             AGENT-CAPABILITIES
    PRODUCT-RELEASE "Nokia SROS"
    STATUS          current
    DESCRIPTION
         "Implementation of Services capabilities for Nokia 7750 systems release
          14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7750
                  in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750, as they are not implemented."

        VARIATION   svcVsdDomainCreationOrigin
            ACCESS  read-only
            DESCRIPTION
                 "svcVsdDomainCreationOrigin is implemented as read-only on
                  Nokia 7750 in release 14.0."

        VARIATION   tlsEgrMcGrpQinqFixedTagPosition
            ACCESS  read-only
            DESCRIPTION
                 "tlsEgrMcGrpQinqFixedTagPosition is supported as read-only."

    ::= { tmnx7750AgentV14v0  40 }

--
-- 7750SR-1 SERVICES CAPABILITIES
--
tmnx7750SR1ServicesV14v0          AGENT-CAPABILITIES
    PRODUCT-RELEASE "Nokia SROS"
    STATUS          current
    DESCRIPTION
         "Implementation of Services capabilities for Nokia 7750 SR-1 systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
-- EXCLUDE tmnxSvcBsxV8v0Group
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  SR-1 in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcEpipeBackboneForceQTagFwd
            ACCESS  not-implemented
            DESCRIPTION
                 "svcEpipeBackboneForceQTagFwd is not implemented on Nokia 7750
                  SR-1 in release 14.0."

        VARIATION   svcEpipePerSvcHashing
            ACCESS  not-implemented
            DESCRIPTION
                 "svcEpipePerSvcHashing is not implemented on Nokia 7750 SR-1 in
                  release 14.0."

        VARIATION   svcIfSapCfgDefFilterProfile
            ACCESS  not-implemented
            DESCRIPTION
                 "svcIfSapCfgDefFilterProfile is not implemented on Nokia 7750
                  SR-1 in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMacNotifCount
            ACCESS  not-implemented
            DESCRIPTION
                 "svcMacNotifCount is not implemented on Nokia 7750 SR-1 in
                  release 14.0."

        VARIATION   svcMacNotifInterval
            ACCESS  not-implemented
            DESCRIPTION
                 "svcMacNotifInterval is not implemented on Nokia 7750 SR-1 in
                  release 14.0."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsBackboneForceQTagFwd
            ACCESS  not-implemented
            DESCRIPTION
                 "svcTlsBackboneForceQTagFwd is not implemented on Nokia 7750
                  SR-1 in release 14.0."

        VARIATION   svcTlsMacNotifAdminState
            ACCESS  not-implemented
            DESCRIPTION
                 "svcTlsMacNotifAdminState is not implemented on Nokia 7750 SR-1
                  in release 14.0."

        VARIATION   svcTlsMacNotifCount
            ACCESS  not-implemented
            DESCRIPTION
                 "svcTlsMacNotifCount is not implemented on Nokia 7750 SR-1 in
                  release 14.0."

        VARIATION   svcTlsMacNotifInterval
            ACCESS  not-implemented
            DESCRIPTION
                 "svcTlsMacNotifInterval is not implemented on Nokia 7750 SR-1
                  in release 14.0."

        VARIATION   svcTlsPerSvcHashing
            ACCESS  not-implemented
            DESCRIPTION
                 "svcTlsPerSvcHashing is not implemented on Nokia 7750 SR-1 in
                  release 14.0."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750 SR-1, as they are not implemented."

        VARIATION   svcVsdDomainCreationOrigin
            ACCESS  read-only
            DESCRIPTION
                 "svcVsdDomainCreationOrigin is implemented as read-only on
                  Nokia 7750 SR-1 in release 14.0."

        VARIATION   tlsEgrMcGrpQinqFixedTagPosition
            ACCESS  read-only
            DESCRIPTION
                 "tlsEgrMcGrpQinqFixedTagPosition is supported as read-only."

    ::= { tmnx7750SR1AgentV14v0  40 }

--
-- 7750SR-a4 SERVICES CAPABILITIES
--
tmnx7750SRa4ServicesV14v0         AGENT-CAPABILITIES
    PRODUCT-RELEASE "Nokia SROS"
    STATUS          current
    DESCRIPTION
         "Implementation of Services capabilities for Nokia 7750 SR-a4 systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  SR-a4 in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7750
                  SR-a4 in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsFdbTableSize
            SYNTAX  Integer32 (1..255999)
            DESCRIPTION
                 "The svcTlsFdbTableSize is limited on Nokia 7750 SR-a4."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750 SR-a4, as they are not implemented."

        VARIATION   svcVsdDomainCreationOrigin
            ACCESS  read-only
            DESCRIPTION
                 "svcVsdDomainCreationOrigin is implemented as read-only on
                  Nokia 7750 SR-a4 in release 14.0."

        VARIATION   tlsEgrMcGrpQinqFixedTagPosition
            ACCESS  read-only
            DESCRIPTION
                 "tlsEgrMcGrpQinqFixedTagPosition is supported as read-only."

    ::= { tmnx7750SRa4AgentV14v0  40 }

--
-- 7750SR-a8 SERVICES CAPABILITIES
--
tmnx7750SRa8ServicesV14v0         AGENT-CAPABILITIES
    PRODUCT-RELEASE "Nokia SROS"
    STATUS          current
    DESCRIPTION
         "Implementation of Services capabilities for Nokia 7750 SR-a8 systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  SR-a8 in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7750
                  SR-a8 in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsFdbTableSize
            SYNTAX  Integer32 (1..255999)
            DESCRIPTION
                 "The svcTlsFdbTableSize is limited on Nokia 7750 SR-a8."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750 SR-a8, as they are not implemented."

        VARIATION   svcVsdDomainCreationOrigin
            ACCESS  read-only
            DESCRIPTION
                 "svcVsdDomainCreationOrigin is implemented as read-only on
                  Nokia 7750 SR-a8 in release 14.0."

        VARIATION   tlsEgrMcGrpQinqFixedTagPosition
            ACCESS  read-only
            DESCRIPTION
                 "tlsEgrMcGrpQinqFixedTagPosition is supported as read-only."

    ::= { tmnx7750SRa8AgentV14v0  40 }

--
-- 7750SR-1e SERVICES CAPABILITIES
--
tmnx7750SR1eServicesV14v0         AGENT-CAPABILITIES
    PRODUCT-RELEASE "Nokia SROS"
    STATUS          current
    DESCRIPTION
         "Implementation of Services capabilities for Nokia 7750 SR-1e systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  SR-1e in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7750
                  SR-1e in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsFdbTableSize
            SYNTAX  Integer32 (1..255999)
            DESCRIPTION
                 "The svcTlsFdbTableSize is limited on Nokia 7750 SR-1e."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750 SR-1e, as they are not implemented."

        VARIATION   svcVsdDomainCreationOrigin
            ACCESS  read-only
            DESCRIPTION
                 "svcVsdDomainCreationOrigin is implemented as read-only on
                  Nokia 7750 SR-1e in release 14.0."

        VARIATION   tlsEgrMcGrpQinqFixedTagPosition
            ACCESS  read-only
            DESCRIPTION
                 "tlsEgrMcGrpQinqFixedTagPosition is supported as read-only."

    ::= { tmnx7750SR1eAgentV14v0  40 }

--
-- 7750SR-2e SERVICES CAPABILITIES
--
tmnx7750SR2eServicesV14v0         AGENT-CAPABILITIES
    PRODUCT-RELEASE "Nokia SROS"
    STATUS          current
    DESCRIPTION
         "Implementation of Services capabilities for Nokia 7750 SR-2e systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  SR-2e in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7750
                  SR-2e in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsFdbTableSize
            SYNTAX  Integer32 (1..255999)
            DESCRIPTION
                 "The svcTlsFdbTableSize is limited on Nokia 7750 SR-2e."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750 SR-2e, as they are not implemented."

        VARIATION   svcVsdDomainCreationOrigin
            ACCESS  read-only
            DESCRIPTION
                 "svcVsdDomainCreationOrigin is implemented as read-only on
                  Nokia 7750 SR-2e in release 14.0."

        VARIATION   tlsEgrMcGrpQinqFixedTagPosition
            ACCESS  read-only
            DESCRIPTION
                 "tlsEgrMcGrpQinqFixedTagPosition is supported as read-only."

    ::= { tmnx7750SR2eAgentV14v0  40 }

--
-- 7750SR-3e SERVICES CAPABILITIES
--
tmnx7750SR3eServicesV14v0         AGENT-CAPABILITIES
    PRODUCT-RELEASE "Nokia SROS"
    STATUS          current
    DESCRIPTION
         "Implementation of Services capabilities for Nokia 7750 SR-3e systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7750
                  SR-3e in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7750
                  SR-3e in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsFdbTableSize
            SYNTAX  Integer32 (1..255999)
            DESCRIPTION
                 "The svcTlsFdbTableSize is limited on Nokia 7750 SR-3e."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7750 SR-3e, as they are not implemented."

        VARIATION   svcVsdDomainCreationOrigin
            ACCESS  read-only
            DESCRIPTION
                 "svcVsdDomainCreationOrigin is implemented as read-only on
                  Nokia 7750 SR-3e in release 14.0."

        VARIATION   tlsEgrMcGrpQinqFixedTagPosition
            ACCESS  read-only
            DESCRIPTION
                 "tlsEgrMcGrpQinqFixedTagPosition is supported as read-only."

    ::= { tmnx7750SR3eAgentV14v0  40 }

--
-- 7450 SERVICES CAPABILITIES
--
tmnx7450ServicesV14v0             AGENT-CAPABILITIES
    PRODUCT-RELEASE "Nokia SROS"
    STATUS          current
    DESCRIPTION
         "Implementation of Services capabilities for Nokia 7450 systems release
          14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
           tmnxSvcBsxV8v0Group,
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7450
                  in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                    -- ipsec                (6)
                       ipMirror             (7),
                       video                (8),
                    -- reserved9            (9)
                       aarp                 (10)
                    }
            DESCRIPTION
                 "The values - 'cem (5)', - 'ipsec (6)' are not supported on
                  Nokia 7450."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7450
                  in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcType
            SYNTAX  INTEGER {
                       epipe                (1),
                       tls                  (3),
                       vprn                 (4),
                       ies                  (5),
                       mirror               (6),
                       apipe                (7),
                       fpipe                (8),
                       ipipe                (9),
                    -- cpipe(10)
                       intTls               (11)
                    }
            DESCRIPTION
                 "The enumeration 'cpipe (10)' is not supported on Nokia 7450."

        VARIATION   svcVllType
            SYNTAX  INTEGER {
                       undef                (1),
                       atmSdu               (6),
                       atmCell              (7),
                       atmVcc               (8),
                       atmVpc               (9),
                       frDlci               (10)
                    -- satopE1              (12)
                    -- satopT1              (13)
                    -- satopE3              (14)
                    -- satopT3              (15)
                    -- cesopsn              (16)
                    -- cesopsnCas(17)
                    }
            DESCRIPTION
                 "The values - satopE3 (14), - satopT3 (15), are not supported
                  on Nokia 7450, as they are not implemented.

                  The values - 'satopE1 (12)', - 'satopT1 (13)', - 'cesopsn
                  (16)', - 'cesopsnCas (17)' are not supported on Nokia 7450, as
                  CEM is not implemented."

        VARIATION   svcVsdDomainCreationOrigin
            ACCESS  read-only
            DESCRIPTION
                 "svcVsdDomainCreationOrigin is implemented as read-only on
                  Nokia 7450 in release 14.0."

        VARIATION   tlsEgrMcGrpQinqFixedTagPosition
            ACCESS  read-only
            DESCRIPTION
                 "tlsEgrMcGrpQinqFixedTagPosition is supported as read-only."

    ::= { tmnx7450AgentV14v0  40 }

--
-- 7450ESS-1 SERVICES CAPABILITIES
--
tmnx7450ESS1ServicesV14v0         AGENT-CAPABILITIES
    PRODUCT-RELEASE "Nokia SROS"
    STATUS          current
    DESCRIPTION
         "Implementation of Services capabilities for Nokia 7450 ESS-1 systems
          release 14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
-- EXCLUDE tmnxSvcBsxV8v0Group
           tmnxSvcCondStaticMacGroup,
           tmnxSvcCreation12v0Group,
           tmnxSvcDhcpBgpV7v0Group,
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7450
                  ESS-1 in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                    -- ipsec                (6)
                       ipMirror             (7),
                       video                (8),
                    -- reserved9            (9)
                       aarp                 (10)
                    }
            DESCRIPTION
                 "The values - 'cem (5)', - 'ipsec (6)' are not supported on
                  Nokia 7450 ESS-1."

        VARIATION   svcApipeInterworking
            SYNTAX  INTEGER {
                       none                 (1),
                       frf-5                (2)
                    -- frf-8-2-translate(3)
                    }
            DESCRIPTION
                 "The enumeration 'frf-8-2-translate (3)' is not supported."

        VARIATION   svcEpipeBackboneForceQTagFwd
            ACCESS  not-implemented
            DESCRIPTION
                 "svcEpipeBackboneForceQTagFwd is not implemented on Nokia 7450
                  ESS-1 in release 14.0."

        VARIATION   svcEpipePerSvcHashing
            ACCESS  not-implemented
            DESCRIPTION
                 "svcEpipePerSvcHashing is not implemented on Nokia 7450 ESS-1
                  in release 14.0."

        VARIATION   svcIfSapCfgDefFilterProfile
            ACCESS  not-implemented
            DESCRIPTION
                 "svcIfSapCfgDefFilterProfile is not implemented on Nokia 7450
                  ESS-1 in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMacNotifCount
            ACCESS  not-implemented
            DESCRIPTION
                 "svcMacNotifCount is not implemented on Nokia 7450 ESS-1 in
                  release 14.0."

        VARIATION   svcMacNotifInterval
            ACCESS  not-implemented
            DESCRIPTION
                 "svcMacNotifInterval is not implemented on Nokia 7450 ESS-1 in
                  release 14.0."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsBackboneForceQTagFwd
            ACCESS  not-implemented
            DESCRIPTION
                 "svcTlsBackboneForceQTagFwd is not implemented on Nokia 7450
                  ESS-1 in release 14.0."

        VARIATION   svcTlsMacNotifAdminState
            ACCESS  not-implemented
            DESCRIPTION
                 "svcTlsMacNotifAdminState is not implemented on Nokia 7450
                  ESS-1 in release 14.0."

        VARIATION   svcTlsMacNotifCount
            ACCESS  not-implemented
            DESCRIPTION
                 "svcTlsMacNotifCount is not implemented on Nokia 7450 ESS-1 in
                  release 14.0."

        VARIATION   svcTlsMacNotifInterval
            ACCESS  not-implemented
            DESCRIPTION
                 "svcTlsMacNotifInterval is not implemented on Nokia 7450 ESS-1
                  in release 14.0."

        VARIATION   svcTlsPerSvcHashing
            ACCESS  not-implemented
            DESCRIPTION
                 "svcTlsPerSvcHashing is not implemented on Nokia 7450 ESS-1 in
                  release 14.0."

        VARIATION   svcType
            SYNTAX  INTEGER {
                       epipe                (1),
                       tls                  (3),
                       vprn                 (4),
                       ies                  (5),
                       mirror               (6),
                       apipe                (7),
                       fpipe                (8),
                       ipipe                (9),
                    -- cpipe(10)
                       intTls               (11)
                    }
            DESCRIPTION
                 "The enumeration 'cpipe (10)' is not supported on Nokia 7450
                  ESS-1."

        VARIATION   svcVllType
            SYNTAX  INTEGER {
                       undef                (1),
                       atmSdu               (6),
                       atmCell              (7),
                       atmVcc               (8),
                       atmVpc               (9),
                       frDlci               (10)
                    -- satopE1              (12)
                    -- satopT1              (13)
                    -- satopE3              (14)
                    -- satopT3              (15)
                    -- cesopsn              (16)
                    -- cesopsnCas(17)
                    }
            DESCRIPTION
                 "The values - satopE3 (14), - satopT3 (15), are not supported
                  on Nokia 7450 ESS-1, as they are not implemented.

                  The values - 'satopE1 (12)', - 'satopT1 (13)', - 'cesopsn
                  (16)', - 'cesopsnCas (17)' are not supported on Nokia 7450
                  ESS-1, as CEM is not implemented."

        VARIATION   svcVsdDomainCreationOrigin
            ACCESS  read-only
            DESCRIPTION
                 "svcVsdDomainCreationOrigin is implemented as read-only on
                  Nokia 7450 ESS-1 in release 14.0."

        VARIATION   tlsEgrMcGrpQinqFixedTagPosition
            ACCESS  read-only
            DESCRIPTION
                 "tlsEgrMcGrpQinqFixedTagPosition is supported as read-only."

    ::= { tmnx7450ESS1AgentV14v0  40 }

--
-- 7710 SERVICES CAPABILITIES
--
tmnx7710ServicesV14v0             AGENT-CAPABILITIES
    PRODUCT-RELEASE "Nokia SROS"
    STATUS          current
    DESCRIPTION
         "Implementation of Services capabilities for Nokia 7710 systems release
          14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
           tmnxSvcApipeInfoV9v0Group,
-- EXCLUDE tmnxSvcBsxV8v0Group
           tmnxSvcCondStaticMacGroup,
           tmnxSvcCreation12v0Group,
-- EXCLUDE tmnxSvcDhcpBgpV7v0Group
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7710
                  in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                    -- ipsec                (6)
                       ipMirror             (7)
                    -- video                (8)
                    -- reserved9            (9)
                    -- aarp                 (10)
                    }
            DESCRIPTION
                 "The values - 'cem (5)' - 'ipsec (6)' - 'video (8)' - 'aarp
                  (10)' are not supported on Nokia 7710."

        VARIATION   svcApipeInterworking
            SYNTAX  INTEGER {
                       none                 (1),
                       frf-5                (2)
                    -- frf-8-2-translate(3)
                    }
            DESCRIPTION
                 "The enumeration 'frf-8-2-translate (3)' is not supported."

        VARIATION   svcEpipeBackboneForceQTagFwd
            ACCESS  not-implemented
            DESCRIPTION
                 "svcEpipeBackboneForceQTagFwd is not implemented on Nokia 7710
                  in release 14.0."

        VARIATION   svcEpipePerSvcHashing
            ACCESS  not-implemented
            DESCRIPTION
                 "svcEpipePerSvcHashing is not implemented on Nokia 7710 in
                  release 14.0."

        VARIATION   svcIfSapCfgDefFilterProfile
            ACCESS  not-implemented
            DESCRIPTION
                 "svcIfSapCfgDefFilterProfile is not implemented on Nokia 7710
                  in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMacNotifCount
            ACCESS  not-implemented
            DESCRIPTION
                 "svcMacNotifCount is not implemented on Nokia 7710 in release
                  14.0."

        VARIATION   svcMacNotifInterval
            ACCESS  not-implemented
            DESCRIPTION
                 "svcMacNotifInterval is not implemented on Nokia 7710 in
                  release 14.0."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcTlsBackboneForceQTagFwd
            ACCESS  not-implemented
            DESCRIPTION
                 "svcTlsBackboneForceQTagFwd is not implemented on Nokia 7710 in
                  release 14.0."

        VARIATION   svcTlsMacNotifAdminState
            ACCESS  not-implemented
            DESCRIPTION
                 "svcTlsMacNotifAdminState is not implemented on Nokia 7710 in
                  release 14.0."

        VARIATION   svcTlsMacNotifCount
            ACCESS  not-implemented
            DESCRIPTION
                 "svcTlsMacNotifCount is not implemented on Nokia 7710 in
                  release 14.0."

        VARIATION   svcTlsMacNotifInterval
            ACCESS  not-implemented
            DESCRIPTION
                 "svcTlsMacNotifInterval is not implemented on Nokia 7710 in
                  release 14.0."

        VARIATION   svcTlsPerSvcHashing
            ACCESS  not-implemented
            DESCRIPTION
                 "svcTlsPerSvcHashing is not implemented on Nokia 7710 in
                  release 14.0."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7710, as they are not implemented."

        VARIATION   svcVsdDomainCreationOrigin
            ACCESS  read-only
            DESCRIPTION
                 "svcVsdDomainCreationOrigin is implemented as read-only on
                  Nokia 7710 in release 14.0."

        VARIATION   tlsEgrMcGrpQinqFixedTagPosition
            ACCESS  read-only
            DESCRIPTION
                 "tlsEgrMcGrpQinqFixedTagPosition is supported as read-only."

    ::= { tmnx7710AgentV14v0  40 }

--
-- 7950 SERVICES CAPABILITIES
--
tmnx7950ServicesV14v0             AGENT-CAPABILITIES
    PRODUCT-RELEASE "Nokia SROS"
    STATUS          current
    DESCRIPTION
         "Implementation of Services capabilities for Nokia 7950 systems release
          14.0."

    SUPPORTS        TIMETRA-SERV-MIB
        INCLUDES {
           svcArpHostNotifGroup,
           svcAutoBindTunnelGroup,
           svcAutoBindTunnelSRTEGroup,
           svcBgpAutoRDGroup,
           svcBgpEvpnAutoBindTnlSRTEGroup,
           svcBgpEvpnGroup,
           svcBgpEvpnIPRouteGroup,
           svcBgpEvpnMplsGroup,
           svcBgpEvpnMplsMh1Group,
           svcBgpEvpnMplsMhAdEviRtGroup,
           svcBgpEvpnMplsRcdSrcMacGroup,
           svcBgpEvpnMplsV14v0Group,
           svcBgpEvpnNotifGroup,
           svcBgpEvpnP2mpMldpGroup,
           svcBgpMHSiteGroup,
           svcBgpVpwsGroup,
           svcEpipeBgpEvpnAutoBindTnlGroup,
           svcEpipePwPortGroup,
           svcEvpnAlmpNotifGroup,
           svcEvpnDestNotifGroup,
           svcEvpnMhEsDFNotifGroup,
           svcEvpnMplsNotifGroup,
           svcIgmpTrkGroup,
           svcOperGrpBfdGroup,
           svcRipListenerGroup,
           svcSiteMinDnTimerNotifGroup,
           svcSiteMinDnTimerNotifyObjsGroup,
           svcSpiLoadBalGroup,
           svcTeidLoadBalGroup,
           svcTlsEndPointV7v0Group,
           svcTlsEsPbrL2Group,
           svcTlsEtreeGroup,
           svcTlsFdbMacStatsGroup,
           svcTlsMacV7v0Group,
           svcTlsPbbV14v0Group,
           svcTlsProxyArpNotifGroup,
           svcTlsProxyArpNotifyObjsGroup,
           svcTlsProxyNdNotifGroup,
           svcTlsStaticBHGroup,
           svcTlsVxlanReplicatorNotifGroup,
           svcVplsEvpnInclMcastV14v0Group,
           svcVplsEvpnV14v0Group,
           svcVprnEsPbrL3Group,
           svcVsdGroup,
           svcVxlan14v0NotifGroup,
           svcVxlanV14v0Group,
           tmnxApipeV3v0Group,
           tmnxArpHostBgpGroup,
           tmnxArpHostNotifyGroup,
           tmnxArpHostV11v0Group,
           tmnxArpHostV13v0Group,
           tmnxCustV14v0Group,
           tmnxCustV9v0Group,
           tmnxIesIfRtrSolicitGroup,
-- EXCLUDE tmnxSvcApipeInfoV9v0Group
-- EXCLUDE tmnxSvcBsxV8v0Group
           tmnxSvcCondStaticMacGroup,
           tmnxSvcCreation12v0Group,
-- EXCLUDE tmnxSvcDhcpBgpV7v0Group
           tmnxSvcDhcpV11v0Group,
           tmnxSvcDhcpV13v0Group,
           tmnxSvcEndPointV6v0Group,
           tmnxSvcEpipeV6v0Group,
           tmnxSvcEthCfmGroup,
           tmnxSvcGrpIfGroup,
           tmnxSvcIesIfIpoeV13v0Group,
           tmnxSvcIesIfNHV10v0Group,
           tmnxSvcIesIfV10v0Group,
           tmnxSvcIesIfV11v0Group,
           tmnxSvcIesIfV12v0Group,
           tmnxSvcIesIfV13v0Group,
           tmnxSvcIesIfV6v0Group,
           tmnxSvcIesIfV7v0Group,
           tmnxSvcIesIfV8v0Group,
           tmnxSvcIfDHCP6V6v0Group,
           tmnxSvcInterAsV8v0Group,
           tmnxSvcIpipeFaultPropGroup,
           tmnxSvcIpipeV8v0Group,
           tmnxSvcMCEPNotifyGroup,
           tmnxSvcMHGroup,
           tmnxSvcMSPwPeV9v0Group,
           tmnxSvcMacReNotifyGroup,
           tmnxSvcMrpPolicyV8v0Group,
           tmnxSvcMvrpV8v0Group,
           tmnxSvcNotifyObjsV14v0Group,
           tmnxSvcNotifyObsoletedV11v0Group,
           tmnxSvcNotifyV10v0Group,
           tmnxSvcNotifyV14v0Group,
           tmnxSvcNotifyV8v0Group,
           tmnxSvcNotifyV9v0Group,
           tmnxSvcOperGrpV9v0Group,
           tmnxSvcP2mpGroup,
           tmnxSvcPEObsoletedGroup,
           tmnxSvcPbbMacV12v0Group,
           tmnxSvcPbbMacV7v0Group,
           tmnxSvcPwV8v0Group,
           tmnxSvcQosRateV13v0Group,
           tmnxSvcQosSchedV13v0Group,
           tmnxSvcQosV12v0Group,
           tmnxSvcRadClassGroup,
           tmnxSvcRoutedCOV10v0Group,
           tmnxSvcRoutedCOV13v0Group,
           tmnxSvcRoutedCOV9v0Group,
           tmnxSvcRoutedVplsV8v0Group,
           tmnxSvcSchedulerRateV11v0Group,
           tmnxSvcShcvPolicyGroup,
           tmnxSvcSiteV8v0Group,
           tmnxSvcSpbGroup,
           tmnxSvcSpbV11v0Group,
           tmnxSvcSysVxlanARGroup,
           tmnxSvcSysVxlanTunTermGroup,
           tmnxSvcTestGroup,
           tmnxSvcTlsBackbone6v1Group,
           tmnxSvcTlsBgpV8v0Group,
           tmnxSvcTlsEgrV6v0Group,
           tmnxSvcTlsEvpnProxyArpGroup,
           tmnxSvcTlsFdbV7v0Group,
           tmnxSvcTlsMFibV13v0Group,
           tmnxSvcTlsMFibV6v0Group,
           tmnxSvcTlsMstiV6v0Group,
           tmnxSvcTlsPipV7v0Group,
           tmnxSvcTlsPipV8v0Group,
           tmnxSvcTlsProxyArpEnhGroup,
           tmnxSvcTlsProxyArpGroup,
           tmnxSvcTlsProxyNdGroup,
           tmnxSvcTlsShgV6v0Group,
           tmnxSvcTlsV6v0Group,
           tmnxSvcTlsV7v0Group,
           tmnxSvcV10v0Group,
           tmnxSvcV12v0Group,
           tmnxSvcV13v0Group,
           tmnxSvcV14v0Group,
           tmnxSvcV7v0Group,
           tmnxSvcV8v0Group,
           tmnxSvcV9v0Group,
           tmnxSvcV9v0R4Group,
           tmnxSvcVllBgpEvpnGroup,
           tmnxSvcVllBgpGroup,
           tmnxSvcVplsGroup,
           tmnxSvcVprnV13v0Group,
           tmnxSvcVsdDynamicSvcGroup,
           tmnxSvcVsdGlobalObjsV13v0Group
        }

        VARIATION   custMultSvcSiteSubscriberMss
            ACCESS  not-implemented
            DESCRIPTION
                 "custMultSvcSiteSubscriberMss is not implemented on Nokia 7950
                  in release 14.0."

        VARIATION   iesIfDefaultPrimaryDnsIPv6Addr
            ACCESS  read-create
            DESCRIPTION
                 "The object iesIfDefaultPrimaryDnsIPv6Addr is not supported.

                  It is not allowed to set it to a value other than its default
                  value."

        VARIATION   iesIfDefaultSecondaryDnsIPv6Addr
            ACCESS  read-create
            DESCRIPTION
                 "The object iesIfDefaultSecondaryDnsIPv6Addr is not supported.

                  It is not allowed to set it to a value other than its default
                  value."

        VARIATION   iesIfIsaTnlNHDynAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHDynAddrType supports only the InetAddressType
                  values 'unknown (0)' and 'ipv4 (1)'."

        VARIATION   iesIfIsaTnlNHStaticAddrType
            SYNTAX  InetAddressType {
                       unknown              (0),
                       ipv4                 (1)
                    -- ipv6                 (2)
                    -- ipv4z                (3)
                    -- ipv6z                (4)
                    -- dns                  (16)
                    }
            DESCRIPTION
                 "iesIfIsaTnlNHStaticAddrType supports only the InetAddressType
                  values 'unknown (0)' and 'ipv4 (1)'."

        VARIATION   iesIfType
            SYNTAX  INTEGER {
                       service              (1),
                       subscriber           (2),
                       group                (3),
                       redundant            (4),
                    -- cem                  (5)
                       ipsec                (6),
                       ipMirror             (7),
                       video                (8),
                    -- reserved9            (9)
                       aarp                 (10)
                    }
            DESCRIPTION
                 "The values 'cem(5)' and 'reserved9(9)' are not supported on
                  SROS systems."

        VARIATION   svcApipeInterworking
            SYNTAX  INTEGER {
                       none                 (1),
                       frf-5                (2)
                    -- frf-8-2-translate(3)
                    }
            DESCRIPTION
                 "The enumeration 'frf-8-2-translate (3)' is not supported."

        VARIATION   svcIfSapCfgDefFilterProfile
            ACCESS  not-implemented
            DESCRIPTION
                 "svcIfSapCfgDefFilterProfile is not implemented on Nokia 7950
                  in release 14.0."

        VARIATION   svcIfSapCfgDefSubIdent
            SYNTAX  INTEGER {
                    -- useSapId             (1)
                       useString            (2),
                       useAutoId            (3)
                    }
            DESCRIPTION
                 "svcIfSapCfgDefSubIdent only supports the value 'useString (2)'
                  and 'useAutoId (3)'."

        VARIATION   svcMrpPolicyParamsRowStatus
            SYNTAX  RowStatus {
                       active               (1),
                    -- notInService         (2)
                    -- notReady             (3)
                       createAndGo          (4),
                    -- createAndWait        (5)
                       destroy              (6)
                    }
            DESCRIPTION
                 "svcMrpPolicyParamsRowStatus supports only 'active (1)',
                  'createAndGo (4)', and 'destroy (6)'."

        VARIATION   svcPEDiscPolServerRowStatus
            SYNTAX  RowStatus {
                       active               (1),
                    -- notInService         (2)
                    -- notReady             (3)
                       createAndGo          (4),
                    -- createAndWait        (5)
                       destroy              (6)
                    }
            DESCRIPTION
                 "svcPEDiscPolServerRowStatus supports only 'active (1)',
                  'createAndGo (4)', and 'destroy (6)'."

        VARIATION   svcPEDiscoveryPolicyRowStatus
            SYNTAX  RowStatus {
                       active               (1),
                    -- notInService         (2)
                    -- notReady             (3)
                       createAndGo          (4),
                    -- createAndWait        (5)
                       destroy              (6)
                    }
            DESCRIPTION
                 "svcPEDiscoveryPolicyRowStatus supports only 'active (1)',
                  'createAndGo (4)', and 'destroy (6)'."

        VARIATION   svcVllType
            SYNTAX  INTEGER {
                       undef                (1),
                       atmSdu               (6),
                       atmCell              (7),
                       atmVcc               (8),
                       atmVpc               (9),
                       frDlci               (10),
                       satopE1              (12),
                       satopT1              (13),
                    -- satopE3              (14)
                    -- satopT3              (15)
                       cesopsn              (16),
                       cesopsnCas(17)
                    }
            DESCRIPTION
                 "The enumerations - satopE3 (14), - satopT3 (15), are not
                  supported on Nokia 7950, as they are not implemented."

        VARIATION   svcVsdDomainCreationOrigin
            ACCESS  read-only
            DESCRIPTION
                 "svcVsdDomainCreationOrigin is implemented as read-only on
                  Nokia 7950 in release 14.0."

        VARIATION   tlsEgrMcGrpQinqFixedTagPosition
            ACCESS  read-only
            DESCRIPTION
                 "tlsEgrMcGrpQinqFixedTagPosition is supported as read-only."

    ::= { tmnx7950AgentV14v0  40 }

--
-- 7750SR-12e SFLOW CAPABILITIES
--
tmnx7750SR12eSflowV14v0           AGENT-CAPABILITIES
    PRODUCT-RELEASE "Nokia SROS"
    STATUS          current
    DESCRIPTION
         "Implementation of sFlow protocol capabilities for Nokia 7750 SR-12e
          systems release 14.0."

    SUPPORTS        SFLOW-MIB
        INCLUDES {
           sFlowAgentGroup
        }

        VARIATION   sFlowCpInterval
            ACCESS  read-only
            DESCRIPTION
                 "sFlowCpInterval is implemented as read-only on Nokia 7750
                  SR-12e in release 14.0."

        VARIATION   sFlowFsTable
            ACCESS  not-implemented
            DESCRIPTION
                 "sFlowFsTable was not implemented."

        VARIATION   sFlowRcvrAddressType
            SYNTAX  InetAddressType {
                       unknown              (0),
                       ipv4                 (1),
                       ipv6                 (2)
                    -- ipv4z                (3)
                    -- ipv6z                (4)
                    -- dns                  (16)
                    }
            DESCRIPTION
                 "sFlowRcvrAddressType supports only the InetAddressType values
                  'unknown (0)', 'ipv4 (1)', and 'ipv6 (2)'."

        VARIATION   sFlowRcvrPort
            SYNTAX  Integer32 (1..65535)
            DESCRIPTION
                 "sFlowRcvrPort supports the range 1..65535."

        VARIATION   sFlowRcvrTimeout
            ACCESS  not-implemented
            DESCRIPTION
                 "sFlowRcvrTimeout was not implemented."

    SUPPORTS        TIMETRA-SFLOW-MIB
        INCLUDES {
           tmnxSflowConfigV12v0Group,
           tmnxSflowNotifV12v0Group,
           tmnxSflowNotifyObjsV12v0Group,
           tmnxSflowRcvrStatsV12v0Group,
           tmnxSflowTimeStampV12v0Group
        }

        VARIATION   tmnxSflowCpRowStatus
            SYNTAX  RowStatus {
                       active               (1),
                    -- notInService         (2)
                    -- notReady             (3)
                       createAndGo          (4),
                    -- createAndWait        (5)
                       destroy              (6)
                    }
            DESCRIPTION
                 "tmnxSflowCpRowStatus supports only 'active (1)', 'createAndGo
                  (4)', and 'destroy (6)'."

        VARIATION   tmnxSflowEgrCMapPlcrRowStatus
            SYNTAX  RowStatus {
                       active               (1),
                    -- notInService         (2)
                    -- notReady             (3)
                       createAndGo          (4),
                    -- createAndWait        (5)
                       destroy              (6)
                    }
            DESCRIPTION
                 "tmnxSflowEgrCMapPlcrRowStatus supports only 'active (1)',
                  'createAndGo (4)', and 'destroy (6)'."

        VARIATION   tmnxSflowEgrCMapQueueRowStatus
            SYNTAX  RowStatus {
                       active               (1),
                    -- notInService         (2)
                    -- notReady             (3)
                       createAndGo          (4),
                    -- createAndWait        (5)
                       destroy              (6)
                    }
            DESCRIPTION
                 "tmnxSflowEgrCMapQueueRowStatus supports only 'active (1)',
                  'createAndGo (4)', and 'destroy (6)'."

        VARIATION   tmnxSflowIngCMapPlcrRowStatus
            SYNTAX  RowStatus {
                       active               (1),
                    -- notInService         (2)
                    -- notReady             (3)
                       createAndGo          (4),
                    -- createAndWait        (5)
                       destroy              (6)
                    }
            DESCRIPTION
                 "tmnxSflowIngCMapPlcrRowStatus supports only 'active (1)',
                  'createAndGo (4)', and 'destroy (6)'."

        VARIATION   tmnxSflowIngCMapQueueRowStatus
            SYNTAX  RowStatus {
                       active               (1),
                    -- notInService         (2)
                    -- notReady             (3)
                       createAndGo          (4),
                    -- createAndWait        (5)
                       destroy              (6)
                    }
            DESCRIPTION
                 "tmnxSflowIngCMapQueueRowStatus supports only 'active (1)',
                  'createAndGo (4)', and 'destroy (6)'."

        VARIATION   tmnxSflowRcvrBackupAddressType
            SYNTAX  InetAddressType {
                       unknown              (0),
                       ipv4                 (1),
                       ipv6                 (2)
                    -- ipv4z                (3)
                    -- ipv6z                (4)
                    -- dns                  (16)
                    }
            DESCRIPTION
                 "tmnxSflowRcvrBackupAddressType supports only the
                  InetAddressType values 'unknown (0)', 'ipv4 (1)', and 'ipv6
                  (2)'."

    ::= { tmnx7750SR12eAgentV14v0  91 }

--
-- 7950 SFLOW CAPABILITIES
--
tmnx7950SflowV14v0                AGENT-CAPABILITIES
    PRODUCT-RELEASE "Nokia SROS"
    STATUS          current
    DESCRIPTION
         "Implementation of sFlow protocol capabilities for Nokia 7950 systems
          release 14.0."

    SUPPORTS        SFLOW-MIB
        INCLUDES {
           sFlowAgentGroup
        }

        VARIATION   sFlowCpInterval
            ACCESS  read-only
            DESCRIPTION
                 "sFlowCpInterval is implemented as read-only on Nokia 7950 in
                  release 14.0."

        VARIATION   sFlowFsTable
            ACCESS  not-implemented
            DESCRIPTION
                 "sFlowFsTable was not implemented."

        VARIATION   sFlowRcvrAddressType
            SYNTAX  InetAddressType {
                       unknown              (0),
                       ipv4                 (1),
                       ipv6                 (2)
                    -- ipv4z                (3)
                    -- ipv6z                (4)
                    -- dns                  (16)
                    }
            DESCRIPTION
                 "sFlowRcvrAddressType supports only the InetAddressType values
                  'unknown (0)', 'ipv4 (1)', and 'ipv6 (2)'."

        VARIATION   sFlowRcvrPort
            SYNTAX  Integer32 (1..65535)
            DESCRIPTION
                 "sFlowRcvrPort supports the range 1..65535."

        VARIATION   sFlowRcvrTimeout
            ACCESS  not-implemented
            DESCRIPTION
                 "sFlowRcvrTimeout was not implemented."

    SUPPORTS        TIMETRA-SFLOW-MIB
        INCLUDES {
           tmnxSflowConfigV12v0Group,
           tmnxSflowNotifV12v0Group,
           tmnxSflowNotifyObjsV12v0Group,
           tmnxSflowRcvrStatsV12v0Group,
           tmnxSflowTimeStampV12v0Group
        }

        VARIATION   tmnxSflowCpRowStatus
            SYNTAX  RowStatus {
                       active               (1),
                    -- notInService         (2)
                    -- notReady             (3)
                       createAndGo          (4),
                    -- createAndWait        (5)
                       destroy              (6)
                    }
            DESCRIPTION
                 "tmnxSflowCpRowStatus supports only 'active (1)', 'createAndGo
                  (4)', and 'destroy (6)'."

        VARIATION   tmnxSflowEgrCMapPlcrRowStatus
            SYNTAX  RowStatus {
                       active               (1),
                    -- notInService         (2)
                    -- notReady             (3)
                       createAndGo          (4),
                    -- createAndWait        (5)
                       destroy              (6)
                    }
            DESCRIPTION
                 "tmnxSflowEgrCMapPlcrRowStatus supports only 'active (1)',
                  'createAndGo (4)', and 'destroy (6)'."

        VARIATION   tmnxSflowEgrCMapQueueRowStatus
            SYNTAX  RowStatus {
                       active               (1),
                    -- notInService         (2)
                    -- notReady             (3)
                       createAndGo          (4),
                    -- createAndWait        (5)
                       destroy              (6)
                    }
            DESCRIPTION
                 "tmnxSflowEgrCMapQueueRowStatus supports only 'active (1)',
                  'createAndGo (4)', and 'destroy (6)'."

        VARIATION   tmnxSflowIngCMapPlcrRowStatus
            SYNTAX  RowStatus {
                       active               (1),
                    -- notInService         (2)
                    -- notReady             (3)
                       createAndGo          (4),
                    -- createAndWait        (5)
                       destroy              (6)
                    }
            DESCRIPTION
                 "tmnxSflowIngCMapPlcrRowStatus supports only 'active (1)',
                  'createAndGo (4)', and 'destroy (6)'."

        VARIATION   tmnxSflowIngCMapQueueRowStatus
            SYNTAX  RowStatus {
                       active               (1),
                    -- notInService         (2)
                    -- notReady             (3)
                       createAndGo          (4),
                    -- createAndWait        (5)
                       destroy              (6)
                    }
            DESCRIPTION
                 "tmnxSflowIngCMapQueueRowStatus supports only 'active (1)',
                  'createAndGo (4)', and 'destroy (6)'."

        VARIATION   tmnxSflowRcvrBackupAddressType
            SYNTAX  InetAddressType {
                       unknown              (0),
                       ipv4                 (1),
                       ipv6                 (2)
                    -- ipv4z                (3)
                    -- ipv6z                (4)
                    -- dns                  (16)
                    }
            DESCRIPTION
                 "tmnxSflowRcvrBackupAddressType supports only the
                  InetAddressType values 'unknown (0)', 'ipv4 (1)', and 'ipv6
                  (2)'."

    ::= { tmnx7950AgentV14v0  91 }

--
-- SROS SNMP CAPABILITIES
--
tmnxSROSSnmpV14v0                 AGENT-CAPABILITIES
    PRODUCT-RELEASE "Nokia SROS"
    STATUS          current
    DESCRIPTION
         "Implementation of SNMP capabilities for Nokia SROS systems release
          14.0."

    SUPPORTS        SNMP-COMMUNITY-MIB
        INCLUDES {
           snmpCommunityTableGroup
        }

        VARIATION   snmpCommunityContextEngineID
            ACCESS  read-only
            DESCRIPTION
                 "The snmpCommunityContextEngineID is implemented as read-only
                  because only one SNMP Engine ID is supported. The engine ID
                  may change when a redundancy failover from active to standby
                  CPM happens."

        VARIATION   snmpCommunityIndex
            SYNTAX  SnmpAdminString (SIZE(1..64))
            DESCRIPTION
                 "The maximum length for snmpCommunityIndex for the base log
                  instance is 32.

                  The maximum length for snmpCommunityIndex for the vprn
                  context is 64."

        VARIATION   snmpCommunitySecurityName
            SYNTAX  SnmpAdminString (SIZE(1..64))
            DESCRIPTION
                 "The maximum length for snmpCommunitySecurityName for the base
                  log instance is 32.

                  The maximum length for snmpCommunitySecurityName for the vprn
                  context is 64."

    SUPPORTS        SNMP-FRAMEWORK-MIB
        INCLUDES {
           snmpEngineGroup
        }

    SUPPORTS        SNMP-MPD-MIB
        INCLUDES {
           snmpMPDGroup
        }

    SUPPORTS        SNMP-NOTIFICATION-MIB
        INCLUDES {
           snmpNotifyFilterGroup,
           snmpNotifyGroup
        }

        VARIATION   snmpNotifyFilterProfileTable
            ACCESS  not-implemented
            DESCRIPTION
                 "snmpNotifyFilterProfileTable is not implemented on Nokia SROS
                  in release 14.0."

        VARIATION   snmpNotifyFilterTable
            ACCESS  not-implemented
            DESCRIPTION
                 "snmpNotifyFilterTable is not implemented on Nokia SROS in
                  release 14.0."

        VARIATION   snmpNotifyRowStatus
            DESCRIPTION
                 "The only values allowed for the snmpNotifyName index is the
                  ASCII numerical value of the TiMOS event log ID that the
                  notification group is associated with. Event log IDs have a
                  range of [1..100]. Leading zero, '0', characters are not
                  allowed."

        VARIATION   snmpNotifyType
            SYNTAX  INTEGER {
                       trap(1)
                    }
            DESCRIPTION
                 "The only value allowed for the snmpNotifyType object is
                  'trap'. The TiMOS agent does not support 'inform'."

    SUPPORTS        SNMP-TARGET-MIB
        INCLUDES {
           snmpTargetBasicGroup
-- EXCLUDE snmpTargetCommandResponderGroup
-- EXCLUDE snmpTargetResponseGroup
        }

        VARIATION   snmpTargetAddrName
            SYNTAX  SnmpAdminString (SIZE(1..46))
            DESCRIPTION
                 "The maximum length for target address name for base log
                  instance is 32.

                  The maximum length for target address name for vprn context
                  is 46."

        VARIATION   snmpTargetAddrParams
            SYNTAX  SnmpAdminString (SIZE(1..46))
            DESCRIPTION
                 "The maximum length for SNMP target parameters for base log
                  instance is 32.

                  The maximum length for SNMP target parameters for vprn
                  context is 46."

        VARIATION   snmpTargetParamsName
            SYNTAX  SnmpAdminString (SIZE(1..46))
            DESCRIPTION
                 "The maximum length for SNMP target parameters name for base
                  log instance is 32.

                  The maximum length for SNMP target parameters name for vprn
                  context is 46."

        VARIATION   snmpTargetParamsSecurityName
            SYNTAX  DisplayString (SIZE(0..46))
            DESCRIPTION
                 "The maximum length supported for target parameters security
                  name for base log instance is 32.

                  The maximum length supported for target parameters security
                  name for vprn context is 46."

    SUPPORTS        SNMP-USER-BASED-SM-MIB
        INCLUDES {
           usmMIBBasicGroup
        }

        VARIATION   usmUserStorageType
            SYNTAX  INTEGER {
                    -- other                (1)
                    -- volatile             (2)
                       nonVolatile          (3)
                    -- permanent            (4)
                    -- readOnly             (5)
                    }
            DESCRIPTION
                 "Only the StorageType TC value 'nonVolatile (3)' is supported
                  for usmUserStorageType."

    SUPPORTS        SNMP-VIEW-BASED-ACM-MIB
        INCLUDES {
           vacmBasicGroup
        }

        VARIATION   vacmSecurityName
            SYNTAX  SnmpAdminString (SIZE(1..64))
            DESCRIPTION
                 "The maximum length supported for vacmSecurityName for base log
                  instance is 32.

                  The maximum length supported for vacmSecurityName for vprn
                  context is 64."

    SUPPORTS        SNMPv2-MIB
        INCLUDES {
           snmpBasicNotificationsGroup,
           snmpCommunityGroup,
           snmpGroup,
           snmpNotificationGroup,
           snmpObsoleteGroup,
-- EXCLUDE snmpSetGroup
           snmpWarmStartNotificationGroup,
           systemGroup
        }

        VARIATION   coldStart
            DESCRIPTION
                 "The coldStart notification is generated on all system reboots
                  - not only for power cycle reboots."

        VARIATION   snmpInBadValues
            DESCRIPTION
                 "This object was defined in RFC1213 for SNMPv1 agents but it
                  was made obsolete in SNMPv2-MIB. However, many customers and
                  NMS developers find this counter useful so this agent
                  continues to support it."

        VARIATION   snmpInGenErrs
            DESCRIPTION
                 "This object was defined in RFC1213 for SNMPv1 agents but it
                  was made obsolete in SNMPv2-MIB. However, many customers and
                  NMS developers find this counter useful so this agent
                  continues to support it."

        VARIATION   snmpInGetNexts
            DESCRIPTION
                 "This object was defined in RFC1213 for SNMPv1 agents but it
                  was made obsolete in SNMPv2-MIB. However, many customers and
                  NMS developers find this counter useful so this agent
                  continues to support it."

        VARIATION   snmpInGetRequests
            DESCRIPTION
                 "This object was defined in RFC1213 for SNMPv1 agents but it
                  was made obsolete in SNMPv2-MIB. However, many customers and
                  NMS developers find this counter useful so this agent
                  continues to support it."

        VARIATION   snmpInGetResponses
            DESCRIPTION
                 "This object was defined in RFC1213 for SNMPv1 agents but it
                  was made obsolete in SNMPv2-MIB. However, many customers and
                  NMS developers find this counter useful so this agent
                  continues to support it."

        VARIATION   snmpInNoSuchNames
            DESCRIPTION
                 "This object was defined in RFC1213 for SNMPv1 agents but it
                  was made obsolete in SNMPv2-MIB. However, many customers and
                  NMS developers find this counter useful so this agent
                  continues to support it."

        VARIATION   snmpInReadOnlys
            DESCRIPTION
                 "This object was defined in RFC1213 for SNMPv1 agents but it
                  was made obsolete in SNMPv2-MIB. However, many customers and
                  NMS developers find this counter useful so this agent
                  continues to support it."

        VARIATION   snmpInSetRequests
            DESCRIPTION
                 "This object was defined in RFC1213 for SNMPv1 agents but it
                  was made obsolete in SNMPv2-MIB. However, many customers and
                  NMS developers find this counter useful so this agent
                  continues to support it."

        VARIATION   snmpInTooBigs
            DESCRIPTION
                 "This object was defined in RFC1213 for SNMPv1 agents but it
                  was made obsolete in SNMPv2-MIB. However, many customers and
                  NMS developers find this counter useful so this agent
                  continues to support it."

        VARIATION   snmpInTotalReqVars
            DESCRIPTION
                 "This object was defined in RFC1213 for SNMPv1 agents but it
                  was made obsolete in SNMPv2-MIB. However, many customers and
                  NMS developers find this counter useful so this agent
                  continues to support it."

        VARIATION   snmpInTotalSetVars
            DESCRIPTION
                 "This object was defined in RFC1213 for SNMPv1 agents but it
                  was made obsolete in SNMPv2-MIB. However, many customers and
                  NMS developers find this counter useful so this agent
                  continues to support it."

        VARIATION   snmpInTraps
            DESCRIPTION
                 "This object was defined in RFC1213 for SNMPv1 agents but it
                  was made obsolete in SNMPv2-MIB. However, many customers and
                  NMS developers find this counter useful so this agent
                  continues to support it."

        VARIATION   snmpOutBadValues
            DESCRIPTION
                 "This object was defined in RFC1213 for SNMPv1 agents but it
                  was made obsolete in SNMPv2-MIB. However, many customers and
                  NMS developers find this counter useful so this agent
                  continues to support it."

        VARIATION   snmpOutGenErrs
            DESCRIPTION
                 "This object was defined in RFC1213 for SNMPv1 agents but it
                  was made obsolete in SNMPv2-MIB. However, many customers and
                  NMS developers find this counter useful so this agent
                  continues to support it."

        VARIATION   snmpOutGetNexts
            DESCRIPTION
                 "This object was defined in RFC1213 for SNMPv1 agents but it
                  was made obsolete in SNMPv2-MIB. However, many customers and
                  NMS developers find this counter useful so this agent
                  continues to support it."

        VARIATION   snmpOutGetRequests
            DESCRIPTION
                 "This object was defined in RFC1213 for SNMPv1 agents but it
                  was made obsolete in SNMPv2-MIB. However, many customers and
                  NMS developers find this counter useful so this agent
                  continues to support it."

        VARIATION   snmpOutGetResponses
            DESCRIPTION
                 "This object was defined in RFC1213 for SNMPv1 agents but it
                  was made obsolete in SNMPv2-MIB. However, many customers and
                  NMS developers find this counter useful so this agent
                  continues to support it."

        VARIATION   snmpOutNoSuchNames
            DESCRIPTION
                 "This object was defined in RFC1213 for SNMPv1 agents but it
                  was made obsolete in SNMPv2-MIB. However, many customers and
                  NMS developers find this counter useful so this agent
                  continues to support it."

        VARIATION   snmpOutPkts
            DESCRIPTION
                 "This object was defined in RFC1213 for SNMPv1 agents but it
                  was made obsolete in SNMPv2-MIB. However, many customers and
                  NMS developers find this counter useful so this agent
                  continues to support it."

        VARIATION   snmpOutSetRequests
            DESCRIPTION
                 "This object was defined in RFC1213 for SNMPv1 agents but it
                  was made obsolete in SNMPv2-MIB. However, many customers and
                  NMS developers find this counter useful so this agent
                  continues to support it."

        VARIATION   snmpOutTooBigs
            DESCRIPTION
                 "This object was defined in RFC1213 for SNMPv1 agents but it
                  was made obsolete in SNMPv2-MIB. However, many customers and
                  NMS developers find this counter useful so this agent
                  continues to support it."

        VARIATION   snmpOutTraps
            DESCRIPTION
                 "This object was defined in RFC1213 for SNMPv1 agents but it
                  was made obsolete in SNMPv2-MIB. However, many customers and
                  NMS developers find this counter useful so this agent
                  continues to support it."

        VARIATION   sysContact
            SYNTAX  DisplayString (SIZE(0..80))
            DESCRIPTION
                 "The maximum length supported for the system contact is 80
                  characters."

        VARIATION   sysLocation
            SYNTAX  DisplayString (SIZE(0..80))
            DESCRIPTION
                 "The maximum length supported for the system contact is 80
                  characters."

        VARIATION   sysName
            SYNTAX  DisplayString (SIZE(0..32))
            DESCRIPTION
                 "The maximum length supported for the system name is 32
                  characters. Setting sysName to the empty string, ''H, resets
                  sysName to the TiMOS default value."

        VARIATION   sysORLastChange
            ACCESS  not-implemented
            DESCRIPTION
                 "sysORLastChange is not implemented on Nokia SROS in release
                  14.0."

        VARIATION   sysORTable
            ACCESS  not-implemented
            DESCRIPTION
                 "sysORTable is not implemented on Nokia SROS in release 14.0."

        VARIATION   warmStart
            DESCRIPTION
                 "The warmStart notification is generated by the new active CPM
                  following a CPM switchover. This notification has been
                  supported starting with the SROS 2.1 release.

                  When the standby CPM card takes over following a failure or
                  reboot of the active CPM card, tmnxRedPrimaryCPMFail,
                  sbiBootConfig and sbiBootSnmpd events from the
                  TIMETRA-SYSTEM-MIB are generated to indicate the secondary CPM
                  has successfully taken control of the system."

    ::= { tmnxSROSAgentV14v0  41 }

--
-- SROS SONET CAPABILITIES
--
tmnxSROSSonetV14v0                AGENT-CAPABILITIES
    PRODUCT-RELEASE "Nokia SROS"
    STATUS          current
    DESCRIPTION
         "Implementation of SONET Interface Types capabilities for Nokia SROS
          systems release 14.0."

    SUPPORTS        SONET-MIB
        INCLUDES {
           sonetFarEndLineStuff2,
           sonetFarEndPathStuff2,
           sonetLineStuff2,
           sonetMediumStuff2,
           sonetPathStuff2,
           sonetSectionStuff2,
           sonetVTStuff2
        }

        VARIATION   sonetMediumCircuitIdentifier
            ACCESS  read-only
            DESCRIPTION
                 "sonetMediumCircuitIdentifier is implemented as read-only on
                  Nokia SROS in release 14.0."

        VARIATION   sonetMediumLineCoding
            ACCESS  read-only
            DESCRIPTION
                 "sonetMediumLineCoding is implemented as read-only on Nokia
                  SROS in release 14.0."

        VARIATION   sonetMediumLineType
            ACCESS  read-only
            DESCRIPTION
                 "sonetMediumLineType is implemented as read-only on Nokia SROS
                  in release 14.0."

        VARIATION   sonetMediumLoopbackConfig
            ACCESS  read-only
            DESCRIPTION
                 "sonetMediumLoopbackConfig is implemented as read-only on Nokia
                  SROS in release 14.0."

        VARIATION   sonetMediumType
            ACCESS  read-only
            DESCRIPTION
                 "sonetMediumType is implemented as read-only on Nokia SROS in
                  release 14.0."

        VARIATION   sonetPathCurrentWidth
            ACCESS  read-only
            DESCRIPTION
                 "sonetPathCurrentWidth is implemented as read-only on Nokia
                  SROS in release 14.0."

        VARIATION   sonetSESthresholdSet
            ACCESS  read-only
            DESCRIPTION
                 "sonetSESthresholdSet is implemented as read-only on Nokia SROS
                  in release 14.0."

        VARIATION   sonetVTCurrentWidth
            ACCESS  read-only
            DESCRIPTION
                 "sonetVTCurrentWidth is implemented as read-only on Nokia SROS
                  in release 14.0."

    ::= { tmnxSROSAgentV14v0  42 }

--
-- 7950 SONET CAPABILITIES
--
tmnx7950SonetV14v0                AGENT-CAPABILITIES
    PRODUCT-RELEASE "Nokia SROS"
    STATUS          current
    DESCRIPTION
         "Implementation of SONET Interface Types capabilities for Nokia 7950
          systems release 14.0."

--    SUPPORTS        SONET-MIB
--        INCLUDES {
--        }

    ::= { tmnx7950AgentV14v0  42 }

--
-- SROS SUBSCR_MGMT CAPABILITIES
--
tmnxSROSSubscrMgmtV14v0           AGENT-CAPABILITIES
    PRODUCT-RELEASE "Nokia SROS"
    STATUS          current
    DESCRIPTION
         "Implementation of Subscriber Management capabilities for Nokia SROS
          systems release 14.0."

    SUPPORTS        TIMETRA-SUBSCRIBER-MGMT-MIB
        INCLUDES {
           tmnxCcIpFltrV8v0Group,
           tmnxCcIpv6FltrV8v0Group,
           tmnxHsmdaSubscriberV10v0Group,
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
           tmnxSubBsxObjV9v0Group,
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
           tmnxSubHsmdaGroup,
           tmnxSubHsmdaV12v0Group,
           tmnxSubHsmdaV14v0Group,
           tmnxSubHttpRedirectGroup,
           tmnxSubHttpRedirectV12v0Group,
           tmnxSubIpoeLinkV10v0Group,
           tmnxSubIpoeV13v0Group,
           tmnxSubIpoeV14v0Group,
           tmnxSubL2tpGroup,
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
           tmnxSubNatV14v0Group,
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
           tmnxSubQosParentLocV12v0Group,
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia SROS
                  in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia SROS in
                  release 14.0."

        VARIATION   tmnxSubFlterProfTbleLastMgmtChg
            ACCESS  not-implemented
            DESCRIPTION
                 "tmnxSubFlterProfTbleLastMgmtChg is not implemented on Nokia
                  SROS in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  SROS in release 14.0."

        VARIATION   tmnxSubIPolRejectUnknownStrings
            ACCESS  not-implemented
            DESCRIPTION
                 "tmnxSubIPolRejectUnknownStrings is not implemented on Nokia
                  SROS in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  SROS in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia SROS in
                  release 14.0."

        VARIATION   tmnxSubInfoMssName
            ACCESS  not-implemented
            DESCRIPTION
                 "tmnxSubInfoMssName is not implemented on Nokia SROS in release
                  14.0."

        VARIATION   tmnxSubProfFltrProfileMapTable
            ACCESS  not-implemented
            DESCRIPTION
                 "tmnxSubProfFltrProfileMapTable is not implemented on Nokia
                  SROS in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  SROS in release 14.0."

        VARIATION   tmnxSubProfUseSubscriberMss
            ACCESS  not-implemented
            DESCRIPTION
                 "tmnxSubProfUseSubscriberMss is not implemented on Nokia SROS
                  in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnxSROSAgentV14v0  47 }

--
-- 7750SR-1 SUBSCR_MGMT CAPABILITIES
--
tmnx7750SR1SubscrMgmtV14v0        AGENT-CAPABILITIES
    PRODUCT-RELEASE "Nokia SROS"
    STATUS          current
    DESCRIPTION
         "Implementation of Subscriber Management capabilities for Nokia 7750
          SR-1 systems release 14.0."

    SUPPORTS        TIMETRA-SUBSCRIBER-MGMT-MIB
        INCLUDES {
           tmnxCcIpFltrV8v0Group,
           tmnxCcIpv6FltrV8v0Group,
           tmnxHsmdaSubscriberV10v0Group,
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
-- EXCLUDE tmnxSubBsxObjV9v0Group
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
           tmnxSubHsmdaGroup,
           tmnxSubHsmdaV12v0Group,
           tmnxSubHsmdaV14v0Group,
           tmnxSubHttpRedirectGroup,
           tmnxSubHttpRedirectV12v0Group,
           tmnxSubIpoeLinkV10v0Group,
           tmnxSubIpoeV13v0Group,
           tmnxSubIpoeV14v0Group,
           tmnxSubL2tpGroup,
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
           tmnxSubNatV14v0Group,
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
           tmnxSubQosParentLocV12v0Group,
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia 7750
                  SR-1 in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubApCategoryEgressPolicers
            ACCESS  not-implemented
            DESCRIPTION
                 "tmnxSubApCategoryEgressPolicers is not implemented on Nokia
                  7750 SR-1 in release 14.0."

        VARIATION   tmnxSubApCategoryIngressPolicers
            ACCESS  not-implemented
            DESCRIPTION
                 "tmnxSubApCategoryIngressPolicers is not implemented on Nokia
                  7750 SR-1 in release 14.0."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia 7750
                  SR-1 in release 14.0."

        VARIATION   tmnxSubFlterProfTbleLastMgmtChg
            ACCESS  not-implemented
            DESCRIPTION
                 "tmnxSubFlterProfTbleLastMgmtChg is not implemented on Nokia
                  7750 SR-1 in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  7750 SR-1 in release 14.0."

        VARIATION   tmnxSubIPolRejectUnknownStrings
            ACCESS  not-implemented
            DESCRIPTION
                 "tmnxSubIPolRejectUnknownStrings is not implemented on Nokia
                  7750 SR-1 in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  7750 SR-1 in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia 7750 SR-1 in
                  release 14.0."

        VARIATION   tmnxSubInfoMssName
            ACCESS  not-implemented
            DESCRIPTION
                 "tmnxSubInfoMssName is not implemented on Nokia 7750 SR-1 in
                  release 14.0."

        VARIATION   tmnxSubProfFltrProfileMapTable
            ACCESS  not-implemented
            DESCRIPTION
                 "tmnxSubProfFltrProfileMapTable is not implemented on Nokia
                  7750 SR-1 in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  7750 SR-1 in release 14.0."

        VARIATION   tmnxSubProfUseSubscriberMss
            ACCESS  not-implemented
            DESCRIPTION
                 "tmnxSubProfUseSubscriberMss is not implemented on Nokia 7750
                  SR-1 in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnx7750SR1AgentV14v0  47 }

--
-- 7750c12 SUBSCR_MGMT CAPABILITIES
--
tmnx7750c12SubscrMgmtV14v0        AGENT-CAPABILITIES
    PRODUCT-RELEASE "Nokia SROS"
    STATUS          current
    DESCRIPTION
         "Implementation of Subscriber Management capabilities for Nokia 7750
          c12 systems release 14.0."

    SUPPORTS        TIMETRA-SUBSCRIBER-MGMT-MIB
        INCLUDES {
           tmnxCcIpFltrV8v0Group,
           tmnxCcIpv6FltrV8v0Group,
-- EXCLUDE tmnxHsmdaSubscriberV10v0Group
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
           tmnxSubBsxObjV9v0Group,
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
-- EXCLUDE tmnxSubHsmdaGroup
-- EXCLUDE tmnxSubHsmdaV12v0Group
           tmnxSubHsmdaV14v0Group,
-- EXCLUDE tmnxSubHttpRedirectGroup
           tmnxSubHttpRedirectV12v0Group,
           tmnxSubIpoeLinkV10v0Group,
           tmnxSubIpoeV13v0Group,
           tmnxSubIpoeV14v0Group,
           tmnxSubL2tpGroup,
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
-- EXCLUDE tmnxSubNatV14v0Group
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
           tmnxSubQosParentLocV12v0Group,
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia 7750
                  c12 in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia 7750 c12
                  in release 14.0."

        VARIATION   tmnxSubFlterProfTbleLastMgmtChg
            ACCESS  not-implemented
            DESCRIPTION
                 "tmnxSubFlterProfTbleLastMgmtChg is not implemented on Nokia
                  7750 c12 in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  7750 c12 in release 14.0."

        VARIATION   tmnxSubIPolRejectUnknownStrings
            ACCESS  not-implemented
            DESCRIPTION
                 "tmnxSubIPolRejectUnknownStrings is not implemented on Nokia
                  7750 c12 in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  7750 c12 in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia 7750 c12 in
                  release 14.0."

        VARIATION   tmnxSubInfoMssName
            ACCESS  not-implemented
            DESCRIPTION
                 "tmnxSubInfoMssName is not implemented on Nokia 7750 c12 in
                  release 14.0."

        VARIATION   tmnxSubProfFltrProfileMapTable
            ACCESS  not-implemented
            DESCRIPTION
                 "tmnxSubProfFltrProfileMapTable is not implemented on Nokia
                  7750 c12 in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  7750 c12 in release 14.0."

        VARIATION   tmnxSubProfUseSubscriberMss
            ACCESS  not-implemented
            DESCRIPTION
                 "tmnxSubProfUseSubscriberMss is not implemented on Nokia 7750
                  c12 in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnx7750c12AgentV14v0  47 }

--
-- 7750c4 SUBSCR_MGMT CAPABILITIES
--
tmnx7750c4SubscrMgmtV14v0         AGENT-CAPABILITIES
    PRODUCT-RELEASE "Nokia SROS"
    STATUS          current
    DESCRIPTION
         "Implementation of Subscriber Management capabilities for Nokia 7750 c4
          systems release 14.0."

    SUPPORTS        TIMETRA-SUBSCRIBER-MGMT-MIB
        INCLUDES {
           tmnxCcIpFltrV8v0Group,
           tmnxCcIpv6FltrV8v0Group,
-- EXCLUDE tmnxHsmdaSubscriberV10v0Group
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
           tmnxSubBsxObjV9v0Group,
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
-- EXCLUDE tmnxSubHsmdaGroup
-- EXCLUDE tmnxSubHsmdaV12v0Group
           tmnxSubHsmdaV14v0Group,
-- EXCLUDE tmnxSubHttpRedirectGroup
           tmnxSubHttpRedirectV12v0Group,
           tmnxSubIpoeLinkV10v0Group,
           tmnxSubIpoeV13v0Group,
           tmnxSubIpoeV14v0Group,
           tmnxSubL2tpGroup,
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
-- EXCLUDE tmnxSubNatV14v0Group
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
           tmnxSubQosParentLocV12v0Group,
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia 7750
                  c4 in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia 7750 c4
                  in release 14.0."

        VARIATION   tmnxSubFlterProfTbleLastMgmtChg
            ACCESS  not-implemented
            DESCRIPTION
                 "tmnxSubFlterProfTbleLastMgmtChg is not implemented on Nokia
                  7750 c4 in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  7750 c4 in release 14.0."

        VARIATION   tmnxSubIPolRejectUnknownStrings
            ACCESS  not-implemented
            DESCRIPTION
                 "tmnxSubIPolRejectUnknownStrings is not implemented on Nokia
                  7750 c4 in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  7750 c4 in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia 7750 c4 in
                  release 14.0."

        VARIATION   tmnxSubInfoMssName
            ACCESS  not-implemented
            DESCRIPTION
                 "tmnxSubInfoMssName is not implemented on Nokia 7750 c4 in
                  release 14.0."

        VARIATION   tmnxSubProfFltrProfileMapTable
            ACCESS  not-implemented
            DESCRIPTION
                 "tmnxSubProfFltrProfileMapTable is not implemented on Nokia
                  7750 c4 in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  7750 c4 in release 14.0."

        VARIATION   tmnxSubProfUseSubscriberMss
            ACCESS  not-implemented
            DESCRIPTION
                 "tmnxSubProfUseSubscriberMss is not implemented on Nokia 7750
                  c4 in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnx7750c4AgentV14v0  47 }

--
-- 7450 SUBSCR_MGMT CAPABILITIES
--
tmnx7450SubscrMgmtV14v0           AGENT-CAPABILITIES
    PRODUCT-RELEASE "Nokia SROS"
    STATUS          current
    DESCRIPTION
         "Implementation of Subscriber Management capabilities for Nokia 7450
          systems release 14.0."

    SUPPORTS        TIMETRA-SUBSCRIBER-MGMT-MIB
        INCLUDES {
           tmnxCcIpFltrV8v0Group,
           tmnxCcIpv6FltrV8v0Group,
           tmnxHsmdaSubscriberV10v0Group,
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
           tmnxSubBsxObjV9v0Group,
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
           tmnxSubHsmdaGroup,
           tmnxSubHsmdaV12v0Group,
           tmnxSubHsmdaV14v0Group,
-- EXCLUDE tmnxSubHttpRedirectGroup
           tmnxSubHttpRedirectV12v0Group,
           tmnxSubIpoeLinkV10v0Group,
           tmnxSubIpoeV13v0Group,
           tmnxSubIpoeV14v0Group,
           tmnxSubL2tpGroup,
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
-- EXCLUDE tmnxSubNatV14v0Group
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
           tmnxSubQosParentLocV12v0Group,
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia 7450
                  in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia 7450 in
                  release 14.0."

        VARIATION   tmnxSubFlterProfTbleLastMgmtChg
            ACCESS  not-implemented
            DESCRIPTION
                 "tmnxSubFlterProfTbleLastMgmtChg is not implemented on Nokia
                  7450 in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  7450 in release 14.0."

        VARIATION   tmnxSubIPolRejectUnknownStrings
            ACCESS  not-implemented
            DESCRIPTION
                 "tmnxSubIPolRejectUnknownStrings is not implemented on Nokia
                  7450 in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  7450 in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia 7450 in
                  release 14.0."

        VARIATION   tmnxSubInfoMssName
            ACCESS  not-implemented
            DESCRIPTION
                 "tmnxSubInfoMssName is not implemented on Nokia 7450 in release
                  14.0."

        VARIATION   tmnxSubProfFltrProfileMapTable
            ACCESS  not-implemented
            DESCRIPTION
                 "tmnxSubProfFltrProfileMapTable is not implemented on Nokia
                  7450 in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  7450 in release 14.0."

        VARIATION   tmnxSubProfUseSubscriberMss
            ACCESS  not-implemented
            DESCRIPTION
                 "tmnxSubProfUseSubscriberMss is not implemented on Nokia 7450
                  in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnx7450AgentV14v0  47 }

--
-- 7450ESS-1 SUBSCR_MGMT CAPABILITIES
--
tmnx7450ESS1SubscrMgmtV14v0       AGENT-CAPABILITIES
    PRODUCT-RELEASE "Nokia SROS"
    STATUS          current
    DESCRIPTION
         "Implementation of Subscriber Management capabilities for Nokia 7450
          ESS-1 systems release 14.0."

    SUPPORTS        TIMETRA-SUBSCRIBER-MGMT-MIB
        INCLUDES {
           tmnxCcIpFltrV8v0Group,
           tmnxCcIpv6FltrV8v0Group,
           tmnxHsmdaSubscriberV10v0Group,
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
-- EXCLUDE tmnxSubBsxObjV9v0Group
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
           tmnxSubHsmdaGroup,
           tmnxSubHsmdaV12v0Group,
           tmnxSubHsmdaV14v0Group,
-- EXCLUDE tmnxSubHttpRedirectGroup
           tmnxSubHttpRedirectV12v0Group,
           tmnxSubIpoeLinkV10v0Group,
           tmnxSubIpoeV13v0Group,
           tmnxSubIpoeV14v0Group,
           tmnxSubL2tpGroup,
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
-- EXCLUDE tmnxSubNatV14v0Group
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
           tmnxSubQosParentLocV12v0Group,
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia 7450
                  ESS-1 in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubApCategoryEgressPolicers
            ACCESS  not-implemented
            DESCRIPTION
                 "tmnxSubApCategoryEgressPolicers is not implemented on Nokia
                  7450 ESS-1 in release 14.0."

        VARIATION   tmnxSubApCategoryIngressPolicers
            ACCESS  not-implemented
            DESCRIPTION
                 "tmnxSubApCategoryIngressPolicers is not implemented on Nokia
                  7450 ESS-1 in release 14.0."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia 7450
                  ESS-1 in release 14.0."

        VARIATION   tmnxSubFlterProfTbleLastMgmtChg
            ACCESS  not-implemented
            DESCRIPTION
                 "tmnxSubFlterProfTbleLastMgmtChg is not implemented on Nokia
                  7450 ESS-1 in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  7450 ESS-1 in release 14.0."

        VARIATION   tmnxSubIPolRejectUnknownStrings
            ACCESS  not-implemented
            DESCRIPTION
                 "tmnxSubIPolRejectUnknownStrings is not implemented on Nokia
                  7450 ESS-1 in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  7450 ESS-1 in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia 7450 ESS-1 in
                  release 14.0."

        VARIATION   tmnxSubInfoMssName
            ACCESS  not-implemented
            DESCRIPTION
                 "tmnxSubInfoMssName is not implemented on Nokia 7450 ESS-1 in
                  release 14.0."

        VARIATION   tmnxSubProfFltrProfileMapTable
            ACCESS  not-implemented
            DESCRIPTION
                 "tmnxSubProfFltrProfileMapTable is not implemented on Nokia
                  7450 ESS-1 in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  7450 ESS-1 in release 14.0."

        VARIATION   tmnxSubProfUseSubscriberMss
            ACCESS  not-implemented
            DESCRIPTION
                 "tmnxSubProfUseSubscriberMss is not implemented on Nokia 7450
                  ESS-1 in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnx7450ESS1AgentV14v0  47 }

--
-- 7710 SUBSCR_MGMT CAPABILITIES
--
tmnx7710SubscrMgmtV14v0           AGENT-CAPABILITIES
    PRODUCT-RELEASE "Nokia SROS"
    STATUS          current
    DESCRIPTION
         "Implementation of Subscriber Management capabilities for Nokia 7710
          systems release 14.0."

    SUPPORTS        TIMETRA-SUBSCRIBER-MGMT-MIB
        INCLUDES {
           tmnxCcIpFltrV8v0Group,
           tmnxCcIpv6FltrV8v0Group,
-- EXCLUDE tmnxHsmdaSubscriberV10v0Group
           tmnxSubAccountingV10v0Group,
           tmnxSubAccountingV11v0Group,
           tmnxSubAccountingV12v0Group,
           tmnxSubAccountingV13v0Group,
           tmnxSubAccountingV14v0Group,
           tmnxSubAleGroup,
           tmnxSubAuthenticationV10v0Group,
           tmnxSubAuthenticationV11v0Group,
           tmnxSubAuthenticationV12v0Group,
           tmnxSubAuthenticationV14v0Group,
           tmnxSubAutoSubIdV10v0Group,
-- EXCLUDE tmnxSubBsxObjV9v0Group
           tmnxSubCcLongCatMapNameGroup,
           tmnxSubCreditControlV10v0Group,
           tmnxSubCreditControlV13v0Group,
           tmnxSubCreditControlV14v0Group,
           tmnxSubCreditControlV8v0Group,
           tmnxSubCreditControlV9v0Group,
           tmnxSubDataTriggerGroup,
           tmnxSubErrorsGroup,
-- EXCLUDE tmnxSubFlterProfGroup
           tmnxSubFrameBasedAccntV6v0Group,
           tmnxSubHostTrackingV9v0Group,
-- EXCLUDE tmnxSubHsmdaGroup
-- EXCLUDE tmnxSubHsmdaV12v0Group
           tmnxSubHsmdaV14v0Group,
-- EXCLUDE tmnxSubHttpRedirectGroup
           tmnxSubHttpRedirectV12v0Group,
           tmnxSubIpoeLinkV10v0Group,
           tmnxSubIpoeV13v0Group,
           tmnxSubIpoeV14v0Group,
-- EXCLUDE tmnxSubL2tpGroup
           tmnxSubMgmtIPv6V8v0Group,
           tmnxSubMgmtIpoeNotifGroup,
           tmnxSubMgmtQosV11v0Group,
           tmnxSubMgmtQosV12v0Group,
           tmnxSubMgmtQosV14v0Group,
           tmnxSubMgmtV10v0NotifGroup,
           tmnxSubMgmtV11v0Group,
           tmnxSubMgmtV12v0Group,
           tmnxSubMgmtV12v0NotifGroup,
           tmnxSubMgmtV13v0Group,
           tmnxSubMgmtV13v0NotifGroup,
           tmnxSubMgmtV14v0Group,
           tmnxSubMgmtV14v0NotifGroup,
           tmnxSubMgmtV7v0NotifGroup,
           tmnxSubMgmtV9v0NotifGroup,
-- EXCLUDE tmnxSubNatV14v0Group
           tmnxSubPccRuleEntryV13v0Group,
           tmnxSubPccRuleEntryV14v0Group,
           tmnxSubPimGroup,
           tmnxSubPppDfGroup,
           tmnxSubPppV11v0Group,
           tmnxSubPppV13v0Group,
           tmnxSubProfileMssExtensionsGroup,
           tmnxSubProfileV9v0Group,
-- EXCLUDE tmnxSubQosParentLocV12v0Group
           tmnxSubRadClassGroup,
           tmnxSubRadNotifStatsV6v0Group,
           tmnxSubRadusPlcyCustomRecordV7v0Group,
           tmnxSubRipV13v0Group,
           tmnxSubSchedulerRateV11v0Group,
           tmnxSubSchedulerRateV12v0Group,
           tmnxSubSchedulerRateV13v0Group,
           tmnxSubServiceGroup,
           tmnxSubShcvGroup,
           tmnxSubSlaacV11v0Group,
           tmnxSubSlaacV12v0Group,
           tmnxSubSlaacV13v0Group,
           tmnxSubSysGroup,
           tmnxSubV6GrpIfRAV11v0Group,
           tmnxSubVSubnetV12v0Group,
           tmnxSubVcpeGroup
        }

        VARIATION   tmnxSLAEgrPolicerOvrRowStatus
            SYNTAX  RowStatus {
                       active               (1),
                    -- notInService         (2)
                    -- notReady             (3)
                       createAndGo          (4),
                    -- createAndWait        (5)
                       destroy              (6)
                    }
            DESCRIPTION
                 "tmnxSLAEgrPolicerOvrRowStatus supports only 'active (1)',
                  'createAndGo (4)', and 'destroy (6)'."

        VARIATION   tmnxSLAEgrQueueOvrRowStatus
            SYNTAX  RowStatus {
                       active               (1),
                    -- notInService         (2)
                    -- notReady             (3)
                       createAndGo          (4),
                    -- createAndWait        (5)
                       destroy              (6)
                    }
            DESCRIPTION
                 "tmnxSLAEgrQueueOvrRowStatus supports only 'active (1)',
                  'createAndGo (4)', and 'destroy (6)'."

        VARIATION   tmnxSLAIngPolicerOvrRowStatus
            SYNTAX  RowStatus {
                       active               (1),
                    -- notInService         (2)
                    -- notReady             (3)
                       createAndGo          (4),
                    -- createAndWait        (5)
                       destroy              (6)
                    }
            DESCRIPTION
                 "tmnxSLAIngPolicerOvrRowStatus supports only 'active (1)',
                  'createAndGo (4)', and 'destroy (6)'."

        VARIATION   tmnxSLAIngQueueOvrRowStatus
            SYNTAX  RowStatus {
                       active               (1),
                    -- notInService         (2)
                    -- notReady             (3)
                       createAndGo          (4),
                    -- createAndWait        (5)
                       destroy              (6)
                    }
            DESCRIPTION
                 "tmnxSLAIngQueueOvrRowStatus supports only 'active (1)',
                  'createAndGo (4)', and 'destroy (6)'."

        VARIATION   tmnxSLAProfCatRowStatus
            SYNTAX  RowStatus {
                       active               (1),
                    -- notInService         (2)
                    -- notReady             (3)
                       createAndGo          (4),
                    -- createAndWait        (5)
                       destroy              (6)
                    }
            DESCRIPTION
                 "tmnxSLAProfCatRowStatus supports only 'active (1)',
                  'createAndGo (4)', and 'destroy (6)'."

        VARIATION   tmnxSPFltrProfMapTblLstMgtChg
            ACCESS  not-implemented
            DESCRIPTION
                 "tmnxSPFltrProfMapTblLstMgtChg is not implemented on Nokia 7710
                  in release 14.0."

        VARIATION   tmnxSubAcctPlcyHostAccounting
            SYNTAX  INTEGER {
                       enabled              (1),
                       disabled             (2),
                       interim              (3)
                    -- host                 (4)
                    -- interimHost          (5)
                    }
            DESCRIPTION
                 "tmnxSubAcctPlcyHostAccounting does not support the values
                  'host (4)' and 'interimHost (5)'"

        VARIATION   tmnxSubAcctPlcyQueueInstAcct
            SYNTAX  INTEGER {
                       enabled              (1),
                       disabled             (2),
                       interim              (3)
                    -- host                 (4)
                    -- interimHost          (5)
                    }
            DESCRIPTION
                 "tmnxSubAcctPlcyQueueInstAcct does not support the values 'host
                  (4)' and 'interimHost (5)'"

        VARIATION   tmnxSubAcctPlcyRowStatus
            SYNTAX  RowStatus {
                       active               (1),
                    -- notInService         (2)
                    -- notReady             (3)
                       createAndGo          (4),
                    -- createAndWait        (5)
                       destroy              (6)
                    }
            DESCRIPTION
                 "tmnxSubAcctPlcyRowStatus supports only 'active (1)',
                  'createAndGo (4)', and 'destroy (6)'."

        VARIATION   tmnxSubApCMapRowStatus
            SYNTAX  RowStatus {
                       active               (1),
                    -- notInService         (2)
                    -- notReady             (3)
                       createAndGo          (4),
                    -- createAndWait        (5)
                       destroy              (6)
                    }
            DESCRIPTION
                 "tmnxSubApCMapRowStatus supports only 'active (1)',
                  'createAndGo (4)', and 'destroy (6)'."

        VARIATION   tmnxSubApCategoryEgressPolicers
            ACCESS  not-implemented
            DESCRIPTION
                 "tmnxSubApCategoryEgressPolicers is not implemented on Nokia
                  7710 in release 14.0."

        VARIATION   tmnxSubApCategoryIngressPolicers
            ACCESS  not-implemented
            DESCRIPTION
                 "tmnxSubApCategoryIngressPolicers is not implemented on Nokia
                  7710 in release 14.0."

        VARIATION   tmnxSubAuthPlcyRowStatus
            SYNTAX  RowStatus {
                       active               (1),
                    -- notInService         (2)
                    -- notReady             (3)
                       createAndGo          (4),
                    -- createAndWait        (5)
                       destroy              (6)
                    }
            DESCRIPTION
                 "tmnxSubAuthPlcyRowStatus supports only 'active (1)',
                  'createAndGo (4)', and 'destroy (6)'."

        VARIATION   tmnxSubAutoSubIdIpoeKey1
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey1 does not support the value 'sessionId
                  (5)'."

        VARIATION   tmnxSubAutoSubIdIpoeKey2
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey2 does not support the value 'sessionId
                  (5)'."

        VARIATION   tmnxSubAutoSubIdIpoeKey3
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey3 does not support the value 'sessionId
                  (5)'."

        VARIATION   tmnxSubAutoSubIdIpoeKey4
            SYNTAX  INTEGER {
                       none                 (0),
                       mac                  (1),
                       sapId                (2),
                       circuitId            (3),
                       remoteId             (4),
                    -- sessionId            (5)
                       dualStackRemoteId    (6)
                    }
            DESCRIPTION
                 "tmnxSubAutoSubIdIpoeKey4 does not support the value 'sessionId
                  (5)'."

        VARIATION   tmnxSubAutoSubIdPppKey1
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey2
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey3
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey4
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubAutoSubIdPppKey5
            SYNTAX  INTEGER {
                       none                 (0),
                       mac                  (1),
                       sapId                (2),
                       circuitId            (3),
                       remoteId             (4),
                       sessionId            (5)
                    -- dualStackRemoteId    (6)
                    }
            DESCRIPTION
                 "The only allowed values for this object are 'none (0)', 'mac
                  (1)', 'sapId (2)', 'circuitId (3)', 'remoteId (4)', and
                  'sessionId (5)'."

        VARIATION   tmnxSubBrgProfDhcp4EndAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4EndAddrTyp supports only the
                  InetAddressType value 'ipv4 (1)'."

        VARIATION   tmnxSubBrgProfDhcp4StartAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4StartAddrTyp supports only the
                  InetAddressType value 'ipv4 (1)'."

        VARIATION   tmnxSubBrgProfDhcp4SubnetAddrTyp
            SYNTAX  InetAddressType {
                    -- unknown              (0)
                       ipv4                 (1)
                    -- ipv6                 (2)
                    -- ipv4z                (3)
                    -- ipv6z                (4)
                    -- dns                  (16)
                    }
            DESCRIPTION
                 "tmnxSubBrgProfDhcp4SubnetAddrTyp supports only the
                  InetAddressType value 'ipv4 (1)'."

        VARIATION   tmnxSubCcPlcyRowStatus
            SYNTAX  RowStatus {
                       active               (1),
                    -- notInService         (2)
                    -- notReady             (3)
                       createAndGo          (4),
                    -- createAndWait        (5)
                       destroy              (6)
                    }
            DESCRIPTION
                 "tmnxSubCcPlcyRowStatus supports only 'active (1)',
                  'createAndGo (4)', and 'destroy (6)'."

        VARIATION   tmnxSubExplicitMapRowStatus
            SYNTAX  RowStatus {
                       active               (1),
                    -- notInService         (2)
                    -- notReady             (3)
                       createAndGo          (4),
                    -- createAndWait        (5)
                       destroy              (6)
                    }
            DESCRIPTION
                 "tmnxSubExplicitMapRowStatus supports only 'active (1)',
                  'createAndGo (4)', and 'destroy (6)'."

        VARIATION   tmnxSubFilterProfileTable
            ACCESS  not-implemented
            DESCRIPTION
                 "tmnxSubFilterProfileTable is not implemented on Nokia 7710 in
                  release 14.0."

        VARIATION   tmnxSubFlterProfTbleLastMgmtChg
            ACCESS  not-implemented
            DESCRIPTION
                 "tmnxSubFlterProfTbleLastMgmtChg is not implemented on Nokia
                  7710 in release 14.0."

        VARIATION   tmnxSubHsmdaEgrQosQRowStatus
            SYNTAX  RowStatus {
                       active               (1),
                    -- notInService         (2)
                    -- notReady             (3)
                       createAndGo          (4),
                    -- createAndWait        (5)
                       destroy              (6)
                    }
            DESCRIPTION
                 "tmnxSubHsmdaEgrQosQRowStatus supports only 'active (1)',
                  'createAndGo (4)', and 'destroy (6)'."

        VARIATION   tmnxSubHttpRdrFwdRowStatus
            SYNTAX  RowStatus {
                       active               (1),
                    -- notInService         (2)
                    -- notReady             (3)
                       createAndGo          (4),
                    -- createAndWait        (5)
                       destroy              (6)
                    }
            DESCRIPTION
                 "tmnxSubHttpRdrFwdRowStatus supports only 'active (1)',
                  'createAndGo (4)', and 'destroy (6)'."

        VARIATION   tmnxSubHttpRdrPlcyDestPort
            SYNTAX  Unsigned32 (1..65535)
            DESCRIPTION
                 "The value zero is not allowed."

        VARIATION   tmnxSubHttpRdrPlcyRowStatus
            SYNTAX  RowStatus {
                       active               (1),
                    -- notInService         (2)
                    -- notReady             (3)
                       createAndGo          (4),
                    -- createAndWait        (5)
                       destroy              (6)
                    }
            DESCRIPTION
                 "tmnxSubHttpRdrPlcyRowStatus supports only 'active (1)',
                  'createAndGo (4)', and 'destroy (6)'."

        VARIATION   tmnxSubIPolAppProfMapRowStatus
            SYNTAX  RowStatus {
                       active               (1),
                    -- notInService         (2)
                    -- notReady             (3)
                       createAndGo          (4),
                    -- createAndWait        (5)
                       destroy              (6)
                    }
            DESCRIPTION
                 "tmnxSubIPolAppProfMapRowStatus supports only 'active (1)',
                  'createAndGo (4)', and 'destroy (6)'."

        VARIATION   tmnxSubIPolFltrProfileMapTable
            ACCESS  not-implemented
            DESCRIPTION
                 "tmnxSubIPolFltrProfileMapTable is not implemented on Nokia
                  7710 in release 14.0."

        VARIATION   tmnxSubIPolRejectUnknownStrings
            ACCESS  not-implemented
            DESCRIPTION
                 "tmnxSubIPolRejectUnknownStrings is not implemented on Nokia
                  7710 in release 14.0."

        VARIATION   tmnxSubIPolRowStatus
            SYNTAX  RowStatus {
                       active               (1),
                    -- notInService         (2)
                    -- notReady             (3)
                       createAndGo          (4),
                    -- createAndWait        (5)
                       destroy              (6)
                    }
            DESCRIPTION
                 "tmnxSubIPolRowStatus supports only 'active (1)', 'createAndGo
                  (4)', and 'destroy (6)'."

        VARIATION   tmnxSubIPolSLAProfMapRowStatus
            SYNTAX  RowStatus {
                       active               (1),
                    -- notInService         (2)
                    -- notReady             (3)
                       createAndGo          (4),
                    -- createAndWait        (5)
                       destroy              (6)
                    }
            DESCRIPTION
                 "tmnxSubIPolSLAProfMapRowStatus supports only 'active (1)',
                  'createAndGo (4)', and 'destroy (6)'."

        VARIATION   tmnxSubIPolSubProfMapRowStatus
            SYNTAX  RowStatus {
                       active               (1),
                    -- notInService         (2)
                    -- notReady             (3)
                       createAndGo          (4),
                    -- createAndWait        (5)
                       destroy              (6)
                    }
            DESCRIPTION
                 "tmnxSubIPolSubProfMapRowStatus supports only 'active (1)',
                  'createAndGo (4)', and 'destroy (6)'."

        VARIATION   tmnxSubIPolUseDirectFltrMapAsDef
            ACCESS  not-implemented
            DESCRIPTION
                 "tmnxSubIPolUseDirectFltrMapAsDef is not implemented on Nokia
                  7710 in release 14.0."

        VARIATION   tmnxSubIgmpPlcyMcRprtAdminState
            SYNTAX  INTEGER {
                    -- noop                 (1)
                       inService            (2),
                       outOfService         (3)
                    }
            DESCRIPTION
                 "tmnxSubIgmpPlcyMcRprtAdminState supports only the values
                  'inService (2)' and 'outOfService (3)'."

        VARIATION   tmnxSubInfoMssCustId
            ACCESS  not-implemented
            DESCRIPTION
                 "tmnxSubInfoMssCustId is not implemented on Nokia 7710 in
                  release 14.0."

        VARIATION   tmnxSubInfoMssName
            ACCESS  not-implemented
            DESCRIPTION
                 "tmnxSubInfoMssName is not implemented on Nokia 7710 in release
                  14.0."

        VARIATION   tmnxSubProfFltrProfileMapTable
            ACCESS  not-implemented
            DESCRIPTION
                 "tmnxSubProfFltrProfileMapTable is not implemented on Nokia
                  7710 in release 14.0."

        VARIATION   tmnxSubProfPCtrlLvlOvrRowStatus
            SYNTAX  RowStatus {
                       active               (1),
                    -- notInService         (2)
                    -- notReady             (3)
                       createAndGo          (4),
                    -- createAndWait        (5)
                       destroy              (6)
                    }
            DESCRIPTION
                 "tmnxSubProfPCtrlLvlOvrRowStatus supports only 'active (1)',
                  'createAndGo (4)', and 'destroy (6)'."

        VARIATION   tmnxSubProfPCtrlOvrRowStatus
            SYNTAX  RowStatus {
                       active               (1),
                    -- notInService         (2)
                    -- notReady             (3)
                       createAndGo          (4),
                    -- createAndWait        (5)
                       destroy              (6)
                    }
            DESCRIPTION
                 "tmnxSubProfPCtrlOvrRowStatus supports only 'active (1)',
                  'createAndGo (4)', and 'destroy (6)'."

        VARIATION   tmnxSubProfRowStatus
            SYNTAX  RowStatus {
                       active               (1),
                    -- notInService         (2)
                    -- notReady             (3)
                       createAndGo          (4),
                    -- createAndWait        (5)
                       destroy              (6)
                    }
            DESCRIPTION
                 "tmnxSubProfRowStatus supports only 'active (1)', 'createAndGo
                  (4)', and 'destroy (6)'."

        VARIATION   tmnxSubProfSLAProfMapRowStatus
            SYNTAX  RowStatus {
                       active               (1),
                    -- notInService         (2)
                    -- notReady             (3)
                       createAndGo          (4),
                    -- createAndWait        (5)
                       destroy              (6)
                    }
            DESCRIPTION
                 "tmnxSubProfSLAProfMapRowStatus supports only 'active (1)',
                  'createAndGo (4)', and 'destroy (6)'."

        VARIATION   tmnxSubProfUseDirectFltrMapAsDef
            ACCESS  not-implemented
            DESCRIPTION
                 "tmnxSubProfUseDirectFltrMapAsDef is not implemented on Nokia
                  7710 in release 14.0."

        VARIATION   tmnxSubProfUseSubscriberMss
            ACCESS  not-implemented
            DESCRIPTION
                 "tmnxSubProfUseSubscriberMss is not implemented on Nokia 7710
                  in release 14.0."

        VARIATION   tmnxSubShcvPlcyRowStatus
            SYNTAX  RowStatus {
                       active               (1),
                    -- notInService         (2)
                    -- notReady             (3)
                       createAndGo          (4),
                    -- createAndWait        (5)
                       destroy              (6)
                    }
            DESCRIPTION
                 "tmnxSubShcvPlcyRowStatus supports only 'active (1)',
                  'createAndGo (4)', and 'destroy (6)'."

        VARIATION   tmnxSubShcvPlcyVplsSrcIp4AddrTyp
            SYNTAX  InetAddressType {
                    -- unknown              (0)
                       ipv4                 (1)
                    -- ipv6                 (2)
                    -- ipv4z                (3)
                    -- ipv6z                (4)
                    -- dns                  (16)
                    }
            DESCRIPTION
                 "tmnxSubShcvPlcyVplsSrcIp4AddrTyp supports only the
                  InetAddressType value 'ipv4 (1)'."

        VARIATION   tmnxSubTrkPlcyRowStatus
            SYNTAX  RowStatus {
                       active               (1),
                    -- notInService         (2)
                    -- notReady             (3)
                       createAndGo          (4),
                    -- createAndWait        (5)
                       destroy              (6)
                    }
            DESCRIPTION
                 "tmnxSubTrkPlcyRowStatus supports only 'active (1)',
                  'createAndGo (4)', and 'destroy (6)'."

    ::= { tmnx7710AgentV14v0  47 }

--
-- 7950 SUBSCR_MGMT CAPABILITIES
--
tmnx7950SubscrMgmtV14v0           AGENT-CAPABILITIES
    PRODUCT-RELEASE "Nokia SROS"
    STATUS          current
    DESCRIPTION
         "Implementation of Subscriber Management capabilities for Nokia 7950
          systems release 14.0."

--    SUPPORTS        TIMETRA-SUBSCRIBER-MGMT-MIB
--        INCLUDES {
--        }

    ::= { tmnx7950AgentV14v0  47 }

--
-- SROS SYSTEM CAPABILITIES
--
tmnxSROSSystemV14v0               AGENT-CAPABILITIES
    PRODUCT-RELEASE "Nokia SROS"
    STATUS          current
    DESCRIPTION
         "Implementation of System capabilities for Nokia SROS systems release
          14.0."

    SUPPORTS        TIMETRA-SYSTEM-MIB
        INCLUDES {
           tmnxPersistenceV12v0Group,
           tmnxPersistenceV14v0Group,
           tmnxSysBofV12v0Group,
           tmnxSysBofV13v0Group,
           tmnxSysBofV14v0Group,
           tmnxSysBofV6v0Group,
           tmnxSysBootedBofGroup,
           tmnxSysCandidateCfgGroup,
           tmnxSysCardResourceGroup,
           tmnxSysCertGroup,
           tmnxSysConfigV8v0Group,
           tmnxSysDNSSecNotifV12v0Group,
           tmnxSysDNSSecV12v0Group,
           tmnxSysDhcpGroup,
           tmnxSysEhsParameterGroup,
           tmnxSysEhsV13v0Group,
           tmnxSysEthInfoGroup,
           tmnxSysFibV13v0Group,
           tmnxSysFileTransProfV13v0Group,
           tmnxSysGeneralV3v0Group,
           tmnxSysGeneralV7v0Group,
           tmnxSysGroupingSystemGroup,
           tmnxSysIcmpVSV6v1Group,
           tmnxSysIpv6MgmtItfV6v0Group,
           tmnxSysLiFilterGroup,
           tmnxSysLiV6v0Group,
           tmnxSysLicenseApplicationGroup,
           tmnxSysLicenseNotifV13v0Group,
           tmnxSysLicenseV12v0Group,
           tmnxSysLicenseV13v0Group,
           tmnxSysLoginControlSecGroup,
           tmnxSysLoginControlV8v0Group,
           tmnxSysLoginControlV9v0Group,
           tmnxSysMgmtProtocolV13v0Group,
           tmnxSysNetconfV11v0Group,
           tmnxSysNetconfV13v0Group,
           tmnxSysNetconfV14v0Group,
           tmnxSysNotificationRBGroup,
           tmnxSysNotificationV10v0Group,
           tmnxSysNotificationV12v0Group,
           tmnxSysNotificationV14v0Group,
           tmnxSysNotificationV6v0Group,
           tmnxSysNotificationV9v0Group,
           tmnxSysNotifyObjsGenGroup,
           tmnxSysNotifyObjsV10v0Group,
           tmnxSysNotifyObjsV11v0Group,
           tmnxSysNotifyObjsV12v0Group,
           tmnxSysNotifyObjsV14v0Group,
           tmnxSysRadiusServerV5v0Group,
           tmnxSysRollbackRescueGroup,
           tmnxSysRollbackV9v0Group,
           tmnxSysSnmpSrcAccesLstV13v0Group,
           tmnxSysStrmV11v0R4Group,
           tmnxSysSwReposV13v0Group,
           tmnxSysTacPlusServerV5v0Group,
           tmnxSysTimeV4v0Group,
           tmnxSysXmppV12v4Group,
           tmnxSystemCpuMonitorGroup
        }

        VARIATION   sntpTimeDiffExceedsThreshold
            ACCESS  not-implemented
            DESCRIPTION
                 "sntpTimeDiffExceedsThreshold notification is not implemented."

        VARIATION   stiDateAndTime
            DESCRIPTION
                 "The maximum date and time (in UTC) supported for the system is
                  2038/01/19 03:14:07"

        VARIATION   stiSummerZoneRowStatus
            SYNTAX  RowStatus {
                       active               (1),
                    -- notInService         (2)
                    -- notReady             (3)
                       createAndGo          (4),
                    -- createAndWait        (5)
                       destroy              (6)
                    }
            DESCRIPTION
                 "stiSummerZoneRowStatus supports only 'active (1)',
                  'createAndGo (4)', and 'destroy (6)'."

        VARIATION   tmnxSysFileTransProfRowStatus
            SYNTAX  RowStatus {
                       active               (1),
                    -- notInService         (2)
                    -- notReady             (3)
                       createAndGo          (4),
                    -- createAndWait        (5)
                       destroy              (6)
                    }
            DESCRIPTION
                 "tmnxSysFileTransProfRowStatus supports only 'active (1)',
                  'createAndGo (4)', and 'destroy (6)'."

        VARIATION   tmnxSysFileTransProfSrcAddrV4T
            SYNTAX  InetAddressType {
                       unknown              (0),
                       ipv4                 (1)
                    -- ipv6                 (2)
                    -- ipv4z                (3)
                    -- ipv6z                (4)
                    -- dns                  (16)
                    }
            DESCRIPTION
                 "tmnxSysFileTransProfSrcAddrV4T supports only the
                  InetAddressType values 'unknown (0)' and 'ipv4 (1)'."

        VARIATION   tmnxSysFileTransProfSrcAddrV6T
            SYNTAX  InetAddressType {
                       unknown              (0),
                    -- ipv4                 (1)
                       ipv6                 (2)
                    -- ipv4z                (3)
                    -- ipv6z                (4)
                    -- dns                  (16)
                    }
            DESCRIPTION
                 "tmnxSysFileTransProfSrcAddrV6T supports only the
                  InetAddressType values 'unknown (0)' and 'ipv6 (2)'."

        VARIATION   tmnxSysSnmpSrcAccessLstRowStatus
            SYNTAX  RowStatus {
                       active               (1),
                    -- notInService         (2)
                    -- notReady             (3)
                       createAndGo          (4),
                    -- createAndWait        (5)
                       destroy              (6)
                    }
            DESCRIPTION
                 "tmnxSysSnmpSrcAccessLstRowStatus supports only 'active (1)',
                  'createAndGo (4)', and 'destroy (6)'."

        VARIATION   tmnxSysSwReposRowStatus
            SYNTAX  RowStatus {
                       active               (1),
                    -- notInService         (2)
                    -- notReady             (3)
                       createAndGo          (4),
                    -- createAndWait        (5)
                       destroy              (6)
                    }
            DESCRIPTION
                 "tmnxSysSwReposRowStatus supports only 'active (1)',
                  'createAndGo (4)', and 'destroy (6)'."

    ::= { tmnxSROSAgentV14v0  43 }

--
-- 7950 SYSTEM CAPABILITIES
--
tmnx7950SystemV14v0               AGENT-CAPABILITIES
    PRODUCT-RELEASE "Nokia SROS"
    STATUS          current
    DESCRIPTION
         "Implementation of System capabilities for Nokia 7950 systems release
          14.0."

    SUPPORTS        TIMETRA-SYSTEM-MIB
        INCLUDES {
           tmnxPersistenceV12v0Group,
           tmnxPersistenceV14v0Group,
           tmnxSysBofV12v0Group,
           tmnxSysBofV13v0Group,
           tmnxSysBofV14v0Group,
           tmnxSysBofV6v0Group,
           tmnxSysBootedBofGroup,
           tmnxSysCandidateCfgGroup,
           tmnxSysCardResourceGroup,
           tmnxSysCertGroup,
           tmnxSysConfigV8v0Group,
           tmnxSysDNSSecNotifV12v0Group,
           tmnxSysDNSSecV12v0Group,
           tmnxSysDhcpGroup,
           tmnxSysEhsParameterGroup,
           tmnxSysEhsV13v0Group,
-- EXCLUDE tmnxSysEthInfoGroup
           tmnxSysFibV13v0Group,
           tmnxSysFileTransProfV13v0Group,
           tmnxSysGeneralV3v0Group,
           tmnxSysGeneralV7v0Group,
           tmnxSysGroupingSystemGroup,
           tmnxSysIcmpVSV6v1Group,
           tmnxSysIpv6MgmtItfV6v0Group,
           tmnxSysLiFilterGroup,
           tmnxSysLiV6v0Group,
           tmnxSysLicenseApplicationGroup,
           tmnxSysLicenseNotifV13v0Group,
           tmnxSysLicenseV12v0Group,
           tmnxSysLicenseV13v0Group,
           tmnxSysLoginControlSecGroup,
           tmnxSysLoginControlV8v0Group,
           tmnxSysLoginControlV9v0Group,
           tmnxSysMgmtProtocolV13v0Group,
           tmnxSysNetconfV11v0Group,
           tmnxSysNetconfV13v0Group,
           tmnxSysNetconfV14v0Group,
           tmnxSysNotificationRBGroup,
           tmnxSysNotificationV10v0Group,
           tmnxSysNotificationV12v0Group,
           tmnxSysNotificationV14v0Group,
           tmnxSysNotificationV6v0Group,
           tmnxSysNotificationV9v0Group,
           tmnxSysNotifyObjsGenGroup,
           tmnxSysNotifyObjsV10v0Group,
           tmnxSysNotifyObjsV11v0Group,
           tmnxSysNotifyObjsV12v0Group,
           tmnxSysNotifyObjsV14v0Group,
           tmnxSysRadiusServerV5v0Group,
           tmnxSysRollbackRescueGroup,
           tmnxSysRollbackV9v0Group,
           tmnxSysSnmpSrcAccesLstV13v0Group,
           tmnxSysStrmV11v0R4Group,
           tmnxSysSwReposV13v0Group,
           tmnxSysTacPlusServerV5v0Group,
           tmnxSysTimeV4v0Group,
           tmnxSysXmppV12v4Group,
           tmnxSystemCpuMonitorGroup
        }

        VARIATION   sntpTimeDiffExceedsThreshold
            ACCESS  not-implemented
            DESCRIPTION
                 "sntpTimeDiffExceedsThreshold notification is not implemented."

        VARIATION   stiDateAndTime
            DESCRIPTION
                 "The maximum date and time (in UTC) supported for the system is
                  2038/01/19 03:14:07"

        VARIATION   stiSummerZoneRowStatus
            SYNTAX  RowStatus {
                       active               (1),
                    -- notInService         (2)
                    -- notReady             (3)
                       createAndGo          (4),
                    -- createAndWait        (5)
                       destroy              (6)
                    }
            DESCRIPTION
                 "stiSummerZoneRowStatus supports only 'active (1)',
                  'createAndGo (4)', and 'destroy (6)'."

        VARIATION   tmnxSysFileTransProfRowStatus
            SYNTAX  RowStatus {
                       active               (1),
                    -- notInService         (2)
                    -- notReady             (3)
                       createAndGo          (4),
                    -- createAndWait        (5)
                       destroy              (6)
                    }
            DESCRIPTION
                 "tmnxSysFileTransProfRowStatus supports only 'active (1)',
                  'createAndGo (4)', and 'destroy (6)'."

        VARIATION   tmnxSysFileTransProfSrcAddrV4T
            SYNTAX  InetAddressType {
                       unknown              (0),
                       ipv4                 (1)
                    -- ipv6                 (2)
                    -- ipv4z                (3)
                    -- ipv6z                (4)
                    -- dns                  (16)
                    }
            DESCRIPTION
                 "tmnxSysFileTransProfSrcAddrV4T supports only the
                  InetAddressType values 'unknown (0)' and 'ipv4 (1)'."

        VARIATION   tmnxSysFileTransProfSrcAddrV6T
            SYNTAX  InetAddressType {
                       unknown              (0),
                    -- ipv4                 (1)
                       ipv6                 (2)
                    -- ipv4z                (3)
                    -- ipv6z                (4)
                    -- dns                  (16)
                    }
            DESCRIPTION
                 "tmnxSysFileTransProfSrcAddrV6T supports only the
                  InetAddressType values 'unknown (0)' and 'ipv6 (2)'."

        VARIATION   tmnxSysSnmpSrcAccessLstRowStatus
            SYNTAX  RowStatus {
                       active               (1),
                    -- notInService         (2)
                    -- notReady             (3)
                       createAndGo          (4),
                    -- createAndWait        (5)
                       destroy              (6)
                    }
            DESCRIPTION
                 "tmnxSysSnmpSrcAccessLstRowStatus supports only 'active (1)',
                  'createAndGo (4)', and 'destroy (6)'."

        VARIATION   tmnxSysSwReposRowStatus
            SYNTAX  RowStatus {
                       active               (1),
                    -- notInService         (2)
                    -- notReady             (3)
                       createAndGo          (4),
                    -- createAndWait        (5)
                       destroy              (6)
                    }
            DESCRIPTION
                 "tmnxSysSwReposRowStatus supports only 'active (1)',
                  'createAndGo (4)', and 'destroy (6)'."

    ::= { tmnx7950AgentV14v0  43 }

--
-- SROS TLS CAPABILITIES
--
tmnxSROSTlsV14v0                  AGENT-CAPABILITIES
    PRODUCT-RELEASE "Nokia SROS"
    STATUS          current
    DESCRIPTION
         "Implementation of TLS capabilities for Nokia SROS systems release
          14.0."

    SUPPORTS        TIMETRA-TLS-MIB
        INCLUDES {
           tmnxTlsClientMgmtInitialGroup,
           tmnxTlsX509CertMgmtGroup
        }

        VARIATION   tTlsClientCiphListRowStatus
            SYNTAX  RowStatus {
                       active               (1),
                    -- notInService         (2)
                    -- notReady             (3)
                       createAndGo          (4),
                    -- createAndWait        (5)
                       destroy              (6)
                    }
            DESCRIPTION
                 "tTlsClientCiphListRowStatus supports only 'active (1)',
                  'createAndGo (4)', and 'destroy (6)'."

        VARIATION   tTlsClntCiphListParamRowStatus
            SYNTAX  RowStatus {
                       active               (1),
                    -- notInService         (2)
                    -- notReady             (3)
                       createAndGo          (4),
                    -- createAndWait        (5)
                       destroy              (6)
                    }
            DESCRIPTION
                 "tTlsClntCiphListParamRowStatus supports only 'active (1)',
                  'createAndGo (4)', and 'destroy (6)'."

        VARIATION   tTlsClntProfileRowStatus
            SYNTAX  RowStatus {
                       active               (1),
                    -- notInService         (2)
                    -- notReady             (3)
                       createAndGo          (4),
                    -- createAndWait        (5)
                       destroy              (6)
                    }
            DESCRIPTION
                 "tTlsClntProfileRowStatus supports only 'active (1)',
                  'createAndGo (4)', and 'destroy (6)'."

        VARIATION   tTlsTrustAnchorProfRowStatus
            SYNTAX  RowStatus {
                       active               (1),
                    -- notInService         (2)
                    -- notReady             (3)
                       createAndGo          (4),
                    -- createAndWait        (5)
                       destroy              (6)
                    }
            DESCRIPTION
                 "tTlsTrustAnchorProfRowStatus supports only 'active (1)',
                  'createAndGo (4)', and 'destroy (6)'."

        VARIATION   tTlsTrustAnchorsRowStatus
            SYNTAX  RowStatus {
                       active               (1),
                    -- notInService         (2)
                    -- notReady             (3)
                       createAndGo          (4),
                    -- createAndWait        (5)
                       destroy              (6)
                    }
            DESCRIPTION
                 "tTlsTrustAnchorsRowStatus supports only 'active (1)',
                  'createAndGo (4)', and 'destroy (6)'."

    ::= { tmnxSROSAgentV14v0  98 }

--
-- SROS TWAMP CAPABILITIES
--
tmnxSROSTwampV14v0                AGENT-CAPABILITIES
    PRODUCT-RELEASE "Nokia SROS"
    STATUS          current
    DESCRIPTION
         "Implementation of Two-Way Active Measurement Protocol (TWAMP)
          capabilities for Nokia SROS systems release 14.0."

    SUPPORTS        TIMETRA-TWAMP-MIB
        INCLUDES {
           tmnxTwampSrvNotifyObjsV9v0Group,
           tmnxTwampSrvNotifyV9v0Group,
           tmnxTwampSrvV14v0Group,
           tmnxTwampSrvV9v0Group
        }

        VARIATION   tmnxTwampSrvPrefixAddrType
            SYNTAX  InetAddressType {
                    -- unknown              (0)
                       ipv4                 (1),
                       ipv6                 (2)
                    -- ipv4z                (3)
                    -- ipv6z                (4)
                    -- dns                  (16)
                    }
            DESCRIPTION
                 "tmnxTwampSrvPrefixAddrType supports only the InetAddressType
                  values 'ipv4 (1)', and 'ipv6 (2)'."

        VARIATION   tmnxTwampSrvPrefixRowStatus
            SYNTAX  RowStatus {
                       active               (1),
                    -- notInService         (2)
                    -- notReady             (3)
                       createAndGo          (4),
                    -- createAndWait        (5)
                       destroy              (6)
                    }
            DESCRIPTION
                 "tmnxTwampSrvPrefixRowStatus supports only 'active (1)',
                  'createAndGo (4)', and 'destroy (6)'."

    ::= { tmnxSROSAgentV14v0  79 }

--
-- SROS VIDEO CAPABILITIES
--
tmnxSROSVideoV14v0                AGENT-CAPABILITIES
    PRODUCT-RELEASE "Nokia SROS"
    STATUS          current
    DESCRIPTION
         "Implementation of the video features on Nokia SROS systems release
          14.0."

    SUPPORTS        TIMETRA-VIDEO-MIB
        INCLUDES {
           tmnxVdoAdiV7v0Group,
           tmnxVdoGlobalV7v0Group,
           tmnxVdoGrpSrcV7v0Group,
           tmnxVdoGrpV13v0Group,
           tmnxVdoGrpV7v0Group,
           tmnxVdoGrpV8v0Group,
           tmnxVdoIfV7v0Group,
           tmnxVdoIfV8v0Group,
           tmnxVdoNotificationsV7v0Group,
           tmnxVdoNotificationsV8v0Group,
           tmnxVdoStatsV7v0Group,
           tmnxVdoStatsV9v0Group
        }

        VARIATION   tmnxVdoAdiChlGrpAddrType
            SYNTAX  InetAddressType {
                    -- unknown              (0)
                       ipv4                 (1)
                    -- ipv6                 (2)
                    -- ipv4z                (3)
                    -- ipv6z                (4)
                    -- dns                  (16)
                    }
            DESCRIPTION
                 "tmnxVdoAdiChlGrpAddrType supports only the InetAddressType
                  value 'ipv4 (1)'."

        VARIATION   tmnxVdoAdiChlGrpAddress
            SYNTAX  InetAddress (SIZE (4))
            DESCRIPTION
                 "tmnxVdoAdiChlGrpAddress only supports the InetAddressType
                  value 'ipv4'."

        VARIATION   tmnxVdoAdiChlRowStatus
            SYNTAX  RowStatus {
                       active               (1),
                    -- notInService         (2)
                    -- notReady             (3)
                       createAndGo          (4),
                    -- createAndWait        (5)
                       destroy              (6)
                    }
            DESCRIPTION
                 "tmnxVdoAdiChlRowStatus supports only 'active (1)',
                  'createAndGo (4)', and 'destroy (6)'."

        VARIATION   tmnxVdoAdiChlSrcAddrType
            SYNTAX  InetAddressType {
                    -- unknown              (0)
                       ipv4                 (1)
                    -- ipv6                 (2)
                    -- ipv4z                (3)
                    -- ipv6z                (4)
                    -- dns                  (16)
                    }
            DESCRIPTION
                 "tmnxVdoAdiChlSrcAddrType supports only the InetAddressType
                  value 'ipv4 (1)'."

        VARIATION   tmnxVdoAdiChlSrcAddress
            SYNTAX  InetAddress (SIZE (4))
            DESCRIPTION
                 "tmnxVdoAdiChlSrcAddress only supports the InetAddressType
                  value 'ipv4'."

        VARIATION   tmnxVdoAdiZoneChlGrpAddrType
            SYNTAX  InetAddressType {
                    -- unknown              (0)
                       ipv4                 (1)
                    -- ipv6                 (2)
                    -- ipv4z                (3)
                    -- ipv6z                (4)
                    -- dns                  (16)
                    }
            DESCRIPTION
                 "tmnxVdoAdiZoneChlGrpAddrType supports only the InetAddressType
                  value 'ipv4 (1)'."

        VARIATION   tmnxVdoAdiZoneChlGrpAddress
            SYNTAX  InetAddress (SIZE (4))
            DESCRIPTION
                 "tmnxVdoAdiZoneChlGrpAddress only supports the InetAddressType
                  value 'ipv4'."

        VARIATION   tmnxVdoAdiZoneChlRowStatus
            SYNTAX  RowStatus {
                       active               (1),
                    -- notInService         (2)
                    -- notReady             (3)
                       createAndGo          (4),
                    -- createAndWait        (5)
                       destroy              (6)
                    }
            DESCRIPTION
                 "tmnxVdoAdiZoneChlRowStatus supports only 'active (1)',
                  'createAndGo (4)', and 'destroy (6)'."

        VARIATION   tmnxVdoAdiZoneChlSrcAddrType
            SYNTAX  InetAddressType {
                    -- unknown              (0)
                       ipv4                 (1)
                    -- ipv6                 (2)
                    -- ipv4z                (3)
                    -- ipv6z                (4)
                    -- dns                  (16)
                    }
            DESCRIPTION
                 "tmnxVdoAdiZoneChlSrcAddrType supports only the InetAddressType
                  value 'ipv4 (1)'."

        VARIATION   tmnxVdoAdiZoneChlSrcAddress
            SYNTAX  InetAddress (SIZE (4))
            DESCRIPTION
                 "tmnxVdoAdiZoneChlSrcAddress only supports the InetAddressType
                  value 'ipv4'."

        VARIATION   tmnxVdoGrpAdminState
            SYNTAX  INTEGER {
                    -- noop                 (1)
                       inService            (2),
                       outOfService         (3)
                    }
            DESCRIPTION
                 "tmnxVdoGrpAdminState supports only the values 'inService (2)'
                  and 'outOfService (3)'."

        VARIATION   tmnxVdoGrpMdaAdminState
            SYNTAX  INTEGER {
                    -- noop                 (1)
                       inService            (2),
                       outOfService         (3)
                    }
            DESCRIPTION
                 "tmnxVdoGrpMdaAdminState supports only the values 'inService
                  (2)' and 'outOfService (3)'."

        VARIATION   tmnxVdoGrpMdaOperState
            SYNTAX  INTEGER {
                    -- noop                 (1)
                       inService            (2),
                       outOfService         (3)
                    }
            DESCRIPTION
                 "tmnxVdoGrpMdaOperState supports only the values 'inService
                  (2)' and 'outOfService (3)'."

        VARIATION   tmnxVdoGrpMdaRowStatus
            SYNTAX  RowStatus {
                       active               (1),
                    -- notInService         (2)
                    -- notReady             (3)
                       createAndGo          (4),
                    -- createAndWait        (5)
                       destroy              (6)
                    }
            DESCRIPTION
                 "tmnxVdoGrpMdaRowStatus supports only 'active (1)',
                  'createAndGo (4)', and 'destroy (6)'."

        VARIATION   tmnxVdoGrpOperState
            SYNTAX  INTEGER {
                    -- noop                 (1)
                       inService            (2),
                       outOfService         (3)
                    }
            DESCRIPTION
                 "tmnxVdoGrpOperState supports only the values 'inService (2)'
                  and 'outOfService (3)'."

        VARIATION   tmnxVdoGrpRowStatus
            SYNTAX  RowStatus {
                       active               (1),
                    -- notInService         (2)
                    -- notReady             (3)
                       createAndGo          (4),
                    -- createAndWait        (5)
                       destroy              (6)
                    }
            DESCRIPTION
                 "tmnxVdoGrpRowStatus supports only 'active (1)', 'createAndGo
                  (4)', and 'destroy (6)'."

        VARIATION   tmnxVdoGrpSrcADIAdminState
            SYNTAX  INTEGER {
                    -- noop                 (1)
                       inService            (2),
                       outOfService         (3)
                    }
            DESCRIPTION
                 "tmnxVdoGrpSrcADIAdminState supports only the values 'inService
                  (2)' and 'outOfService (3)'."

        VARIATION   tmnxVdoGrpSrcFCCSrvrAdminState
            SYNTAX  INTEGER {
                    -- noop                 (1)
                       inService            (2),
                       outOfService         (3)
                    }
            DESCRIPTION
                 "tmnxVdoGrpSrcFCCSrvrAdminState supports only the values
                  'inService (2)' and 'outOfService (3)'."

        VARIATION   tmnxVdoGrpSrcGroupAddress
            SYNTAX  InetAddress (SIZE (4))
            DESCRIPTION
                 "tmnxVdoGrpSrcGroupAddress only supports the InetAddressType
                  value 'ipv4'."

        VARIATION   tmnxVdoGrpSrcGrpAddrType
            SYNTAX  InetAddressType {
                    -- unknown              (0)
                       ipv4                 (1)
                    -- ipv6                 (2)
                    -- ipv4z                (3)
                    -- ipv6z                (4)
                    -- dns                  (16)
                    }
            DESCRIPTION
                 "tmnxVdoGrpSrcGrpAddrType supports only the InetAddressType
                  value 'ipv4 (1)'."

        VARIATION   tmnxVdoGrpSrcRTClientAdminState
            SYNTAX  INTEGER {
                    -- noop                 (1)
                       inService            (2),
                       outOfService         (3)
                    }
            DESCRIPTION
                 "tmnxVdoGrpSrcRTClientAdminState supports only the values
                  'inService (2)' and 'outOfService (3)'."

        VARIATION   tmnxVdoGrpSrcRTClntRTSvrAddr
            SYNTAX  InetAddress (SIZE (4))
            DESCRIPTION
                 "tmnxVdoGrpSrcRTClntRTSvrAddr only supports the InetAddressType
                  value 'ipv4'."

        VARIATION   tmnxVdoGrpSrcRTClntRTSvrAddrType
            SYNTAX  InetAddressType {
                    -- unknown              (0)
                       ipv4                 (1)
                    -- ipv6                 (2)
                    -- ipv4z                (3)
                    -- ipv6z                (4)
                    -- dns                  (16)
                    }
            DESCRIPTION
                 "tmnxVdoGrpSrcRTClntRTSvrAddrType supports only the
                  InetAddressType value 'ipv4 (1)'."

        VARIATION   tmnxVdoGrpSrcRTSrvrAdminState
            SYNTAX  INTEGER {
                    -- noop                 (1)
                       inService            (2),
                       outOfService         (3)
                    }
            DESCRIPTION
                 "tmnxVdoGrpSrcRTSrvrAdminState supports only the values
                  'inService (2)' and 'outOfService (3)'."

        VARIATION   tmnxVdoGrpSrcSourceAddress
            SYNTAX  InetAddress (SIZE (4))
            DESCRIPTION
                 "tmnxVdoGrpSrcSourceAddress only supports the InetAddressType
                  value 'ipv4'."

        VARIATION   tmnxVdoGrpSrcSrcAddrType
            SYNTAX  InetAddressType {
                    -- unknown              (0)
                       ipv4                 (1)
                    -- ipv6                 (2)
                    -- ipv4z                (3)
                    -- ipv6z                (4)
                    -- dns                  (16)
                    }
            DESCRIPTION
                 "tmnxVdoGrpSrcSrcAddrType supports only the InetAddressType
                  value 'ipv4 (1)'."

        VARIATION   tmnxVdoIfAddrIpAddrType
            SYNTAX  InetAddressType {
                    -- unknown              (0)
                       ipv4                 (1)
                    -- ipv6                 (2)
                    -- ipv4z                (3)
                    -- ipv6z                (4)
                    -- dns                  (16)
                    }
            DESCRIPTION
                 "tmnxVdoIfAddrIpAddrType supports only the InetAddressType
                  value 'ipv4 (1)'."

        VARIATION   tmnxVdoIfAddrIpAddress
            SYNTAX  InetAddress (SIZE (4))
            DESCRIPTION
                 "tmnxVdoIfAddrIpAddress only supports the InetAddressType value
                  'ipv4'."

        VARIATION   tmnxVdoIfAddrRowStatus
            SYNTAX  RowStatus {
                       active               (1),
                    -- notInService         (2)
                    -- notReady             (3)
                       createAndGo          (4),
                    -- createAndWait        (5)
                       destroy              (6)
                    }
            DESCRIPTION
                 "tmnxVdoIfAddrRowStatus supports only 'active (1)',
                  'createAndGo (4)', and 'destroy (6)'."

        VARIATION   tmnxVdoIfAdminState
            SYNTAX  INTEGER {
                    -- noop                 (1)
                       inService            (2),
                       outOfService         (3)
                    }
            DESCRIPTION
                 "tmnxVdoIfAdminState supports only the values 'inService (2)'
                  and 'outOfService (3)'."

        VARIATION   tmnxVdoIfGatewayAddr
            SYNTAX  InetAddress (SIZE (0|4))
            DESCRIPTION
                 "tmnxVdoIfGatewayAddr only supports the InetAddressType values
                  'unknown' and 'ipv4'."

        VARIATION   tmnxVdoIfGatewayAddrType
            SYNTAX  InetAddressType {
                       unknown              (0),
                       ipv4                 (1)
                    -- ipv6                 (2)
                    -- ipv4z                (3)
                    -- ipv6z                (4)
                    -- dns                  (16)
                    }
            DESCRIPTION
                 "tmnxVdoIfGatewayAddrType supports only the InetAddressType
                  values 'unknown (0)' and 'ipv4 (1)'."

        VARIATION   tmnxVdoIfOperState
            SYNTAX  INTEGER {
                    -- noop                 (1)
                       inService            (2),
                       outOfService         (3)
                    }
            DESCRIPTION
                 "tmnxVdoIfOperState supports only the values 'inService (2)'
                  and 'outOfService (3)'."

        VARIATION   tmnxVdoIfRTClientAddr
            SYNTAX  InetAddress (SIZE (0|4))
            DESCRIPTION
                 "tmnxVdoIfRTClientAddr only supports the InetAddressType values
                  'unknown' and 'ipv4'."

        VARIATION   tmnxVdoIfRTClientAddrType
            SYNTAX  InetAddressType {
                       unknown              (0),
                       ipv4                 (1)
                    -- ipv6                 (2)
                    -- ipv4z                (3)
                    -- ipv6z                (4)
                    -- dns                  (16)
                    }
            DESCRIPTION
                 "tmnxVdoIfRTClientAddrType supports only the InetAddressType
                  values 'unknown (0)' and 'ipv4 (1)'."

        VARIATION   tmnxVdoIfRowStatus
            SYNTAX  RowStatus {
                       active               (1),
                    -- notInService         (2)
                    -- notReady             (3)
                       createAndGo          (4),
                    -- createAndWait        (5)
                       destroy              (6)
                    }
            DESCRIPTION
                 "tmnxVdoIfRowStatus supports only 'active (1)', 'createAndGo
                  (4)', and 'destroy (6)'."

        VARIATION   tmnxVdoIfScte30AdSrvrAddr
            SYNTAX  InetAddress (SIZE (4))
            DESCRIPTION
                 "tmnxVdoIfScte30AdSrvrAddr only supports the InetAddressType
                  value 'ipv4'."

        VARIATION   tmnxVdoIfScte30AdSrvrAddrType
            SYNTAX  InetAddressType {
                    -- unknown              (0)
                       ipv4                 (1)
                    -- ipv6                 (2)
                    -- ipv4z                (3)
                    -- ipv6z                (4)
                    -- dns                  (16)
                    }
            DESCRIPTION
                 "tmnxVdoIfScte30AdSrvrAddrType supports only the
                  InetAddressType value 'ipv4 (1)'."

        VARIATION   tmnxVdoIfScte30AdSrvrRowStatus
            SYNTAX  RowStatus {
                       active               (1),
                    -- notInService         (2)
                    -- notReady             (3)
                       createAndGo          (4),
                    -- createAndWait        (5)
                       destroy              (6)
                    }
            DESCRIPTION
                 "tmnxVdoIfScte30AdSrvrRowStatus supports only 'active (1)',
                  'createAndGo (4)', and 'destroy (6)'."

        VARIATION   tmnxVdoIfScte30ControlAddr
            SYNTAX  InetAddress (SIZE (0|4))
            DESCRIPTION
                 "tmnxVdoIfScte30ControlAddr only supports the InetAddressType
                  values 'unknown' and 'ipv4'."

        VARIATION   tmnxVdoIfScte30ControlAddrType
            SYNTAX  InetAddressType {
                       unknown              (0),
                       ipv4                 (1)
                    -- ipv6                 (2)
                    -- ipv4z                (3)
                    -- ipv6z                (4)
                    -- dns                  (16)
                    }
            DESCRIPTION
                 "tmnxVdoIfScte30ControlAddrType supports only the
                  InetAddressType values 'unknown (0)' and 'ipv4 (1)'."

        VARIATION   tmnxVdoIfScte30DataAddr
            SYNTAX  InetAddress (SIZE (0|4))
            DESCRIPTION
                 "tmnxVdoIfScte30DataAddr only supports the InetAddressType
                  values 'unknown' and 'ipv4'."

        VARIATION   tmnxVdoIfScte30DataAddrType
            SYNTAX  InetAddressType {
                       unknown              (0),
                       ipv4                 (1)
                    -- ipv6                 (2)
                    -- ipv4z                (3)
                    -- ipv6z                (4)
                    -- dns                  (16)
                    }
            DESCRIPTION
                 "tmnxVdoIfScte30DataAddrType supports only the InetAddressType
                  values 'unknown (0)' and 'ipv4 (1)'."

        VARIATION   tmnxVdoSGAdiServerAddr
            SYNTAX  InetAddress (SIZE (4))
            DESCRIPTION
                 "tmnxVdoSGAdiServerAddr only supports the InetAddressType value
                  'ipv4'."

        VARIATION   tmnxVdoSGAdiServerAddrType
            SYNTAX  InetAddressType {
                    -- unknown              (0)
                       ipv4                 (1)
                    -- ipv6                 (2)
                    -- ipv4z                (3)
                    -- ipv6z                (4)
                    -- dns                  (16)
                    }
            DESCRIPTION
                 "tmnxVdoSGAdiServerAddrType supports only the InetAddressType
                  value 'ipv4 (1)'."

        VARIATION   tmnxVdoSGSpliceAdServerAddr
            SYNTAX  InetAddress (SIZE (4))
            DESCRIPTION
                 "tmnxVdoSGSpliceAdServerAddr only supports the InetAddressType
                  value 'ipv4'."

        VARIATION   tmnxVdoSGSpliceAdServerAddrType
            SYNTAX  InetAddressType {
                    -- unknown              (0)
                       ipv4                 (1)
                    -- ipv6                 (2)
                    -- ipv4z                (3)
                    -- ipv6z                (4)
                    -- dns                  (16)
                    }
            DESCRIPTION
                 "tmnxVdoSGSpliceAdServerAddrType supports only the
                  InetAddressType value 'ipv4 (1)'."

        VARIATION   tmnxVdoSessionDestAddr
            SYNTAX  InetAddress (SIZE (4))
            DESCRIPTION
                 "tmnxVdoSessionDestAddr only supports the InetAddressType value
                  'ipv4'."

        VARIATION   tmnxVdoSessionDestAddrType
            SYNTAX  InetAddressType {
                    -- unknown              (0)
                       ipv4                 (1)
                    -- ipv6                 (2)
                    -- ipv4z                (3)
                    -- ipv6z                (4)
                    -- dns                  (16)
                    }
            DESCRIPTION
                 "tmnxVdoSessionDestAddrType supports only the InetAddressType
                  value 'ipv4 (1)'."

        VARIATION   tmnxVdoSessionSourceAddr
            SYNTAX  InetAddress (SIZE (4))
            DESCRIPTION
                 "tmnxVdoSessionSourceAddr only supports the InetAddressType
                  value 'ipv4'."

        VARIATION   tmnxVdoSessionSourceAddrType
            SYNTAX  InetAddressType {
                    -- unknown              (0)
                       ipv4                 (1)
                    -- ipv6                 (2)
                    -- ipv4z                (3)
                    -- ipv6z                (4)
                    -- dns                  (16)
                    }
            DESCRIPTION
                 "tmnxVdoSessionSourceAddrType supports only the InetAddressType
                  value 'ipv4 (1)'."

    ::= { tmnxSROSAgentV14v0  72 }

--
-- 7750c12 VIDEO CAPABILITIES
--
tmnx7750c12VideoV14v0             AGENT-CAPABILITIES
    PRODUCT-RELEASE "Nokia SROS"
    STATUS          current
    DESCRIPTION
         "Implementation of the video features on Nokia 7750 c12 systems release
          14.0."

--    SUPPORTS        TIMETRA-VIDEO-MIB
--        INCLUDES {
--        }

    ::= { tmnx7750c12AgentV14v0  72 }

--
-- 7750c4 VIDEO CAPABILITIES
--
tmnx7750c4VideoV14v0              AGENT-CAPABILITIES
    PRODUCT-RELEASE "Nokia SROS"
    STATUS          current
    DESCRIPTION
         "Implementation of the video features on Nokia 7750 c4 systems release
          14.0."

--    SUPPORTS        TIMETRA-VIDEO-MIB
--        INCLUDES {
--        }

    ::= { tmnx7750c4AgentV14v0  72 }

--
-- 7710 VIDEO CAPABILITIES
--
tmnx7710VideoV14v0                AGENT-CAPABILITIES
    PRODUCT-RELEASE "Nokia SROS"
    STATUS          current
    DESCRIPTION
         "Implementation of the video features on Nokia 7710 systems release
          14.0."

--    SUPPORTS        TIMETRA-VIDEO-MIB
--        INCLUDES {
--        }

    ::= { tmnx7710AgentV14v0  72 }

--
-- SROS VRRP CAPABILITIES
--
tmnxSROSVrrpV14v0                 AGENT-CAPABILITIES
    PRODUCT-RELEASE "Nokia SROS"
    STATUS          current
    DESCRIPTION
         "Implementation of VRRP protocol capabilities for Nokia SROS systems
          release 14.0."

    SUPPORTS        TIMETRA-VRRP-MIB
        INCLUDES {
           tVrrpBfdV9v0Group,
           tVrrpHostUnreachGroup,
           tVrrpHostUnreachableV7v0Group,
           tVrrpMasterV7v0Group,
           tVrrpMcIPsecGroup,
           tVrrpNotificationV10v0Group,
           tVrrpNotificationV7v0Group,
           tVrrpOpV7v0Group,
           tVrrpRouteUnknownV7v0Group,
           tVrrpRouterAdverV7v0Group,
           tVrrpStatV7v0Group,
           tmnxVrrpLagWtDnEvtGroup,
           tmnxVrrpNotificationV6v1Group,
           tmnxVrrpOperV10v0Group,
           tmnxVrrpOperV140v0Group,
           tmnxVrrpOperV6v1Group,
           tmnxVrrpPolicyAdminGroup,
           tmnxVrrpPolicyV5v0Group,
           tmnxVrrpPriorityEventsGroup,
           tmnxVrrpRouteMasterGroup,
           tmnxVrrpStatsGroup
        }

    SUPPORTS        TIMETRA-VRRP-V3-MIB
        INCLUDES {
           vrrpNotificationsGroup,
           vrrpNotifyObjsGroup,
           vrrpOperationsGroup,
           vrrpStatisticsGroup,
           vrrpTrapInfoGroup
        }

        VARIATION   vrrpAssociatedIpAddrRowStatus
            SYNTAX  RowStatus {
                       active               (1),
                    -- notInService         (2)
                    -- notReady             (3)
                       createAndGo          (4),
                    -- createAndWait        (5)
                       destroy              (6)
                    }
            DESCRIPTION
                 "vrrpAssociatedIpAddrRowStatus supports only 'active (1)',
                  'createAndGo (4)', and 'destroy (6)'."

        VARIATION   vrrpAssociatedStorageType
            SYNTAX  INTEGER {
                    -- other                (1)
                    -- volatile             (2)
                       nonVolatile          (3)
                    -- permanent            (4)
                    -- readOnly             (5)
                    }
            DESCRIPTION
                 "vrrpAssociatedStorageType supports only 'nonVolatile' storage
                  type."

        VARIATION   vrrpOperationsAcceptMode
            ACCESS  not-implemented
            DESCRIPTION
                 "vrrpOperationsAcceptMode is not implemented on Nokia SROS in
                  release 14.0.

                  vrrpOperationsAcceptMode is not supported. Instead
                  tVrrpOpPingReply, tVrrpOpTelnetReply and
                  tVrrpOpTracerouteReply should be used."

        VARIATION   vrrpOperationsAdvInterval
            SYNTAX  TimeInterval (10..4095)
            DESCRIPTION
                 "The range for vrrpOperationsAdvInterval is changed from
                  (1..4095) to (10..4095) as minimum time-interval supported on
                  the system is 10 centiseconds."

        VARIATION   vrrpOperationsPrimaryIpAddr
            ACCESS  read-only
            DESCRIPTION
                 "vrrpOperationsPrimaryIpAddr is implemented as read-only on
                  Nokia SROS in release 14.0."

        VARIATION   vrrpTrapProtoError
            ACCESS  not-implemented
            DESCRIPTION
                 "vrrpTrapProtoError is not implemented on Nokia SROS in release
                  14.0."

    SUPPORTS        VRRP-MIB
        INCLUDES {
           vrrpNotificationGroup,
           vrrpOperGroup,
           vrrpStatsGroup,
           vrrpTrapGroup
        }

        VARIATION   vrrpOperAdvertisementInterval
            SYNTAX  Integer32 (0..255)
            DESCRIPTION
                 "The range for vrrpOperAdvertisementInterval is changed from
                  (1..255) to (0..255) to support the interval time to be less
                  than 1 sec. To set milliseconds time interval the object
                  tmnxVrrpOperAdvIntervalMilSec should be specified. To get the
                  total interval time, add the value for
                  vrrpOperAdvertisementInterval in seconds and
                  tmnxVrrpOperAdvIntervalMilSec in milliseconds."

        VARIATION   vrrpOperAuthType
            ACCESS  read-only
            DESCRIPTION
                 "vrrpOperAuthType is implemented as read-only on Nokia SROS in
                  release 14.0."

        VARIATION   vrrpOperPrimaryIpAddr
            ACCESS  read-only
            DESCRIPTION
                 "vrrpOperPrimaryIpAddr is implemented as read-only on Nokia
                  SROS in release 14.0."

    ::= { tmnxSROSAgentV14v0  44 }

--
-- SROS VRTR CAPABILITIES
--
tmnxSROSVrtrV14v0                 AGENT-CAPABILITIES
    PRODUCT-RELEASE "Nokia SROS"
    STATUS          current
    DESCRIPTION
         "Implementation of Virtual Router capabilities for Nokia SROS systems
          release 14.0."

    SUPPORTS        TIMETRA-VRTR-MIB
        INCLUDES {
           tmnxDscpAppV6v0Group,
           tmnxMGVRtrIfV4v0Group,
           tmnxVRtrAggrRouteV12v0Group,
           tmnxVRtrBfdV11v0Group,
           tmnxVRtrBgpAutoRDGroup,
           tmnxVRtrBgpEvpn12v0Group,
           tmnxVRtrBgpEvpnIpRoutes12v0Group,
           tmnxVRtrBgpLblIpRoutes14v0Group,
           tmnxVRtrCidrNextHopOwnInstGroup,
           tmnxVRtrConfExtV12v0Group,
           tmnxVRtrConfFlowspecV14v0Group,
           tmnxVRtrCreation12v0Group,
           tmnxVRtrEntropyLabelGroup,
           tmnxVRtrExportBgpVpnV11v0Group,
           tmnxVRtrFibStatsV14v0Group,
           tmnxVRtrFibStatsV8v0Group,
           tmnxVRtrFlowSpecV11v0Group,
           tmnxVRtrFpeV14v0Group,
           tmnxVRtrGenerateICMPV12v0Group,
           tmnxVRtrGlobalV10v0Group,
           tmnxVRtrGlobalV6v0Group,
           tmnxVRtrGrtLocalMgmtV10v0Group,
           tmnxVRtrHoldDownTimeV12v0Group,
           tmnxVRtrIPsecStatGroup,
           tmnxVRtrIPv6IPsecStatGroup,
           tmnxVRtrIPv6IfV4v0Group,
           tmnxVRtrIPv6IpV5v0Group,
-- EXCLUDE tmnxVRtrIPv6MgtIfV7v0Group
           tmnxVRtrIPv6V4v0Group,
           tmnxVRtrIcmpTunnelingGroup,
           tmnxVRtrIcmpV4ParamV14v0Group,
           tmnxVRtrIcmpV4StatsV14v0Group,
           tmnxVRtrIfArpNbrLimitGroup,
           tmnxVRtrIfArpNbrNotifGroup,
           tmnxVRtrIfCpmProtectGroup,
           tmnxVRtrIfDHCP6V10v0Group,
           tmnxVRtrIfDHCP6V11v0Group,
           tmnxVRtrIfDHCP6V12v0Group,
           tmnxVRtrIfDHCP6V9v0Group,
           tmnxVRtrIfDHCPRelayV11v0Group,
           tmnxVRtrIfDHCPRelayV13v0Group,
           tmnxVRtrIfDHCPRelayV14v0Group,
           tmnxVRtrIfDHCPRelayV6v1Group,
           tmnxVRtrIfDHCPRelayV9v0Group,
           tmnxVRtrIfDhcpServerGroup,
           tmnxVRtrIfExtIfArpRetryTimerGrp,
           tmnxVRtrIfExtV12v0Group,
           tmnxVRtrIfExtV13v0Group,
           tmnxVRtrIfExtV14v0Group,
           tmnxVRtrIfIpReasV9v0Group,
           tmnxVRtrIfIpcpV6v0Group,
           tmnxVRtrIfLagPerLinkHashGroup,
           tmnxVRtrIfMacStatsV11v0Group,
           tmnxVRtrIfSendV12v0Group,
           tmnxVRtrIfStatsV11v0Group,
           tmnxVRtrIfStatsV9v0Group,
           tmnxVRtrIfSubscrAuthV3v0Group,
           tmnxVRtrIfV10v0Group,
           tmnxVRtrIfV14v0Group,
           tmnxVRtrInetAllCidrRouteV7v0Group,
           tmnxVRtrInetSRIndirectV13v0Group,
           tmnxVRtrInetSRIndirectV14v0Group,
           tmnxVRtrInetStaticRouteV7v0Group,
           tmnxVRtrIpPoolGroup,
           tmnxVRtrIpV13v0Group,
           tmnxVRtrIpV13v0ObsoletedGroup,
           tmnxVRtrIpv6RtrAdvertV11v0Group,
           tmnxVRtrLagEgrLoadBal12v0Group,
           tmnxVRtrLagHashLoadBal12v0Group,
           tmnxVRtrLdpIpv613v0Group,
           tmnxVRtrLoadBalEnhV13v0Group,
           tmnxVRtrLoopbackNotifGroup,
           tmnxVRtrLspBfdGroup,
           tmnxVRtrMSPwV9v0Group,
           tmnxVRtrMcastSpmsiEnhV13v0Group,
           tmnxVRtrMcastV11v0Group,
           tmnxVRtrMvpnPmsiV8v0Group,
           tmnxVRtrMvpnSrcRedV9v0R4Group,
           tmnxVRtrNatRedGroup,
           tmnxVRtrNetDomainGroup,
           tmnxVRtrNotificationNHRvplsArpGr,
           tmnxVRtrNotificationV10v0Group,
           tmnxVRtrNotificationV14v0Group,
           tmnxVRtrNotifyObjsNHRvplsArpGrp,
           tmnxVRtrPlcyAcctTempl12v0Group,
           tmnxVRtrPolicyGroup,
           tmnxVRtrQPPBV9v0R4Group,
           tmnxVRtrQosQGrplV10v0Group,
           tmnxVRtrRAV12v0Group,
           tmnxVRtrSrTeV14v0Group,
           tmnxVRtrStatV10v0Group,
           tmnxVRtrStatV11v0Group,
           tmnxVRtrStatV9v0Group,
           tmnxVRtrStaticRoutePrefixGroup,
           tmnxVRtrStaticRteCPEChkV6v0Group,
           tmnxVRtrStickyHashEcmp12v0Group,
           tmnxVRtrTunIntV8v0Group,
           tmnxVRtrTunnelExtTableV13v0Group,
           tmnxVRtrTunnelTableCBFV13v0Group,
           tmnxVRtrTunnelTableLSCV14v0Group,
           tmnxVRtrTunnelTableNhTV14v0Group,
           tmnxVRtrTunnelTableStatGroup,
           tmnxVRtrUniqueIfIndexGroup,
           tmnxVRtrV12v0Group,
           tmnxVRtrV13v0GenObsoletedGroup,
           tmnxVRtrV13v0IfStatsGroup,
           tmnxVRtrV14v0Group,
           tmnxVRtrV14v0NotifyObjsGroup,
           tmnxVRtrV6TunnelTableStatGroup,
           tmnxVRtrV6v1Group,
           tmnxVRtrV9v0Group,
           tmnxVRtrVccvBfd12v0Group,
           tmnxVRtrVirtualCPE12v0Group,
           tmnxVRtruRPFV10v0Group,
           tmnxVRtruRPFV7v0Group,
           tmnxVrtrDcpNotifyObjsV11v0Group,
           tmnxVrtrIfDCpuProtV11v0Group,
           tmnxVrtrIfDHCP6ProxyDuidGroup,
           tmnxVrtrIfDcpNotifyV11v0Group,
           tmnxvRtrIfAttributeGroup
        }

        VARIATION   vRtrFibStatMobileHostRoutes
            ACCESS  not-implemented
            DESCRIPTION
                 "vRtrFibStatMobileHostRoutes is not implemented on Nokia SROS
                  in release 14.0."

        VARIATION   vRtrFibStatV6MobileHostRoutes
            ACCESS  not-implemented
            DESCRIPTION
                 "vRtrFibStatV6MobileHostRoutes is not implemented on Nokia SROS
                  in release 14.0."

        VARIATION   vRtrIPv6RouteThresholdSoakTime
            ACCESS  read-only
            DESCRIPTION
                 "vRtrIPv6RouteThresholdSoakTime is implemented as read-only on
                  Nokia SROS in release 14.0."

        VARIATION   vRtrIfAlias
            ACCESS  read-only
            DESCRIPTION
                 "vRtrIfAlias is implemented as read-only on Nokia SROS in
                  release 14.0."

        VARIATION   vRtrIfBfdType
            SYNTAX  INTEGER {
                       cpmNp(1),
                       auto(2)
                    }
            DESCRIPTION
                 "cpmNp(1) is not supported on SROS SR-1 or ESS-1."

        VARIATION   vRtrIfDHCP6ProxyDuidEnIdDataType
            SYNTAX  INTEGER {
                    -- ipv4(1)
                       ascii(2),
                       hex(3)
                    -- ipv6(4)
                    -- domain(5)
                    }
            DESCRIPTION
                 "The only allowed values for this object are 'ascii(2)' and
                  'hex(3)'."

        VARIATION   vRtrIfDHCPLeasePopulate
            DESCRIPTION
                 "The default value of vRtrIfDHCPLeasePopulate is '1', not '0',
                  when the interface running DHCP has vRtrIfType
                  'serviceIesGroup'."

        VARIATION   vRtrIfDHCPRelaySiaddrOvrAddr
            SYNTAX  InetAddress (SIZE (0|4))
            DESCRIPTION
                 "vRtrIfDHCPRelaySiaddrOvrAddr supports only InetAddressType
                  values 'unknown (0)' and 'ipv4 (1)'."

        VARIATION   vRtrIfDHCPRelaySiaddrOvrAddrType
            SYNTAX  InetAddressType {
                       unknown              (0),
                       ipv4                 (1)
                    -- ipv6                 (2)
                    -- ipv4z                (3)
                    -- ipv6z                (4)
                    -- dns                  (16)
                    }
            DESCRIPTION
                 "vRtrIfDHCPRelaySiaddrOvrAddrType supports only the
                  InetAddressType values 'unknown (0)' and 'ipv4 (1)'."

        VARIATION   vRtrIfIpReasBytesRx
            ACCESS  not-implemented
            DESCRIPTION
                 "vRtrIfIpReasBytesRx is not implemented on Nokia SROS in
                  release 14.0."

        VARIATION   vRtrIfIpReasBytesRxHigh32
            ACCESS  not-implemented
            DESCRIPTION
                 "vRtrIfIpReasBytesRxHigh32 is not implemented on Nokia SROS in
                  release 14.0."

        VARIATION   vRtrIfIpReasBytesRxLow32
            ACCESS  not-implemented
            DESCRIPTION
                 "vRtrIfIpReasBytesRxLow32 is not implemented on Nokia SROS in
                  release 14.0."

        VARIATION   vRtrIfIpReasBytesTx
            ACCESS  not-implemented
            DESCRIPTION
                 "vRtrIfIpReasBytesTx is not implemented on Nokia SROS in
                  release 14.0."

        VARIATION   vRtrIfIpReasBytesTxHigh32
            ACCESS  not-implemented
            DESCRIPTION
                 "vRtrIfIpReasBytesTxHigh32 is not implemented on Nokia SROS in
                  release 14.0."

        VARIATION   vRtrIfIpReasBytesTxLow32
            ACCESS  not-implemented
            DESCRIPTION
                 "vRtrIfIpReasBytesTxLow32 is not implemented on Nokia SROS in
                  release 14.0."

        VARIATION   vRtrIfIpReasContextValue
            ACCESS  not-implemented
            DESCRIPTION
                 "vRtrIfIpReasContextValue is not implemented on Nokia SROS in
                  release 14.0."

        VARIATION   vRtrIfIpReasFragBytesRcvd
            ACCESS  not-implemented
            DESCRIPTION
                 "vRtrIfIpReasFragBytesRcvd is not implemented on Nokia SROS in
                  release 14.0."

        VARIATION   vRtrIfIpReasFragBytesRcvdHigh32
            ACCESS  not-implemented
            DESCRIPTION
                 "vRtrIfIpReasFragBytesRcvdHigh32 is not implemented on Nokia
                  SROS in release 14.0."

        VARIATION   vRtrIfIpReasFragBytesRcvdLow32
            ACCESS  not-implemented
            DESCRIPTION
                 "vRtrIfIpReasFragBytesRcvdLow32 is not implemented on Nokia
                  SROS in release 14.0."

        VARIATION   vRtrIfIpReasFragBytesReas
            ACCESS  not-implemented
            DESCRIPTION
                 "vRtrIfIpReasFragBytesReas is not implemented on Nokia SROS in
                  release 14.0."

        VARIATION   vRtrIfIpReasFragBytesReasHigh32
            ACCESS  not-implemented
            DESCRIPTION
                 "vRtrIfIpReasFragBytesReasHigh32 is not implemented on Nokia
                  SROS in release 14.0."

        VARIATION   vRtrIfIpReasFragBytesReasLow32
            ACCESS  not-implemented
            DESCRIPTION
                 "vRtrIfIpReasFragBytesReasLow32 is not implemented on Nokia
                  SROS in release 14.0."

        VARIATION   vRtrIfIpReasFragDisc
            ACCESS  not-implemented
            DESCRIPTION
                 "vRtrIfIpReasFragDisc is not implemented on Nokia SROS in
                  release 14.0."

        VARIATION   vRtrIfIpReasFragDiscHigh32
            ACCESS  not-implemented
            DESCRIPTION
                 "vRtrIfIpReasFragDiscHigh32 is not implemented on Nokia SROS in
                  release 14.0."

        VARIATION   vRtrIfIpReasFragDiscLow32
            ACCESS  not-implemented
            DESCRIPTION
                 "vRtrIfIpReasFragDiscLow32 is not implemented on Nokia SROS in
                  release 14.0."

        VARIATION   vRtrIfIpReasFragPktsRcvd
            ACCESS  not-implemented
            DESCRIPTION
                 "vRtrIfIpReasFragPktsRcvd is not implemented on Nokia SROS in
                  release 14.0."

        VARIATION   vRtrIfIpReasFragPktsRcvdHigh32
            ACCESS  not-implemented
            DESCRIPTION
                 "vRtrIfIpReasFragPktsRcvdHigh32 is not implemented on Nokia
                  SROS in release 14.0."

        VARIATION   vRtrIfIpReasFragPktsRcvdLow32
            ACCESS  not-implemented
            DESCRIPTION
                 "vRtrIfIpReasFragPktsRcvdLow32 is not implemented on Nokia SROS
                  in release 14.0."

        VARIATION   vRtrIfIpReasFragPktsReas
            ACCESS  not-implemented
            DESCRIPTION
                 "vRtrIfIpReasFragPktsReas is not implemented on Nokia SROS in
                  release 14.0."

        VARIATION   vRtrIfIpReasFragPktsReasHigh32
            ACCESS  not-implemented
            DESCRIPTION
                 "vRtrIfIpReasFragPktsReasHigh32 is not implemented on Nokia
                  SROS in release 14.0."

        VARIATION   vRtrIfIpReasFragPktsReasLow32
            ACCESS  not-implemented
            DESCRIPTION
                 "vRtrIfIpReasFragPktsReasLow32 is not implemented on Nokia SROS
                  in release 14.0."

        VARIATION   vRtrIfIpReasFragReasErrors
            ACCESS  not-implemented
            DESCRIPTION
                 "vRtrIfIpReasFragReasErrors is not implemented on Nokia SROS in
                  release 14.0."

        VARIATION   vRtrIfIpReasFragReasErrorsHigh32
            ACCESS  not-implemented
            DESCRIPTION
                 "vRtrIfIpReasFragReasErrorsHigh32 is not implemented on Nokia
                  SROS in release 14.0."

        VARIATION   vRtrIfIpReasFragReasErrorsLow32
            ACCESS  not-implemented
            DESCRIPTION
                 "vRtrIfIpReasFragReasErrorsLow32 is not implemented on Nokia
                  SROS in release 14.0."

        VARIATION   vRtrIfIpReasOutBufRes
            ACCESS  not-implemented
            DESCRIPTION
                 "vRtrIfIpReasOutBufRes is not implemented on Nokia SROS in
                  release 14.0."

        VARIATION   vRtrIfIpReasOutBufResHigh32
            ACCESS  not-implemented
            DESCRIPTION
                 "vRtrIfIpReasOutBufResHigh32 is not implemented on Nokia SROS
                  in release 14.0."

        VARIATION   vRtrIfIpReasOutBufResLow32
            ACCESS  not-implemented
            DESCRIPTION
                 "vRtrIfIpReasOutBufResLow32 is not implemented on Nokia SROS in
                  release 14.0."

        VARIATION   vRtrIfIpReasPktsRx
            ACCESS  not-implemented
            DESCRIPTION
                 "vRtrIfIpReasPktsRx is not implemented on Nokia SROS in release
                  14.0."

        VARIATION   vRtrIfIpReasPktsRxHigh32
            ACCESS  not-implemented
            DESCRIPTION
                 "vRtrIfIpReasPktsRxHigh32 is not implemented on Nokia SROS in
                  release 14.0."

        VARIATION   vRtrIfIpReasPktsRxLow32
            ACCESS  not-implemented
            DESCRIPTION
                 "vRtrIfIpReasPktsRxLow32 is not implemented on Nokia SROS in
                  release 14.0."

        VARIATION   vRtrIfIpReasPktsTx
            ACCESS  not-implemented
            DESCRIPTION
                 "vRtrIfIpReasPktsTx is not implemented on Nokia SROS in release
                  14.0."

        VARIATION   vRtrIfIpReasPktsTxHigh32
            ACCESS  not-implemented
            DESCRIPTION
                 "vRtrIfIpReasPktsTxHigh32 is not implemented on Nokia SROS in
                  release 14.0."

        VARIATION   vRtrIfIpReasPktsTxLow32
            ACCESS  not-implemented
            DESCRIPTION
                 "vRtrIfIpReasPktsTxLow32 is not implemented on Nokia SROS in
                  release 14.0."

        VARIATION   vRtrIfIpReasPortID
            ACCESS  not-implemented
            DESCRIPTION
                 "vRtrIfIpReasPortID is not implemented on Nokia SROS in release
                  14.0."

        VARIATION   vRtrIfIpReasV6BytesRx
            ACCESS  not-implemented
            DESCRIPTION
                 "vRtrIfIpReasV6BytesRx is not implemented on Nokia SROS in
                  release 14.0."

        VARIATION   vRtrIfIpReasV6BytesRxHigh32
            ACCESS  not-implemented
            DESCRIPTION
                 "vRtrIfIpReasV6BytesRxHigh32 is not implemented on Nokia SROS
                  in release 14.0."

        VARIATION   vRtrIfIpReasV6BytesRxLow32
            ACCESS  not-implemented
            DESCRIPTION
                 "vRtrIfIpReasV6BytesRxLow32 is not implemented on Nokia SROS in
                  release 14.0."

        VARIATION   vRtrIfIpReasV6BytesTx
            ACCESS  not-implemented
            DESCRIPTION
                 "vRtrIfIpReasV6BytesTx is not implemented on Nokia SROS in
                  release 14.0."

        VARIATION   vRtrIfIpReasV6BytesTxHigh32
            ACCESS  not-implemented
            DESCRIPTION
                 "vRtrIfIpReasV6BytesTxHigh32 is not implemented on Nokia SROS
                  in release 14.0."

        VARIATION   vRtrIfIpReasV6BytesTxLow32
            ACCESS  not-implemented
            DESCRIPTION
                 "vRtrIfIpReasV6BytesTxLow32 is not implemented on Nokia SROS in
                  release 14.0."

        VARIATION   vRtrIfIpReasV6FragBytesRcvd
            ACCESS  not-implemented
            DESCRIPTION
                 "vRtrIfIpReasV6FragBytesRcvd is not implemented on Nokia SROS
                  in release 14.0."

        VARIATION   vRtrIfIpReasV6FragBytesRcvdH32
            ACCESS  not-implemented
            DESCRIPTION
                 "vRtrIfIpReasV6FragBytesRcvdH32 is not implemented on Nokia
                  SROS in release 14.0."

        VARIATION   vRtrIfIpReasV6FragBytesRcvdL32
            ACCESS  not-implemented
            DESCRIPTION
                 "vRtrIfIpReasV6FragBytesRcvdL32 is not implemented on Nokia
                  SROS in release 14.0."

        VARIATION   vRtrIfIpReasV6FragBytesReas
            ACCESS  not-implemented
            DESCRIPTION
                 "vRtrIfIpReasV6FragBytesReas is not implemented on Nokia SROS
                  in release 14.0."

        VARIATION   vRtrIfIpReasV6FragBytesReasH32
            ACCESS  not-implemented
            DESCRIPTION
                 "vRtrIfIpReasV6FragBytesReasH32 is not implemented on Nokia
                  SROS in release 14.0."

        VARIATION   vRtrIfIpReasV6FragBytesReasL32
            ACCESS  not-implemented
            DESCRIPTION
                 "vRtrIfIpReasV6FragBytesReasL32 is not implemented on Nokia
                  SROS in release 14.0."

        VARIATION   vRtrIfIpReasV6FragDisc
            ACCESS  not-implemented
            DESCRIPTION
                 "vRtrIfIpReasV6FragDisc is not implemented on Nokia SROS in
                  release 14.0."

        VARIATION   vRtrIfIpReasV6FragDiscHigh32
            ACCESS  not-implemented
            DESCRIPTION
                 "vRtrIfIpReasV6FragDiscHigh32 is not implemented on Nokia SROS
                  in release 14.0."

        VARIATION   vRtrIfIpReasV6FragDiscLow32
            ACCESS  not-implemented
            DESCRIPTION
                 "vRtrIfIpReasV6FragDiscLow32 is not implemented on Nokia SROS
                  in release 14.0."

        VARIATION   vRtrIfIpReasV6FragPktsRcvd
            ACCESS  not-implemented
            DESCRIPTION
                 "vRtrIfIpReasV6FragPktsRcvd is not implemented on Nokia SROS in
                  release 14.0."

        VARIATION   vRtrIfIpReasV6FragPktsRcvdHigh32
            ACCESS  not-implemented
            DESCRIPTION
                 "vRtrIfIpReasV6FragPktsRcvdHigh32 is not implemented on Nokia
                  SROS in release 14.0."

        VARIATION   vRtrIfIpReasV6FragPktsRcvdLow32
            ACCESS  not-implemented
            DESCRIPTION
                 "vRtrIfIpReasV6FragPktsRcvdLow32 is not implemented on Nokia
                  SROS in release 14.0."

        VARIATION   vRtrIfIpReasV6FragPktsReas
            ACCESS  not-implemented
            DESCRIPTION
                 "vRtrIfIpReasV6FragPktsReas is not implemented on Nokia SROS in
                  release 14.0."

        VARIATION   vRtrIfIpReasV6FragPktsReasHigh32
            ACCESS  not-implemented
            DESCRIPTION
                 "vRtrIfIpReasV6FragPktsReasHigh32 is not implemented on Nokia
                  SROS in release 14.0."

        VARIATION   vRtrIfIpReasV6FragPktsReasLow32
            ACCESS  not-implemented
            DESCRIPTION
                 "vRtrIfIpReasV6FragPktsReasLow32 is not implemented on Nokia
                  SROS in release 14.0."

        VARIATION   vRtrIfIpReasV6FragReasErrors
            ACCESS  not-implemented
            DESCRIPTION
                 "vRtrIfIpReasV6FragReasErrors is not implemented on Nokia SROS
                  in release 14.0."

        VARIATION   vRtrIfIpReasV6FragReasErrorsH32
            ACCESS  not-implemented
            DESCRIPTION
                 "vRtrIfIpReasV6FragReasErrorsH32 is not implemented on Nokia
                  SROS in release 14.0."

        VARIATION   vRtrIfIpReasV6FragReasErrorsL32
            ACCESS  not-implemented
            DESCRIPTION
                 "vRtrIfIpReasV6FragReasErrorsL32 is not implemented on Nokia
                  SROS in release 14.0."

        VARIATION   vRtrIfIpReasV6OutBufRes
            ACCESS  not-implemented
            DESCRIPTION
                 "vRtrIfIpReasV6OutBufRes is not implemented on Nokia SROS in
                  release 14.0."

        VARIATION   vRtrIfIpReasV6OutBufResHigh32
            ACCESS  not-implemented
            DESCRIPTION
                 "vRtrIfIpReasV6OutBufResHigh32 is not implemented on Nokia SROS
                  in release 14.0."

        VARIATION   vRtrIfIpReasV6OutBufResLow32
            ACCESS  not-implemented
            DESCRIPTION
                 "vRtrIfIpReasV6OutBufResLow32 is not implemented on Nokia SROS
                  in release 14.0."

        VARIATION   vRtrIfIpReasV6PktsRx
            ACCESS  not-implemented
            DESCRIPTION
                 "vRtrIfIpReasV6PktsRx is not implemented on Nokia SROS in
                  release 14.0."

        VARIATION   vRtrIfIpReasV6PktsRxHigh32
            ACCESS  not-implemented
            DESCRIPTION
                 "vRtrIfIpReasV6PktsRxHigh32 is not implemented on Nokia SROS in
                  release 14.0."

        VARIATION   vRtrIfIpReasV6PktsRxLow32
            ACCESS  not-implemented
            DESCRIPTION
                 "vRtrIfIpReasV6PktsRxLow32 is not implemented on Nokia SROS in
                  release 14.0."

        VARIATION   vRtrIfIpReasV6PktsTx
            ACCESS  not-implemented
            DESCRIPTION
                 "vRtrIfIpReasV6PktsTx is not implemented on Nokia SROS in
                  release 14.0."

        VARIATION   vRtrIfIpReasV6PktsTxHigh32
            ACCESS  not-implemented
            DESCRIPTION
                 "vRtrIfIpReasV6PktsTxHigh32 is not implemented on Nokia SROS in
                  release 14.0."

        VARIATION   vRtrIfIpReasV6PktsTxLow32
            ACCESS  not-implemented
            DESCRIPTION
                 "vRtrIfIpReasV6PktsTxLow32 is not implemented on Nokia SROS in
                  release 14.0."

        VARIATION   vRtrIfIpcpPeerAddr
            SYNTAX  InetAddress (SIZE (0|4))
            DESCRIPTION
                 "vRtrIfIpcpPeerAddr supports only InetAddressType values
                  'unknown (0)' and 'ipv4 (1)'."

        VARIATION   vRtrIfIpcpPeerAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPeerAddrType supports only the InetAddressType
                  values 'unknown (0)' and 'ipv4 (1)'."

        VARIATION   vRtrIfIpcpPriDnsAddr
            SYNTAX  InetAddress (SIZE (0|4))
            DESCRIPTION
                 "vRtrIfIpcpPriDnsAddr supports only InetAddressType values
                  'unknown (0)' and 'ipv4 (1)'."

        VARIATION   vRtrIfIpcpPriDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPriDnsAddrType supports only the InetAddressType
                  values 'unknown (0)' and 'ipv4 (1)'."

        VARIATION   vRtrIfIpcpSecDnsAddr
            SYNTAX  InetAddress (SIZE (0|4))
            DESCRIPTION
                 "vRtrIfIpcpSecDnsAddr supports only InetAddressType values
                  'unknown (0)' and 'ipv4 (1)'."

        VARIATION   vRtrIfIpcpSecDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpSecDnsAddrType supports only the InetAddressType
                  values 'unknown (0)' and 'ipv4 (1)'."

        VARIATION   vRtrIfIpv6TrackMobile
            ACCESS  not-implemented
            DESCRIPTION
                 "vRtrIfIpv6TrackMobile is not implemented on Nokia SROS in
                  release 14.0."

        VARIATION   vRtrIfTrackMobile
            ACCESS  not-implemented
            DESCRIPTION
                 "vRtrIfTrackMobile is not implemented on Nokia SROS in release
                  14.0."

        VARIATION   vRtrIgnoreIcmpRedirect
            DESCRIPTION
                 "The default value of vRtrIgnoreIcmpRedirect is changed to
                  'true' from 'false' in release 4.0-R13 and 5.0-R3."

        VARIATION   vRtrInetSRIndirectEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectSrTeLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteIndexEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRoutePfxEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrIpCidrRoutePreference
            ACCESS  read-only
            DESCRIPTION
                 "vRtrIpCidrRoutePreference is implemented as read-only on Nokia
                  SROS in release 14.0."

        VARIATION   vRtrIpPoolIsRemote
            ACCESS  not-implemented
            DESCRIPTION
                 "vRtrIpPoolIsRemote is not implemented on Nokia SROS in release
                  14.0."

        VARIATION   vRtrLdpShortcut
            SYNTAX  TmnxEnabledDisabled
            DESCRIPTION
                 "vRtrLdpShortcut is only supported in the default or base
                  routing instance."

        VARIATION   vRtrLdpTunIfSenderAddr
            SYNTAX  InetAddress (SIZE (4))
            DESCRIPTION
                 "vRtrRsvpTunIfSenderAddr supports only InetAddressType 'ipv4'."

        VARIATION   vRtrLdpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrLdpTunIfSenderAddrType supports only the InetAddressType
                  value 'ipv4 (1)'."

        VARIATION   vRtrMobileHostActiveRoutes
            ACCESS  not-implemented
            DESCRIPTION
                 "vRtrMobileHostActiveRoutes is not implemented on Nokia SROS in
                  release 14.0."

        VARIATION   vRtrMobileHostRoutes
            ACCESS  not-implemented
            DESCRIPTION
                 "vRtrMobileHostRoutes is not implemented on Nokia SROS in
                  release 14.0."

        VARIATION   vRtrMvpnIpmsiType
            SYNTAX  INTEGER {
                       none                 (0),
                    -- rsvp                 (1)
                       pim                  (2)
                    }
            DESCRIPTION
                 "The value 'rsvp(1)' is not supported in the release 8.0R1."

        VARIATION   vRtrMvpnSpmsiType
            SYNTAX  INTEGER {
                       none                 (0),
                    -- rsvp                 (1)
                       pim                  (2)
                    }
            DESCRIPTION
                 "The value 'rsvp(1)' is not supported in the release 8.0R1."

        VARIATION   vRtrNextVRtrID
            ACCESS  read-only
            DESCRIPTION
                 "vRtrNextVRtrID is implemented as read-only on Nokia SROS in
                  release 14.0."

        VARIATION   vRtrRouteThresholdSoakTime
            ACCESS  read-only
            DESCRIPTION
                 "vRtrRouteThresholdSoakTime is implemented as read-only on
                  Nokia SROS in release 14.0."

        VARIATION   vRtrRsvpTunIfSenderAddr
            SYNTAX  InetAddress (SIZE (4))
            DESCRIPTION
                 "vRtrRsvpTunIfSenderAddr supports only InetAddressType 'ipv4'."

        VARIATION   vRtrRsvpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSenderAddrType supports only the InetAddressType
                  value 'ipv4 (1)'."

        VARIATION   vRtrRsvpTunIfSrcAddr
            SYNTAX  InetAddress (SIZE (4))
            DESCRIPTION
                 "vRtrRsvpTunIfSenderAddr supports only InetAddressType 'ipv4'."

        VARIATION   vRtrRsvpTunIfSrcAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSrcAddrType supports only the InetAddressType
                  value 'ipv4 (1)'."

        VARIATION   vRtrRsvpTunIfStandbyAddr
            SYNTAX  InetAddress (SIZE (4))
            DESCRIPTION
                 "vRtrRsvpTunIfSenderAddr supports only InetAddressType 'ipv4'."

        VARIATION   vRtrRsvpTunIfStandbyAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfStandbyAddrType supports only the InetAddressType
                  value 'ipv4 (1)'."

        VARIATION   vRtrV6MobileHostActiveRoutes
            ACCESS  not-implemented
            DESCRIPTION
                 "vRtrV6MobileHostActiveRoutes is not implemented on Nokia SROS
                  in release 14.0."

        VARIATION   vRtrV6MobileHostRoutes
            ACCESS  not-implemented
            DESCRIPTION
                 "vRtrV6MobileHostRoutes is not implemented on Nokia SROS in
                  release 14.0."

    ::= { tmnxSROSAgentV14v0  45 }

--
-- 7750c12 VRTR CAPABILITIES
--
tmnx7750c12VrtrV14v0              AGENT-CAPABILITIES
    PRODUCT-RELEASE "Nokia SROS"
    STATUS          current
    DESCRIPTION
         "Implementation of Virtual Router capabilities for Nokia 7750 c12
          systems release 14.0."

    SUPPORTS        TIMETRA-VRTR-MIB
        INCLUDES {
           tmnxDscpAppV6v0Group,
           tmnxMGVRtrIfV4v0Group,
           tmnxVRtrAggrRouteV12v0Group,
           tmnxVRtrBfdV11v0Group,
           tmnxVRtrBgpAutoRDGroup,
           tmnxVRtrBgpEvpn12v0Group,
           tmnxVRtrBgpEvpnIpRoutes12v0Group,
           tmnxVRtrBgpLblIpRoutes14v0Group,
           tmnxVRtrCidrNextHopOwnInstGroup,
           tmnxVRtrConfExtV12v0Group,
           tmnxVRtrConfFlowspecV14v0Group,
           tmnxVRtrCreation12v0Group,
           tmnxVRtrEntropyLabelGroup,
           tmnxVRtrExportBgpVpnV11v0Group,
           tmnxVRtrFibStatsV14v0Group,
           tmnxVRtrFibStatsV8v0Group,
           tmnxVRtrFlowSpecV11v0Group,
           tmnxVRtrFpeV14v0Group,
           tmnxVRtrGenerateICMPV12v0Group,
           tmnxVRtrGlobalV10v0Group,
           tmnxVRtrGlobalV6v0Group,
           tmnxVRtrGrtLocalMgmtV10v0Group,
           tmnxVRtrHoldDownTimeV12v0Group,
           tmnxVRtrIPsecStatGroup,
           tmnxVRtrIPv6IPsecStatGroup,
           tmnxVRtrIPv6IfV4v0Group,
           tmnxVRtrIPv6IpV5v0Group,
-- EXCLUDE tmnxVRtrIPv6MgtIfV7v0Group
           tmnxVRtrIPv6V4v0Group,
           tmnxVRtrIcmpTunnelingGroup,
           tmnxVRtrIcmpV4ParamV14v0Group,
           tmnxVRtrIcmpV4StatsV14v0Group,
           tmnxVRtrIfArpNbrLimitGroup,
           tmnxVRtrIfArpNbrNotifGroup,
-- EXCLUDE tmnxVRtrIfCpmProtectGroup
           tmnxVRtrIfDHCP6V10v0Group,
           tmnxVRtrIfDHCP6V11v0Group,
           tmnxVRtrIfDHCP6V12v0Group,
           tmnxVRtrIfDHCP6V9v0Group,
           tmnxVRtrIfDHCPRelayV11v0Group,
           tmnxVRtrIfDHCPRelayV13v0Group,
           tmnxVRtrIfDHCPRelayV14v0Group,
           tmnxVRtrIfDHCPRelayV6v1Group,
           tmnxVRtrIfDHCPRelayV9v0Group,
           tmnxVRtrIfDhcpServerGroup,
           tmnxVRtrIfExtIfArpRetryTimerGrp,
           tmnxVRtrIfExtV12v0Group,
           tmnxVRtrIfExtV13v0Group,
           tmnxVRtrIfExtV14v0Group,
           tmnxVRtrIfIpReasV9v0Group,
           tmnxVRtrIfIpcpV6v0Group,
           tmnxVRtrIfLagPerLinkHashGroup,
           tmnxVRtrIfMacStatsV11v0Group,
           tmnxVRtrIfSendV12v0Group,
           tmnxVRtrIfStatsV11v0Group,
           tmnxVRtrIfStatsV9v0Group,
           tmnxVRtrIfSubscrAuthV3v0Group,
           tmnxVRtrIfV10v0Group,
           tmnxVRtrIfV14v0Group,
           tmnxVRtrInetAllCidrRouteV7v0Group,
           tmnxVRtrInetSRIndirectV13v0Group,
           tmnxVRtrInetSRIndirectV14v0Group,
           tmnxVRtrInetStaticRouteV7v0Group,
           tmnxVRtrIpPoolGroup,
           tmnxVRtrIpV13v0Group,
           tmnxVRtrIpV13v0ObsoletedGroup,
           tmnxVRtrIpv6RtrAdvertV11v0Group,
           tmnxVRtrLagEgrLoadBal12v0Group,
           tmnxVRtrLagHashLoadBal12v0Group,
           tmnxVRtrLdpIpv613v0Group,
           tmnxVRtrLoadBalEnhV13v0Group,
           tmnxVRtrLoopbackNotifGroup,
           tmnxVRtrLspBfdGroup,
           tmnxVRtrMSPwV9v0Group,
           tmnxVRtrMcastSpmsiEnhV13v0Group,
           tmnxVRtrMcastV11v0Group,
           tmnxVRtrMvpnPmsiV8v0Group,
           tmnxVRtrMvpnSrcRedV9v0R4Group,
           tmnxVRtrNatRedGroup,
           tmnxVRtrNetDomainGroup,
           tmnxVRtrNotificationNHRvplsArpGr,
           tmnxVRtrNotificationV10v0Group,
           tmnxVRtrNotificationV14v0Group,
           tmnxVRtrNotifyObjsNHRvplsArpGrp,
           tmnxVRtrPlcyAcctTempl12v0Group,
           tmnxVRtrPolicyGroup,
           tmnxVRtrQPPBV9v0R4Group,
           tmnxVRtrQosQGrplV10v0Group,
           tmnxVRtrRAV12v0Group,
           tmnxVRtrSrTeV14v0Group,
           tmnxVRtrStatV10v0Group,
           tmnxVRtrStatV11v0Group,
           tmnxVRtrStatV9v0Group,
           tmnxVRtrStaticRoutePrefixGroup,
           tmnxVRtrStaticRteCPEChkV6v0Group,
           tmnxVRtrStickyHashEcmp12v0Group,
           tmnxVRtrTunIntV8v0Group,
           tmnxVRtrTunnelExtTableV13v0Group,
           tmnxVRtrTunnelTableCBFV13v0Group,
           tmnxVRtrTunnelTableLSCV14v0Group,
           tmnxVRtrTunnelTableNhTV14v0Group,
           tmnxVRtrTunnelTableStatGroup,
           tmnxVRtrUniqueIfIndexGroup,
           tmnxVRtrV12v0Group,
           tmnxVRtrV13v0GenObsoletedGroup,
           tmnxVRtrV13v0IfStatsGroup,
           tmnxVRtrV14v0Group,
           tmnxVRtrV14v0NotifyObjsGroup,
           tmnxVRtrV6TunnelTableStatGroup,
           tmnxVRtrV6v1Group,
           tmnxVRtrV9v0Group,
           tmnxVRtrVccvBfd12v0Group,
           tmnxVRtrVirtualCPE12v0Group,
           tmnxVRtruRPFV10v0Group,
           tmnxVRtruRPFV7v0Group,
           tmnxVrtrDcpNotifyObjsV11v0Group,
           tmnxVrtrIfDCpuProtV11v0Group,
           tmnxVrtrIfDHCP6ProxyDuidGroup,
           tmnxVrtrIfDcpNotifyV11v0Group,
           tmnxvRtrIfAttributeGroup
        }

        VARIATION   vRtrFibStatMobileHostRoutes
            ACCESS  not-implemented
            DESCRIPTION
                 "vRtrFibStatMobileHostRoutes is not implemented on Nokia 7750
                  c12 in release 14.0."

        VARIATION   vRtrFibStatV6MobileHostRoutes
            ACCESS  not-implemented
            DESCRIPTION
                 "vRtrFibStatV6MobileHostRoutes is not implemented on Nokia 7750
                  c12 in release 14.0."

        VARIATION   vRtrIPv6RouteThresholdSoakTime
            ACCESS  read-only
            DESCRIPTION
                 "vRtrIPv6RouteThresholdSoakTime is implemented as read-only on
                  Nokia 7750 c12 in release 14.0."

        VARIATION   vRtrIfAlias
            ACCESS  read-only
            DESCRIPTION
                 "vRtrIfAlias is implemented as read-only on Nokia 7750 c12 in
                  release 14.0."

        VARIATION   vRtrIfBfdType
            SYNTAX  INTEGER {
                    -- cpmNp(1)
                       auto(2)
                    }
            DESCRIPTION
                 "cpmNp(1) is not supported on Nokia 7750 c12."

        VARIATION   vRtrIfDHCP6ProxyDuidEnIdDataType
            SYNTAX  INTEGER {
                    -- ipv4(1)
                       ascii(2),
                       hex(3)
                    -- ipv6(4)
                    -- domain(5)
                    }
            DESCRIPTION
                 "The only allowed values for this object are 'ascii(2)' and
                  'hex(3)'."

        VARIATION   vRtrIfDHCPLeasePopulate
            DESCRIPTION
                 "The default value of vRtrIfDHCPLeasePopulate is '1', not '0',
                  when the interface running DHCP has vRtrIfType
                  'serviceIesGroup'."

        VARIATION   vRtrIfDHCPRelaySiaddrOvrAddr
            SYNTAX  InetAddress (SIZE (0|4))
            DESCRIPTION
                 "vRtrIfDHCPRelaySiaddrOvrAddr supports only InetAddressType
                  values 'unknown (0)' and 'ipv4 (1)'."

        VARIATION   vRtrIfDHCPRelaySiaddrOvrAddrType
            SYNTAX  InetAddressType {
                       unknown              (0),
                       ipv4                 (1)
                    -- ipv6                 (2)
                    -- ipv4z                (3)
                    -- ipv6z                (4)
                    -- dns                  (16)
                    }
            DESCRIPTION
                 "vRtrIfDHCPRelaySiaddrOvrAddrType supports only the
                  InetAddressType values 'unknown (0)' and 'ipv4 (1)'."

        VARIATION   vRtrIfIpReasBytesRx
            ACCESS  not-implemented
            DESCRIPTION
                 "vRtrIfIpReasBytesRx is not implemented on Nokia 7750 c12 in
                  release 14.0."

        VARIATION   vRtrIfIpReasBytesRxHigh32
            ACCESS  not-implemented
            DESCRIPTION
                 "vRtrIfIpReasBytesRxHigh32 is not implemented on Nokia 7750 c12
                  in release 14.0."

        VARIATION   vRtrIfIpReasBytesRxLow32
            ACCESS  not-implemented
            DESCRIPTION
                 "vRtrIfIpReasBytesRxLow32 is not implemented on Nokia 7750 c12
                  in release 14.0."

        VARIATION   vRtrIfIpReasBytesTx
            ACCESS  not-implemented
            DESCRIPTION
                 "vRtrIfIpReasBytesTx is not implemented on Nokia 7750 c12 in
                  release 14.0."

        VARIATION   vRtrIfIpReasBytesTxHigh32
            ACCESS  not-implemented
            DESCRIPTION
                 "vRtrIfIpReasBytesTxHigh32 is not implemented on Nokia 7750 c12
                  in release 14.0."

        VARIATION   vRtrIfIpReasBytesTxLow32
            ACCESS  not-implemented
            DESCRIPTION
                 "vRtrIfIpReasBytesTxLow32 is not implemented on Nokia 7750 c12
                  in release 14.0."

        VARIATION   vRtrIfIpReasContextValue
            ACCESS  not-implemented
            DESCRIPTION
                 "vRtrIfIpReasContextValue is not implemented on Nokia 7750 c12
                  in release 14.0."

        VARIATION   vRtrIfIpReasFragBytesRcvd
            ACCESS  not-implemented
            DESCRIPTION
                 "vRtrIfIpReasFragBytesRcvd is not implemented on Nokia 7750 c12
                  in release 14.0."

        VARIATION   vRtrIfIpReasFragBytesRcvdHigh32
            ACCESS  not-implemented
            DESCRIPTION
                 "vRtrIfIpReasFragBytesRcvdHigh32 is not implemented on Nokia
                  7750 c12 in release 14.0."

        VARIATION   vRtrIfIpReasFragBytesRcvdLow32
            ACCESS  not-implemented
            DESCRIPTION
                 "vRtrIfIpReasFragBytesRcvdLow32 is not implemented on Nokia
                  7750 c12 in release 14.0."

        VARIATION   vRtrIfIpReasFragBytesReas
            ACCESS  not-implemented
            DESCRIPTION
                 "vRtrIfIpReasFragBytesReas is not implemented on Nokia 7750 c12
                  in release 14.0."

        VARIATION   vRtrIfIpReasFragBytesReasHigh32
            ACCESS  not-implemented
            DESCRIPTION
                 "vRtrIfIpReasFragBytesReasHigh32 is not implemented on Nokia
                  7750 c12 in release 14.0."

        VARIATION   vRtrIfIpReasFragBytesReasLow32
            ACCESS  not-implemented
            DESCRIPTION
                 "vRtrIfIpReasFragBytesReasLow32 is not implemented on Nokia
                  7750 c12 in release 14.0."

        VARIATION   vRtrIfIpReasFragDisc
            ACCESS  not-implemented
            DESCRIPTION
                 "vRtrIfIpReasFragDisc is not implemented on Nokia 7750 c12 in
                  release 14.0."

        VARIATION   vRtrIfIpReasFragDiscHigh32
            ACCESS  not-implemented
            DESCRIPTION
                 "vRtrIfIpReasFragDiscHigh32 is not implemented on Nokia 7750
                  c12 in release 14.0."

        VARIATION   vRtrIfIpReasFragDiscLow32
            ACCESS  not-implemented
            DESCRIPTION
                 "vRtrIfIpReasFragDiscLow32 is not implemented on Nokia 7750 c12
                  in release 14.0."

        VARIATION   vRtrIfIpReasFragPktsRcvd
            ACCESS  not-implemented
            DESCRIPTION
                 "vRtrIfIpReasFragPktsRcvd is not implemented on Nokia 7750 c12
                  in release 14.0."

        VARIATION   vRtrIfIpReasFragPktsRcvdHigh32
            ACCESS  not-implemented
            DESCRIPTION
                 "vRtrIfIpReasFragPktsRcvdHigh32 is not implemented on Nokia
                  7750 c12 in release 14.0."

        VARIATION   vRtrIfIpReasFragPktsRcvdLow32
            ACCESS  not-implemented
            DESCRIPTION
                 "vRtrIfIpReasFragPktsRcvdLow32 is not implemented on Nokia 7750
                  c12 in release 14.0."

        VARIATION   vRtrIfIpReasFragPktsReas
            ACCESS  not-implemented
            DESCRIPTION
                 "vRtrIfIpReasFragPktsReas is not implemented on Nokia 7750 c12
                  in release 14.0."

        VARIATION   vRtrIfIpReasFragPktsReasHigh32
            ACCESS  not-implemented
            DESCRIPTION
                 "vRtrIfIpReasFragPktsReasHigh32 is not implemented on Nokia
                  7750 c12 in release 14.0."

        VARIATION   vRtrIfIpReasFragPktsReasLow32
            ACCESS  not-implemented
            DESCRIPTION
                 "vRtrIfIpReasFragPktsReasLow32 is not implemented on Nokia 7750
                  c12 in release 14.0."

        VARIATION   vRtrIfIpReasFragReasErrors
            ACCESS  not-implemented
            DESCRIPTION
                 "vRtrIfIpReasFragReasErrors is not implemented on Nokia 7750
                  c12 in release 14.0."

        VARIATION   vRtrIfIpReasFragReasErrorsHigh32
            ACCESS  not-implemented
            DESCRIPTION
                 "vRtrIfIpReasFragReasErrorsHigh32 is not implemented on Nokia
                  7750 c12 in release 14.0."

        VARIATION   vRtrIfIpReasFragReasErrorsLow32
            ACCESS  not-implemented
            DESCRIPTION
                 "vRtrIfIpReasFragReasErrorsLow32 is not implemented on Nokia
                  7750 c12 in release 14.0."

        VARIATION   vRtrIfIpReasOutBufRes
            ACCESS  not-implemented
            DESCRIPTION
                 "vRtrIfIpReasOutBufRes is not implemented on Nokia 7750 c12 in
                  release 14.0."

        VARIATION   vRtrIfIpReasOutBufResHigh32
            ACCESS  not-implemented
            DESCRIPTION
                 "vRtrIfIpReasOutBufResHigh32 is not implemented on Nokia 7750
                  c12 in release 14.0."

        VARIATION   vRtrIfIpReasOutBufResLow32
            ACCESS  not-implemented
            DESCRIPTION
                 "vRtrIfIpReasOutBufResLow32 is not implemented on Nokia 7750
                  c12 in release 14.0."

        VARIATION   vRtrIfIpReasPktsRx
            ACCESS  not-implemented
            DESCRIPTION
                 "vRtrIfIpReasPktsRx is not implemented on Nokia 7750 c12 in
                  release 14.0."

        VARIATION   vRtrIfIpReasPktsRxHigh32
            ACCESS  not-implemented
            DESCRIPTION
                 "vRtrIfIpReasPktsRxHigh32 is not implemented on Nokia 7750 c12
                  in release 14.0."

        VARIATION   vRtrIfIpReasPktsRxLow32
            ACCESS  not-implemented
            DESCRIPTION
                 "vRtrIfIpReasPktsRxLow32 is not implemented on Nokia 7750 c12
                  in release 14.0."

        VARIATION   vRtrIfIpReasPktsTx
            ACCESS  not-implemented
            DESCRIPTION
                 "vRtrIfIpReasPktsTx is not implemented on Nokia 7750 c12 in
                  release 14.0."

        VARIATION   vRtrIfIpReasPktsTxHigh32
            ACCESS  not-implemented
            DESCRIPTION
                 "vRtrIfIpReasPktsTxHigh32 is not implemented on Nokia 7750 c12
                  in release 14.0."

        VARIATION   vRtrIfIpReasPktsTxLow32
            ACCESS  not-implemented
            DESCRIPTION
                 "vRtrIfIpReasPktsTxLow32 is not implemented on Nokia 7750 c12
                  in release 14.0."

        VARIATION   vRtrIfIpReasPortID
            ACCESS  not-implemented
            DESCRIPTION
                 "vRtrIfIpReasPortID is not implemented on Nokia 7750 c12 in
                  release 14.0."

        VARIATION   vRtrIfIpReasV6BytesRx
            ACCESS  not-implemented
            DESCRIPTION
                 "vRtrIfIpReasV6BytesRx is not implemented on Nokia 7750 c12 in
                  release 14.0."

        VARIATION   vRtrIfIpReasV6BytesRxHigh32
            ACCESS  not-implemented
            DESCRIPTION
                 "vRtrIfIpReasV6BytesRxHigh32 is not implemented on Nokia 7750
                  c12 in release 14.0."

        VARIATION   vRtrIfIpReasV6BytesRxLow32
            ACCESS  not-implemented
            DESCRIPTION
                 "vRtrIfIpReasV6BytesRxLow32 is not implemented on Nokia 7750
                  c12 in release 14.0."

        VARIATION   vRtrIfIpReasV6BytesTx
            ACCESS  not-implemented
            DESCRIPTION
                 "vRtrIfIpReasV6BytesTx is not implemented on Nokia 7750 c12 in
                  release 14.0."

        VARIATION   vRtrIfIpReasV6BytesTxHigh32
            ACCESS  not-implemented
            DESCRIPTION
                 "vRtrIfIpReasV6BytesTxHigh32 is not implemented on Nokia 7750
                  c12 in release 14.0."

        VARIATION   vRtrIfIpReasV6BytesTxLow32
            ACCESS  not-implemented
            DESCRIPTION
                 "vRtrIfIpReasV6BytesTxLow32 is not implemented on Nokia 7750
                  c12 in release 14.0."

        VARIATION   vRtrIfIpReasV6FragBytesRcvd
            ACCESS  not-implemented
            DESCRIPTION
                 "vRtrIfIpReasV6FragBytesRcvd is not implemented on Nokia 7750
                  c12 in release 14.0."

        VARIATION   vRtrIfIpReasV6FragBytesRcvdH32
            ACCESS  not-implemented
            DESCRIPTION
                 "vRtrIfIpReasV6FragBytesRcvdH32 is not implemented on Nokia
                  7750 c12 in release 14.0."

        VARIATION   vRtrIfIpReasV6FragBytesRcvdL32
            ACCESS  not-implemented
            DESCRIPTION
                 "vRtrIfIpReasV6FragBytesRcvdL32 is not implemented on Nokia
                  7750 c12 in release 14.0."

        VARIATION   vRtrIfIpReasV6FragBytesReas
            ACCESS  not-implemented
            DESCRIPTION
                 "vRtrIfIpReasV6FragBytesReas is not implemented on Nokia 7750
                  c12 in release 14.0."

        VARIATION   vRtrIfIpReasV6FragBytesReasH32
            ACCESS  not-implemented
            DESCRIPTION
                 "vRtrIfIpReasV6FragBytesReasH32 is not implemented on Nokia
                  7750 c12 in release 14.0."

        VARIATION   vRtrIfIpReasV6FragBytesReasL32
            ACCESS  not-implemented
            DESCRIPTION
                 "vRtrIfIpReasV6FragBytesReasL32 is not implemented on Nokia
                  7750 c12 in release 14.0."

        VARIATION   vRtrIfIpReasV6FragDisc
            ACCESS  not-implemented
            DESCRIPTION
                 "vRtrIfIpReasV6FragDisc is not implemented on Nokia 7750 c12 in
                  release 14.0."

        VARIATION   vRtrIfIpReasV6FragDiscHigh32
            ACCESS  not-implemented
            DESCRIPTION
                 "vRtrIfIpReasV6FragDiscHigh32 is not implemented on Nokia 7750
                  c12 in release 14.0."

        VARIATION   vRtrIfIpReasV6FragDiscLow32
            ACCESS  not-implemented
            DESCRIPTION
                 "vRtrIfIpReasV6FragDiscLow32 is not implemented on Nokia 7750
                  c12 in release 14.0."

        VARIATION   vRtrIfIpReasV6FragPktsRcvd
            ACCESS  not-implemented
            DESCRIPTION
                 "vRtrIfIpReasV6FragPktsRcvd is not implemented on Nokia 7750
                  c12 in release 14.0."

        VARIATION   vRtrIfIpReasV6FragPktsRcvdHigh32
            ACCESS  not-implemented
            DESCRIPTION
                 "vRtrIfIpReasV6FragPktsRcvdHigh32 is not implemented on Nokia
                  7750 c12 in release 14.0."

        VARIATION   vRtrIfIpReasV6FragPktsRcvdLow32
            ACCESS  not-implemented
            DESCRIPTION
                 "vRtrIfIpReasV6FragPktsRcvdLow32 is not implemented on Nokia
                  7750 c12 in release 14.0."

        VARIATION   vRtrIfIpReasV6FragPktsReas
            ACCESS  not-implemented
            DESCRIPTION
                 "vRtrIfIpReasV6FragPktsReas is not implemented on Nokia 7750
                  c12 in release 14.0."

        VARIATION   vRtrIfIpReasV6FragPktsReasHigh32
            ACCESS  not-implemented
            DESCRIPTION
                 "vRtrIfIpReasV6FragPktsReasHigh32 is not implemented on Nokia
                  7750 c12 in release 14.0."

        VARIATION   vRtrIfIpReasV6FragPktsReasLow32
            ACCESS  not-implemented
            DESCRIPTION
                 "vRtrIfIpReasV6FragPktsReasLow32 is not implemented on Nokia
                  7750 c12 in release 14.0."

        VARIATION   vRtrIfIpReasV6FragReasErrors
            ACCESS  not-implemented
            DESCRIPTION
                 "vRtrIfIpReasV6FragReasErrors is not implemented on Nokia 7750
                  c12 in release 14.0."

        VARIATION   vRtrIfIpReasV6FragReasErrorsH32
            ACCESS  not-implemented
            DESCRIPTION
                 "vRtrIfIpReasV6FragReasErrorsH32 is not implemented on Nokia
                  7750 c12 in release 14.0."

        VARIATION   vRtrIfIpReasV6FragReasErrorsL32
            ACCESS  not-implemented
            DESCRIPTION
                 "vRtrIfIpReasV6FragReasErrorsL32 is not implemented on Nokia
                  7750 c12 in release 14.0."

        VARIATION   vRtrIfIpReasV6OutBufRes
            ACCESS  not-implemented
            DESCRIPTION
                 "vRtrIfIpReasV6OutBufRes is not implemented on Nokia 7750 c12
                  in release 14.0."

        VARIATION   vRtrIfIpReasV6OutBufResHigh32
            ACCESS  not-implemented
            DESCRIPTION
                 "vRtrIfIpReasV6OutBufResHigh32 is not implemented on Nokia 7750
                  c12 in release 14.0."

        VARIATION   vRtrIfIpReasV6OutBufResLow32
            ACCESS  not-implemented
            DESCRIPTION
                 "vRtrIfIpReasV6OutBufResLow32 is not implemented on Nokia 7750
                  c12 in release 14.0."

        VARIATION   vRtrIfIpReasV6PktsRx
            ACCESS  not-implemented
            DESCRIPTION
                 "vRtrIfIpReasV6PktsRx is not implemented on Nokia 7750 c12 in
                  release 14.0."

        VARIATION   vRtrIfIpReasV6PktsRxHigh32
            ACCESS  not-implemented
            DESCRIPTION
                 "vRtrIfIpReasV6PktsRxHigh32 is not implemented on Nokia 7750
                  c12 in release 14.0."

        VARIATION   vRtrIfIpReasV6PktsRxLow32
            ACCESS  not-implemented
            DESCRIPTION
                 "vRtrIfIpReasV6PktsRxLow32 is not implemented on Nokia 7750 c12
                  in release 14.0."

        VARIATION   vRtrIfIpReasV6PktsTx
            ACCESS  not-implemented
            DESCRIPTION
                 "vRtrIfIpReasV6PktsTx is not implemented on Nokia 7750 c12 in
                  release 14.0."

        VARIATION   vRtrIfIpReasV6PktsTxHigh32
            ACCESS  not-implemented
            DESCRIPTION
                 "vRtrIfIpReasV6PktsTxHigh32 is not implemented on Nokia 7750
                  c12 in release 14.0."

        VARIATION   vRtrIfIpReasV6PktsTxLow32
            ACCESS  not-implemented
            DESCRIPTION
                 "vRtrIfIpReasV6PktsTxLow32 is not implemented on Nokia 7750 c12
                  in release 14.0."

        VARIATION   vRtrIfIpcpPeerAddr
            SYNTAX  InetAddress (SIZE (0|4))
            DESCRIPTION
                 "vRtrIfIpcpPeerAddr supports only InetAddressType values
                  'unknown (0)' and 'ipv4 (1)'."

        VARIATION   vRtrIfIpcpPeerAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPeerAddrType supports only the InetAddressType
                  values 'unknown (0)' and 'ipv4 (1)'."

        VARIATION   vRtrIfIpcpPriDnsAddr
            SYNTAX  InetAddress (SIZE (0|4))
            DESCRIPTION
                 "vRtrIfIpcpPriDnsAddr supports only InetAddressType values
                  'unknown (0)' and 'ipv4 (1)'."

        VARIATION   vRtrIfIpcpPriDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPriDnsAddrType supports only the InetAddressType
                  values 'unknown (0)' and 'ipv4 (1)'."

        VARIATION   vRtrIfIpcpSecDnsAddr
            SYNTAX  InetAddress (SIZE (0|4))
            DESCRIPTION
                 "vRtrIfIpcpSecDnsAddr supports only InetAddressType values
                  'unknown (0)' and 'ipv4 (1)'."

        VARIATION   vRtrIfIpcpSecDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpSecDnsAddrType supports only the InetAddressType
                  values 'unknown (0)' and 'ipv4 (1)'."

        VARIATION   vRtrIfIpv6TrackMobile
            ACCESS  not-implemented
            DESCRIPTION
                 "vRtrIfIpv6TrackMobile is not implemented on Nokia 7750 c12 in
                  release 14.0."

        VARIATION   vRtrIfTrackMobile
            ACCESS  not-implemented
            DESCRIPTION
                 "vRtrIfTrackMobile is not implemented on Nokia 7750 c12 in
                  release 14.0."

        VARIATION   vRtrIfType
            SYNTAX  INTEGER {
                       network(1),
                       service(2),
                       serviceIes(3),
                    -- serviceRtdVpls(4)
                       serviceVprn(5),
                       serviceIesSubscriber(6),
                       serviceIesGroup(7),
                       serviceVprnSubscriber(8),
                       serviceVprnGroup(9),
                       serviceIesRedundant(10),
                       serviceVprnRedundant(11),
                       serviceVpls(12),
                       serviceIesCem(13),
                       serviceVprnCem(14),
                    -- serviceVprnIPsec(15)
                       serviceVprnIPMirror(16),
                       serviceVideo(17),
                       serviceVplsVideo(18),
                    -- multiHomingPrimary(19)
                    -- multiHomingSecondary(20)
                       serviceIesTunnel(21),
                    -- serviceIpReas(22)
                    -- networkIpReas(23)
                       networkVprn(24),
                       tmsService(25),
                       serviceIesAarp(26),
                       serviceVprnAarp(27),
                       serviceIesAa(28),
                       serviceVprnAa(29),
                       unnumMplsTp(30)
                    }
            DESCRIPTION
                 "The values - 'serviceRtdVpls (4)' (obsoleted) -
                  'serviceVprnIPsec (15)' (IPsec Tunneling) -
                  'multiHomingPrimary (19)' (obsoleted) - 'multiHomingSecondary
                  (20)' (obsoleted) - 'serviceIpReas (22)' (MG specific) -
                  'networkIpReas (23)' (MG specific) are not supported on Nokia
                  7750 c12."

        VARIATION   vRtrIgnoreIcmpRedirect
            DESCRIPTION
                 "The default value of vRtrIgnoreIcmpRedirect is changed to
                  'true' from 'false' in release 4.0-R13 and 5.0-R3."

        VARIATION   vRtrInetSRIndirectEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectSrTeLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteIndexEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRoutePfxEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrIpCidrRoutePreference
            ACCESS  read-only
            DESCRIPTION
                 "vRtrIpCidrRoutePreference is implemented as read-only on Nokia
                  7750 c12 in release 14.0."

        VARIATION   vRtrIpPoolIsRemote
            ACCESS  not-implemented
            DESCRIPTION
                 "vRtrIpPoolIsRemote is not implemented on Nokia 7750 c12 in
                  release 14.0."

        VARIATION   vRtrLdpShortcut
            SYNTAX  TmnxEnabledDisabled
            DESCRIPTION
                 "vRtrLdpShortcut is only supported in the default or base
                  routing instance."

        VARIATION   vRtrLdpTunIfSenderAddr
            SYNTAX  InetAddress (SIZE (4))
            DESCRIPTION
                 "vRtrRsvpTunIfSenderAddr supports only InetAddressType 'ipv4'."

        VARIATION   vRtrLdpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrLdpTunIfSenderAddrType supports only the InetAddressType
                  value 'ipv4 (1)'."

        VARIATION   vRtrMobileHostActiveRoutes
            ACCESS  not-implemented
            DESCRIPTION
                 "vRtrMobileHostActiveRoutes is not implemented on Nokia 7750
                  c12 in release 14.0."

        VARIATION   vRtrMobileHostRoutes
            ACCESS  not-implemented
            DESCRIPTION
                 "vRtrMobileHostRoutes is not implemented on Nokia 7750 c12 in
                  release 14.0."

        VARIATION   vRtrMvpnIpmsiType
            SYNTAX  INTEGER {
                       none                 (0),
                    -- rsvp                 (1)
                       pim                  (2)
                    }
            DESCRIPTION
                 "The value 'rsvp(1)' is not supported in the release 8.0R1."

        VARIATION   vRtrMvpnSpmsiType
            SYNTAX  INTEGER {
                       none                 (0),
                    -- rsvp                 (1)
                       pim                  (2)
                    }
            DESCRIPTION
                 "The value 'rsvp(1)' is not supported in the release 8.0R1."

        VARIATION   vRtrNextVRtrID
            ACCESS  read-only
            DESCRIPTION
                 "vRtrNextVRtrID is implemented as read-only on Nokia 7750 c12
                  in release 14.0."

        VARIATION   vRtrRouteThresholdSoakTime
            ACCESS  read-only
            DESCRIPTION
                 "vRtrRouteThresholdSoakTime is implemented as read-only on
                  Nokia 7750 c12 in release 14.0."

        VARIATION   vRtrRsvpTunIfSenderAddr
            SYNTAX  InetAddress (SIZE (4))
            DESCRIPTION
                 "vRtrRsvpTunIfSenderAddr supports only InetAddressType 'ipv4'."

        VARIATION   vRtrRsvpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSenderAddrType supports only the InetAddressType
                  value 'ipv4 (1)'."

        VARIATION   vRtrRsvpTunIfSrcAddr
            SYNTAX  InetAddress (SIZE (4))
            DESCRIPTION
                 "vRtrRsvpTunIfSenderAddr supports only InetAddressType 'ipv4'."

        VARIATION   vRtrRsvpTunIfSrcAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSrcAddrType supports only the InetAddressType
                  value 'ipv4 (1)'."

        VARIATION   vRtrRsvpTunIfStandbyAddr
            SYNTAX  InetAddress (SIZE (4))
            DESCRIPTION
                 "vRtrRsvpTunIfSenderAddr supports only InetAddressType 'ipv4'."

        VARIATION   vRtrRsvpTunIfStandbyAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfStandbyAddrType supports only the InetAddressType
                  value 'ipv4 (1)'."

        VARIATION   vRtrV6MobileHostActiveRoutes
            ACCESS  not-implemented
            DESCRIPTION
                 "vRtrV6MobileHostActiveRoutes is not implemented on Nokia 7750
                  c12 in release 14.0."

        VARIATION   vRtrV6MobileHostRoutes
            ACCESS  not-implemented
            DESCRIPTION
                 "vRtrV6MobileHostRoutes is not implemented on Nokia 7750 c12 in
                  release 14.0."

    ::= { tmnx7750c12AgentV14v0  45 }

--
-- 7750c4 VRTR CAPABILITIES
--
tmnx7750c4VrtrV14v0               AGENT-CAPABILITIES
    PRODUCT-RELEASE "Nokia SROS"
    STATUS          current
    DESCRIPTION
         "Implementation of Virtual Router capabilities for Nokia 7750 c4
          systems release 14.0."

    SUPPORTS        TIMETRA-VRTR-MIB
        INCLUDES {
           tmnxDscpAppV6v0Group,
           tmnxMGVRtrIfV4v0Group,
           tmnxVRtrAggrRouteV12v0Group,
           tmnxVRtrBfdV11v0Group,
           tmnxVRtrBgpAutoRDGroup,
           tmnxVRtrBgpEvpn12v0Group,
           tmnxVRtrBgpEvpnIpRoutes12v0Group,
           tmnxVRtrBgpLblIpRoutes14v0Group,
           tmnxVRtrCidrNextHopOwnInstGroup,
           tmnxVRtrConfExtV12v0Group,
           tmnxVRtrConfFlowspecV14v0Group,
           tmnxVRtrCreation12v0Group,
           tmnxVRtrEntropyLabelGroup,
           tmnxVRtrExportBgpVpnV11v0Group,
           tmnxVRtrFibStatsV14v0Group,
           tmnxVRtrFibStatsV8v0Group,
           tmnxVRtrFlowSpecV11v0Group,
           tmnxVRtrFpeV14v0Group,
           tmnxVRtrGenerateICMPV12v0Group,
           tmnxVRtrGlobalV10v0Group,
           tmnxVRtrGlobalV6v0Group,
           tmnxVRtrGrtLocalMgmtV10v0Group,
           tmnxVRtrHoldDownTimeV12v0Group,
           tmnxVRtrIPsecStatGroup,
           tmnxVRtrIPv6IPsecStatGroup,
           tmnxVRtrIPv6IfV4v0Group,
           tmnxVRtrIPv6IpV5v0Group,
-- EXCLUDE tmnxVRtrIPv6MgtIfV7v0Group
           tmnxVRtrIPv6V4v0Group,
           tmnxVRtrIcmpTunnelingGroup,
           tmnxVRtrIcmpV4ParamV14v0Group,
           tmnxVRtrIcmpV4StatsV14v0Group,
           tmnxVRtrIfArpNbrLimitGroup,
           tmnxVRtrIfArpNbrNotifGroup,
-- EXCLUDE tmnxVRtrIfCpmProtectGroup
           tmnxVRtrIfDHCP6V10v0Group,
           tmnxVRtrIfDHCP6V11v0Group,
           tmnxVRtrIfDHCP6V12v0Group,
           tmnxVRtrIfDHCP6V9v0Group,
           tmnxVRtrIfDHCPRelayV11v0Group,
           tmnxVRtrIfDHCPRelayV13v0Group,
           tmnxVRtrIfDHCPRelayV14v0Group,
           tmnxVRtrIfDHCPRelayV6v1Group,
           tmnxVRtrIfDHCPRelayV9v0Group,
           tmnxVRtrIfDhcpServerGroup,
           tmnxVRtrIfExtIfArpRetryTimerGrp,
           tmnxVRtrIfExtV12v0Group,
           tmnxVRtrIfExtV13v0Group,
           tmnxVRtrIfExtV14v0Group,
           tmnxVRtrIfIpReasV9v0Group,
           tmnxVRtrIfIpcpV6v0Group,
           tmnxVRtrIfLagPerLinkHashGroup,
           tmnxVRtrIfMacStatsV11v0Group,
           tmnxVRtrIfSendV12v0Group,
           tmnxVRtrIfStatsV11v0Group,
           tmnxVRtrIfStatsV9v0Group,
           tmnxVRtrIfSubscrAuthV3v0Group,
           tmnxVRtrIfV10v0Group,
           tmnxVRtrIfV14v0Group,
           tmnxVRtrInetAllCidrRouteV7v0Group,
           tmnxVRtrInetSRIndirectV13v0Group,
           tmnxVRtrInetSRIndirectV14v0Group,
           tmnxVRtrInetStaticRouteV7v0Group,
           tmnxVRtrIpPoolGroup,
           tmnxVRtrIpV13v0Group,
           tmnxVRtrIpV13v0ObsoletedGroup,
           tmnxVRtrIpv6RtrAdvertV11v0Group,
           tmnxVRtrLagEgrLoadBal12v0Group,
           tmnxVRtrLagHashLoadBal12v0Group,
           tmnxVRtrLdpIpv613v0Group,
           tmnxVRtrLoadBalEnhV13v0Group,
           tmnxVRtrLoopbackNotifGroup,
           tmnxVRtrLspBfdGroup,
           tmnxVRtrMSPwV9v0Group,
           tmnxVRtrMcastSpmsiEnhV13v0Group,
           tmnxVRtrMcastV11v0Group,
           tmnxVRtrMvpnPmsiV8v0Group,
           tmnxVRtrMvpnSrcRedV9v0R4Group,
           tmnxVRtrNatRedGroup,
           tmnxVRtrNetDomainGroup,
           tmnxVRtrNotificationNHRvplsArpGr,
           tmnxVRtrNotificationV10v0Group,
           tmnxVRtrNotificationV14v0Group,
           tmnxVRtrNotifyObjsNHRvplsArpGrp,
           tmnxVRtrPlcyAcctTempl12v0Group,
           tmnxVRtrPolicyGroup,
           tmnxVRtrQPPBV9v0R4Group,
           tmnxVRtrQosQGrplV10v0Group,
           tmnxVRtrRAV12v0Group,
           tmnxVRtrSrTeV14v0Group,
           tmnxVRtrStatV10v0Group,
           tmnxVRtrStatV11v0Group,
           tmnxVRtrStatV9v0Group,
           tmnxVRtrStaticRoutePrefixGroup,
           tmnxVRtrStaticRteCPEChkV6v0Group,
           tmnxVRtrStickyHashEcmp12v0Group,
           tmnxVRtrTunIntV8v0Group,
           tmnxVRtrTunnelExtTableV13v0Group,
           tmnxVRtrTunnelTableCBFV13v0Group,
           tmnxVRtrTunnelTableLSCV14v0Group,
           tmnxVRtrTunnelTableNhTV14v0Group,
           tmnxVRtrTunnelTableStatGroup,
           tmnxVRtrUniqueIfIndexGroup,
           tmnxVRtrV12v0Group,
           tmnxVRtrV13v0GenObsoletedGroup,
           tmnxVRtrV13v0IfStatsGroup,
           tmnxVRtrV14v0Group,
           tmnxVRtrV14v0NotifyObjsGroup,
           tmnxVRtrV6TunnelTableStatGroup,
           tmnxVRtrV6v1Group,
           tmnxVRtrV9v0Group,
           tmnxVRtrVccvBfd12v0Group,
           tmnxVRtrVirtualCPE12v0Group,
           tmnxVRtruRPFV10v0Group,
           tmnxVRtruRPFV7v0Group,
           tmnxVrtrDcpNotifyObjsV11v0Group,
           tmnxVrtrIfDCpuProtV11v0Group,
           tmnxVrtrIfDHCP6ProxyDuidGroup,
           tmnxVrtrIfDcpNotifyV11v0Group,
           tmnxvRtrIfAttributeGroup
        }

        VARIATION   vRtrFibStatMobileHostRoutes
            ACCESS  not-implemented
            DESCRIPTION
                 "vRtrFibStatMobileHostRoutes is not implemented on Nokia 7750
                  c4 in release 14.0."

        VARIATION   vRtrFibStatV6MobileHostRoutes
            ACCESS  not-implemented
            DESCRIPTION
                 "vRtrFibStatV6MobileHostRoutes is not implemented on Nokia 7750
                  c4 in release 14.0."

        VARIATION   vRtrIPv6RouteThresholdSoakTime
            ACCESS  read-only
            DESCRIPTION
                 "vRtrIPv6RouteThresholdSoakTime is implemented as read-only on
                  Nokia 7750 c4 in release 14.0."

        VARIATION   vRtrIfAlias
            ACCESS  read-only
            DESCRIPTION
                 "vRtrIfAlias is implemented as read-only on Nokia 7750 c4 in
                  release 14.0."

        VARIATION   vRtrIfBfdType
            SYNTAX  INTEGER {
                    -- cpmNp(1)
                       auto(2)
                    }
            DESCRIPTION
                 "cpmNp(1) is not supported on Nokia 7750 c4."

        VARIATION   vRtrIfDHCP6ProxyDuidEnIdDataType
            SYNTAX  INTEGER {
                    -- ipv4(1)
                       ascii(2),
                       hex(3)
                    -- ipv6(4)
                    -- domain(5)
                    }
            DESCRIPTION
                 "The only allowed values for this object are 'ascii(2)' and
                  'hex(3)'."

        VARIATION   vRtrIfDHCPLeasePopulate
            DESCRIPTION
                 "The default value of vRtrIfDHCPLeasePopulate is '1', not '0',
                  when the interface running DHCP has vRtrIfType
                  'serviceIesGroup'."

        VARIATION   vRtrIfDHCPRelaySiaddrOvrAddr
            SYNTAX  InetAddress (SIZE (0|4))
            DESCRIPTION
                 "vRtrIfDHCPRelaySiaddrOvrAddr supports only InetAddressType
                  values 'unknown (0)' and 'ipv4 (1)'."

        VARIATION   vRtrIfDHCPRelaySiaddrOvrAddrType
            SYNTAX  InetAddressType {
                       unknown              (0),
                       ipv4                 (1)
                    -- ipv6                 (2)
                    -- ipv4z                (3)
                    -- ipv6z                (4)
                    -- dns                  (16)
                    }
            DESCRIPTION
                 "vRtrIfDHCPRelaySiaddrOvrAddrType supports only the
                  InetAddressType values 'unknown (0)' and 'ipv4 (1)'."

        VARIATION   vRtrIfIpReasBytesRx
            ACCESS  not-implemented
            DESCRIPTION
                 "vRtrIfIpReasBytesRx is not implemented on Nokia 7750 c4 in
                  release 14.0."

        VARIATION   vRtrIfIpReasBytesRxHigh32
            ACCESS  not-implemented
            DESCRIPTION
                 "vRtrIfIpReasBytesRxHigh32 is not implemented on Nokia 7750 c4
                  in release 14.0."

        VARIATION   vRtrIfIpReasBytesRxLow32
            ACCESS  not-implemented
            DESCRIPTION
                 "vRtrIfIpReasBytesRxLow32 is not implemented on Nokia 7750 c4
                  in release 14.0."

        VARIATION   vRtrIfIpReasBytesTx
            ACCESS  not-implemented
            DESCRIPTION
                 "vRtrIfIpReasBytesTx is not implemented on Nokia 7750 c4 in
                  release 14.0."

        VARIATION   vRtrIfIpReasBytesTxHigh32
            ACCESS  not-implemented
            DESCRIPTION
                 "vRtrIfIpReasBytesTxHigh32 is not implemented on Nokia 7750 c4
                  in release 14.0."

        VARIATION   vRtrIfIpReasBytesTxLow32
            ACCESS  not-implemented
            DESCRIPTION
                 "vRtrIfIpReasBytesTxLow32 is not implemented on Nokia 7750 c4
                  in release 14.0."

        VARIATION   vRtrIfIpReasContextValue
            ACCESS  not-implemented
            DESCRIPTION
                 "vRtrIfIpReasContextValue is not implemented on Nokia 7750 c4
                  in release 14.0."

        VARIATION   vRtrIfIpReasFragBytesRcvd
            ACCESS  not-implemented
            DESCRIPTION
                 "vRtrIfIpReasFragBytesRcvd is not implemented on Nokia 7750 c4
                  in release 14.0."

        VARIATION   vRtrIfIpReasFragBytesRcvdHigh32
            ACCESS  not-implemented
            DESCRIPTION
                 "vRtrIfIpReasFragBytesRcvdHigh32 is not implemented on Nokia
                  7750 c4 in release 14.0."

        VARIATION   vRtrIfIpReasFragBytesRcvdLow32
            ACCESS  not-implemented
            DESCRIPTION
                 "vRtrIfIpReasFragBytesRcvdLow32 is not implemented on Nokia
                  7750 c4 in release 14.0."

        VARIATION   vRtrIfIpReasFragBytesReas
            ACCESS  not-implemented
            DESCRIPTION
                 "vRtrIfIpReasFragBytesReas is not implemented on Nokia 7750 c4
                  in release 14.0."

        VARIATION   vRtrIfIpReasFragBytesReasHigh32
            ACCESS  not-implemented
            DESCRIPTION
                 "vRtrIfIpReasFragBytesReasHigh32 is not implemented on Nokia
                  7750 c4 in release 14.0."

        VARIATION   vRtrIfIpReasFragBytesReasLow32
            ACCESS  not-implemented
            DESCRIPTION
                 "vRtrIfIpReasFragBytesReasLow32 is not implemented on Nokia
                  7750 c4 in release 14.0."

        VARIATION   vRtrIfIpReasFragDisc
            ACCESS  not-implemented
            DESCRIPTION
                 "vRtrIfIpReasFragDisc is not implemented on Nokia 7750 c4 in
                  release 14.0."

        VARIATION   vRtrIfIpReasFragDiscHigh32
            ACCESS  not-implemented
            DESCRIPTION
                 "vRtrIfIpReasFragDiscHigh32 is not implemented on Nokia 7750 c4
                  in release 14.0."

        VARIATION   vRtrIfIpReasFragDiscLow32
            ACCESS  not-implemented
            DESCRIPTION
                 "vRtrIfIpReasFragDiscLow32 is not implemented on Nokia 7750 c4
                  in release 14.0."

        VARIATION   vRtrIfIpReasFragPktsRcvd
            ACCESS  not-implemented
            DESCRIPTION
                 "vRtrIfIpReasFragPktsRcvd is not implemented on Nokia 7750 c4
                  in release 14.0."

        VARIATION   vRtrIfIpReasFragPktsRcvdHigh32
            ACCESS  not-implemented
            DESCRIPTION
                 "vRtrIfIpReasFragPktsRcvdHigh32 is not implemented on Nokia
                  7750 c4 in release 14.0."

        VARIATION   vRtrIfIpReasFragPktsRcvdLow32
            ACCESS  not-implemented
            DESCRIPTION
                 "vRtrIfIpReasFragPktsRcvdLow32 is not implemented on Nokia 7750
                  c4 in release 14.0."

        VARIATION   vRtrIfIpReasFragPktsReas
            ACCESS  not-implemented
            DESCRIPTION
                 "vRtrIfIpReasFragPktsReas is not implemented on Nokia 7750 c4
                  in release 14.0."

        VARIATION   vRtrIfIpReasFragPktsReasHigh32
            ACCESS  not-implemented
            DESCRIPTION
                 "vRtrIfIpReasFragPktsReasHigh32 is not implemented on Nokia
                  7750 c4 in release 14.0."

        VARIATION   vRtrIfIpReasFragPktsReasLow32
            ACCESS  not-implemented
            DESCRIPTION
                 "vRtrIfIpReasFragPktsReasLow32 is not implemented on Nokia 7750
                  c4 in release 14.0."

        VARIATION   vRtrIfIpReasFragReasErrors
            ACCESS  not-implemented
            DESCRIPTION
                 "vRtrIfIpReasFragReasErrors is not implemented on Nokia 7750 c4
                  in release 14.0."

        VARIATION   vRtrIfIpReasFragReasErrorsHigh32
            ACCESS  not-implemented
            DESCRIPTION
                 "vRtrIfIpReasFragReasErrorsHigh32 is not implemented on Nokia
                  7750 c4 in release 14.0."

        VARIATION   vRtrIfIpReasFragReasErrorsLow32
            ACCESS  not-implemented
            DESCRIPTION
                 "vRtrIfIpReasFragReasErrorsLow32 is not implemented on Nokia
                  7750 c4 in release 14.0."

        VARIATION   vRtrIfIpReasOutBufRes
            ACCESS  not-implemented
            DESCRIPTION
                 "vRtrIfIpReasOutBufRes is not implemented on Nokia 7750 c4 in
                  release 14.0."

        VARIATION   vRtrIfIpReasOutBufResHigh32
            ACCESS  not-implemented
            DESCRIPTION
                 "vRtrIfIpReasOutBufResHigh32 is not implemented on Nokia 7750
                  c4 in release 14.0."

        VARIATION   vRtrIfIpReasOutBufResLow32
            ACCESS  not-implemented
            DESCRIPTION
                 "vRtrIfIpReasOutBufResLow32 is not implemented on Nokia 7750 c4
                  in release 14.0."

        VARIATION   vRtrIfIpReasPktsRx
            ACCESS  not-implemented
            DESCRIPTION
                 "vRtrIfIpReasPktsRx is not implemented on Nokia 7750 c4 in
                  release 14.0."

        VARIATION   vRtrIfIpReasPktsRxHigh32
            ACCESS  not-implemented
            DESCRIPTION
                 "vRtrIfIpReasPktsRxHigh32 is not implemented on Nokia 7750 c4
                  in release 14.0."

        VARIATION   vRtrIfIpReasPktsRxLow32
            ACCESS  not-implemented
            DESCRIPTION
                 "vRtrIfIpReasPktsRxLow32 is not implemented on Nokia 7750 c4 in
                  release 14.0."

        VARIATION   vRtrIfIpReasPktsTx
            ACCESS  not-implemented
            DESCRIPTION
                 "vRtrIfIpReasPktsTx is not implemented on Nokia 7750 c4 in
                  release 14.0."

        VARIATION   vRtrIfIpReasPktsTxHigh32
            ACCESS  not-implemented
            DESCRIPTION
                 "vRtrIfIpReasPktsTxHigh32 is not implemented on Nokia 7750 c4
                  in release 14.0."

        VARIATION   vRtrIfIpReasPktsTxLow32
            ACCESS  not-implemented
            DESCRIPTION
                 "vRtrIfIpReasPktsTxLow32 is not implemented on Nokia 7750 c4 in
                  release 14.0."

        VARIATION   vRtrIfIpReasPortID
            ACCESS  not-implemented
            DESCRIPTION
                 "vRtrIfIpReasPortID is not implemented on Nokia 7750 c4 in
                  release 14.0."

        VARIATION   vRtrIfIpReasV6BytesRx
            ACCESS  not-implemented
            DESCRIPTION
                 "vRtrIfIpReasV6BytesRx is not implemented on Nokia 7750 c4 in
                  release 14.0."

        VARIATION   vRtrIfIpReasV6BytesRxHigh32
            ACCESS  not-implemented
            DESCRIPTION
                 "vRtrIfIpReasV6BytesRxHigh32 is not implemented on Nokia 7750
                  c4 in release 14.0."

        VARIATION   vRtrIfIpReasV6BytesRxLow32
            ACCESS  not-implemented
            DESCRIPTION
                 "vRtrIfIpReasV6BytesRxLow32 is not implemented on Nokia 7750 c4
                  in release 14.0."

        VARIATION   vRtrIfIpReasV6BytesTx
            ACCESS  not-implemented
            DESCRIPTION
                 "vRtrIfIpReasV6BytesTx is not implemented on Nokia 7750 c4 in
                  release 14.0."

        VARIATION   vRtrIfIpReasV6BytesTxHigh32
            ACCESS  not-implemented
            DESCRIPTION
                 "vRtrIfIpReasV6BytesTxHigh32 is not implemented on Nokia 7750
                  c4 in release 14.0."

        VARIATION   vRtrIfIpReasV6BytesTxLow32
            ACCESS  not-implemented
            DESCRIPTION
                 "vRtrIfIpReasV6BytesTxLow32 is not implemented on Nokia 7750 c4
                  in release 14.0."

        VARIATION   vRtrIfIpReasV6FragBytesRcvd
            ACCESS  not-implemented
            DESCRIPTION
                 "vRtrIfIpReasV6FragBytesRcvd is not implemented on Nokia 7750
                  c4 in release 14.0."

        VARIATION   vRtrIfIpReasV6FragBytesRcvdH32
            ACCESS  not-implemented
            DESCRIPTION
                 "vRtrIfIpReasV6FragBytesRcvdH32 is not implemented on Nokia
                  7750 c4 in release 14.0."

        VARIATION   vRtrIfIpReasV6FragBytesRcvdL32
            ACCESS  not-implemented
            DESCRIPTION
                 "vRtrIfIpReasV6FragBytesRcvdL32 is not implemented on Nokia
                  7750 c4 in release 14.0."

        VARIATION   vRtrIfIpReasV6FragBytesReas
            ACCESS  not-implemented
            DESCRIPTION
                 "vRtrIfIpReasV6FragBytesReas is not implemented on Nokia 7750
                  c4 in release 14.0."

        VARIATION   vRtrIfIpReasV6FragBytesReasH32
            ACCESS  not-implemented
            DESCRIPTION
                 "vRtrIfIpReasV6FragBytesReasH32 is not implemented on Nokia
                  7750 c4 in release 14.0."

        VARIATION   vRtrIfIpReasV6FragBytesReasL32
            ACCESS  not-implemented
            DESCRIPTION
                 "vRtrIfIpReasV6FragBytesReasL32 is not implemented on Nokia
                  7750 c4 in release 14.0."

        VARIATION   vRtrIfIpReasV6FragDisc
            ACCESS  not-implemented
            DESCRIPTION
                 "vRtrIfIpReasV6FragDisc is not implemented on Nokia 7750 c4 in
                  release 14.0."

        VARIATION   vRtrIfIpReasV6FragDiscHigh32
            ACCESS  not-implemented
            DESCRIPTION
                 "vRtrIfIpReasV6FragDiscHigh32 is not implemented on Nokia 7750
                  c4 in release 14.0."

        VARIATION   vRtrIfIpReasV6FragDiscLow32
            ACCESS  not-implemented
            DESCRIPTION
                 "vRtrIfIpReasV6FragDiscLow32 is not implemented on Nokia 7750
                  c4 in release 14.0."

        VARIATION   vRtrIfIpReasV6FragPktsRcvd
            ACCESS  not-implemented
            DESCRIPTION
                 "vRtrIfIpReasV6FragPktsRcvd is not implemented on Nokia 7750 c4
                  in release 14.0."

        VARIATION   vRtrIfIpReasV6FragPktsRcvdHigh32
            ACCESS  not-implemented
            DESCRIPTION
                 "vRtrIfIpReasV6FragPktsRcvdHigh32 is not implemented on Nokia
                  7750 c4 in release 14.0."

        VARIATION   vRtrIfIpReasV6FragPktsRcvdLow32
            ACCESS  not-implemented
            DESCRIPTION
                 "vRtrIfIpReasV6FragPktsRcvdLow32 is not implemented on Nokia
                  7750 c4 in release 14.0."

        VARIATION   vRtrIfIpReasV6FragPktsReas
            ACCESS  not-implemented
            DESCRIPTION
                 "vRtrIfIpReasV6FragPktsReas is not implemented on Nokia 7750 c4
                  in release 14.0."

        VARIATION   vRtrIfIpReasV6FragPktsReasHigh32
            ACCESS  not-implemented
            DESCRIPTION
                 "vRtrIfIpReasV6FragPktsReasHigh32 is not implemented on Nokia
                  7750 c4 in release 14.0."

        VARIATION   vRtrIfIpReasV6FragPktsReasLow32
            ACCESS  not-implemented
            DESCRIPTION
                 "vRtrIfIpReasV6FragPktsReasLow32 is not implemented on Nokia
                  7750 c4 in release 14.0."

        VARIATION   vRtrIfIpReasV6FragReasErrors
            ACCESS  not-implemented
            DESCRIPTION
                 "vRtrIfIpReasV6FragReasErrors is not implemented on Nokia 7750
                  c4 in release 14.0."

        VARIATION   vRtrIfIpReasV6FragReasErrorsH32
            ACCESS  not-implemented
            DESCRIPTION
                 "vRtrIfIpReasV6FragReasErrorsH32 is not implemented on Nokia
                  7750 c4 in release 14.0."

        VARIATION   vRtrIfIpReasV6FragReasErrorsL32
            ACCESS  not-implemented
            DESCRIPTION
                 "vRtrIfIpReasV6FragReasErrorsL32 is not implemented on Nokia
                  7750 c4 in release 14.0."

        VARIATION   vRtrIfIpReasV6OutBufRes
            ACCESS  not-implemented
            DESCRIPTION
                 "vRtrIfIpReasV6OutBufRes is not implemented on Nokia 7750 c4 in
                  release 14.0."

        VARIATION   vRtrIfIpReasV6OutBufResHigh32
            ACCESS  not-implemented
            DESCRIPTION
                 "vRtrIfIpReasV6OutBufResHigh32 is not implemented on Nokia 7750
                  c4 in release 14.0."

        VARIATION   vRtrIfIpReasV6OutBufResLow32
            ACCESS  not-implemented
            DESCRIPTION
                 "vRtrIfIpReasV6OutBufResLow32 is not implemented on Nokia 7750
                  c4 in release 14.0."

        VARIATION   vRtrIfIpReasV6PktsRx
            ACCESS  not-implemented
            DESCRIPTION
                 "vRtrIfIpReasV6PktsRx is not implemented on Nokia 7750 c4 in
                  release 14.0."

        VARIATION   vRtrIfIpReasV6PktsRxHigh32
            ACCESS  not-implemented
            DESCRIPTION
                 "vRtrIfIpReasV6PktsRxHigh32 is not implemented on Nokia 7750 c4
                  in release 14.0."

        VARIATION   vRtrIfIpReasV6PktsRxLow32
            ACCESS  not-implemented
            DESCRIPTION
                 "vRtrIfIpReasV6PktsRxLow32 is not implemented on Nokia 7750 c4
                  in release 14.0."

        VARIATION   vRtrIfIpReasV6PktsTx
            ACCESS  not-implemented
            DESCRIPTION
                 "vRtrIfIpReasV6PktsTx is not implemented on Nokia 7750 c4 in
                  release 14.0."

        VARIATION   vRtrIfIpReasV6PktsTxHigh32
            ACCESS  not-implemented
            DESCRIPTION
                 "vRtrIfIpReasV6PktsTxHigh32 is not implemented on Nokia 7750 c4
                  in release 14.0."

        VARIATION   vRtrIfIpReasV6PktsTxLow32
            ACCESS  not-implemented
            DESCRIPTION
                 "vRtrIfIpReasV6PktsTxLow32 is not implemented on Nokia 7750 c4
                  in release 14.0."

        VARIATION   vRtrIfIpcpPeerAddr
            SYNTAX  InetAddress (SIZE (0|4))
            DESCRIPTION
                 "vRtrIfIpcpPeerAddr supports only InetAddressType values
                  'unknown (0)' and 'ipv4 (1)'."

        VARIATION   vRtrIfIpcpPeerAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPeerAddrType supports only the InetAddressType
                  values 'unknown (0)' and 'ipv4 (1)'."

        VARIATION   vRtrIfIpcpPriDnsAddr
            SYNTAX  InetAddress (SIZE (0|4))
            DESCRIPTION
                 "vRtrIfIpcpPriDnsAddr supports only InetAddressType values
                  'unknown (0)' and 'ipv4 (1)'."

        VARIATION   vRtrIfIpcpPriDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPriDnsAddrType supports only the InetAddressType
                  values 'unknown (0)' and 'ipv4 (1)'."

        VARIATION   vRtrIfIpcpSecDnsAddr
            SYNTAX  InetAddress (SIZE (0|4))
            DESCRIPTION
                 "vRtrIfIpcpSecDnsAddr supports only InetAddressType values
                  'unknown (0)' and 'ipv4 (1)'."

        VARIATION   vRtrIfIpcpSecDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpSecDnsAddrType supports only the InetAddressType
                  values 'unknown (0)' and 'ipv4 (1)'."

        VARIATION   vRtrIfIpv6TrackMobile
            ACCESS  not-implemented
            DESCRIPTION
                 "vRtrIfIpv6TrackMobile is not implemented on Nokia 7750 c4 in
                  release 14.0."

        VARIATION   vRtrIfTrackMobile
            ACCESS  not-implemented
            DESCRIPTION
                 "vRtrIfTrackMobile is not implemented on Nokia 7750 c4 in
                  release 14.0."

        VARIATION   vRtrIfType
            SYNTAX  INTEGER {
                       network(1),
                       service(2),
                       serviceIes(3),
                    -- serviceRtdVpls(4)
                       serviceVprn(5),
                       serviceIesSubscriber(6),
                       serviceIesGroup(7),
                       serviceVprnSubscriber(8),
                       serviceVprnGroup(9),
                       serviceIesRedundant(10),
                       serviceVprnRedundant(11),
                       serviceVpls(12),
                       serviceIesCem(13),
                       serviceVprnCem(14),
                    -- serviceVprnIPsec(15)
                       serviceVprnIPMirror(16),
                       serviceVideo(17),
                       serviceVplsVideo(18),
                    -- multiHomingPrimary(19)
                    -- multiHomingSecondary(20)
                       serviceIesTunnel(21),
                    -- serviceIpReas(22)
                    -- networkIpReas(23)
                       networkVprn(24),
                       tmsService(25),
                       serviceIesAarp(26),
                       serviceVprnAarp(27),
                       serviceIesAa(28),
                       serviceVprnAa(29),
                       unnumMplsTp(30)
                    }
            DESCRIPTION
                 "The values - 'serviceRtdVpls (4)' (obsoleted) -
                  'serviceVprnIPsec (15)' (IPsec Tunneling) -
                  'multiHomingPrimary (19)' (obsoleted) - 'multiHomingSecondary
                  (20)' (obsoleted) - 'serviceIpReas (22)' (MG specific) -
                  'networkIpReas (23)' (MG specific) are not supported on Nokia
                  7750 c4."

        VARIATION   vRtrIgnoreIcmpRedirect
            DESCRIPTION
                 "The default value of vRtrIgnoreIcmpRedirect is changed to
                  'true' from 'false' in release 4.0-R13 and 5.0-R3."

        VARIATION   vRtrInetSRIndirectEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectSrTeLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteIndexEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRoutePfxEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrIpCidrRoutePreference
            ACCESS  read-only
            DESCRIPTION
                 "vRtrIpCidrRoutePreference is implemented as read-only on Nokia
                  7750 c4 in release 14.0."

        VARIATION   vRtrIpPoolIsRemote
            ACCESS  not-implemented
            DESCRIPTION
                 "vRtrIpPoolIsRemote is not implemented on Nokia 7750 c4 in
                  release 14.0."

        VARIATION   vRtrLdpShortcut
            SYNTAX  TmnxEnabledDisabled
            DESCRIPTION
                 "vRtrLdpShortcut is only supported in the default or base
                  routing instance."

        VARIATION   vRtrLdpTunIfSenderAddr
            SYNTAX  InetAddress (SIZE (4))
            DESCRIPTION
                 "vRtrRsvpTunIfSenderAddr supports only InetAddressType 'ipv4'."

        VARIATION   vRtrLdpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrLdpTunIfSenderAddrType supports only the InetAddressType
                  value 'ipv4 (1)'."

        VARIATION   vRtrMobileHostActiveRoutes
            ACCESS  not-implemented
            DESCRIPTION
                 "vRtrMobileHostActiveRoutes is not implemented on Nokia 7750 c4
                  in release 14.0."

        VARIATION   vRtrMobileHostRoutes
            ACCESS  not-implemented
            DESCRIPTION
                 "vRtrMobileHostRoutes is not implemented on Nokia 7750 c4 in
                  release 14.0."

        VARIATION   vRtrMvpnIpmsiType
            SYNTAX  INTEGER {
                       none                 (0),
                    -- rsvp                 (1)
                       pim                  (2)
                    }
            DESCRIPTION
                 "The value 'rsvp(1)' is not supported in the release 8.0R1."

        VARIATION   vRtrMvpnSpmsiType
            SYNTAX  INTEGER {
                       none                 (0),
                    -- rsvp                 (1)
                       pim                  (2)
                    }
            DESCRIPTION
                 "The value 'rsvp(1)' is not supported in the release 8.0R1."

        VARIATION   vRtrNextVRtrID
            ACCESS  read-only
            DESCRIPTION
                 "vRtrNextVRtrID is implemented as read-only on Nokia 7750 c4 in
                  release 14.0."

        VARIATION   vRtrRouteThresholdSoakTime
            ACCESS  read-only
            DESCRIPTION
                 "vRtrRouteThresholdSoakTime is implemented as read-only on
                  Nokia 7750 c4 in release 14.0."

        VARIATION   vRtrRsvpTunIfSenderAddr
            SYNTAX  InetAddress (SIZE (4))
            DESCRIPTION
                 "vRtrRsvpTunIfSenderAddr supports only InetAddressType 'ipv4'."

        VARIATION   vRtrRsvpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSenderAddrType supports only the InetAddressType
                  value 'ipv4 (1)'."

        VARIATION   vRtrRsvpTunIfSrcAddr
            SYNTAX  InetAddress (SIZE (4))
            DESCRIPTION
                 "vRtrRsvpTunIfSenderAddr supports only InetAddressType 'ipv4'."

        VARIATION   vRtrRsvpTunIfSrcAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSrcAddrType supports only the InetAddressType
                  value 'ipv4 (1)'."

        VARIATION   vRtrRsvpTunIfStandbyAddr
            SYNTAX  InetAddress (SIZE (4))
            DESCRIPTION
                 "vRtrRsvpTunIfSenderAddr supports only InetAddressType 'ipv4'."

        VARIATION   vRtrRsvpTunIfStandbyAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfStandbyAddrType supports only the InetAddressType
                  value 'ipv4 (1)'."

        VARIATION   vRtrV6MobileHostActiveRoutes
            ACCESS  not-implemented
            DESCRIPTION
                 "vRtrV6MobileHostActiveRoutes is not implemented on Nokia 7750
                  c4 in release 14.0."

        VARIATION   vRtrV6MobileHostRoutes
            ACCESS  not-implemented
            DESCRIPTION
                 "vRtrV6MobileHostRoutes is not implemented on Nokia 7750 c4 in
                  release 14.0."

    ::= { tmnx7750c4AgentV14v0  45 }

--
-- 7710 VRTR CAPABILITIES
--
tmnx7710VrtrV14v0                 AGENT-CAPABILITIES
    PRODUCT-RELEASE "Nokia SROS"
    STATUS          current
    DESCRIPTION
         "Implementation of Virtual Router capabilities for Nokia 7710 systems
          release 14.0."

    SUPPORTS        TIMETRA-VRTR-MIB
        INCLUDES {
           tmnxDscpAppV6v0Group,
           tmnxMGVRtrIfV4v0Group,
           tmnxVRtrAggrRouteV12v0Group,
           tmnxVRtrBfdV11v0Group,
           tmnxVRtrBgpAutoRDGroup,
           tmnxVRtrBgpEvpn12v0Group,
           tmnxVRtrBgpEvpnIpRoutes12v0Group,
           tmnxVRtrBgpLblIpRoutes14v0Group,
           tmnxVRtrCidrNextHopOwnInstGroup,
           tmnxVRtrConfExtV12v0Group,
           tmnxVRtrConfFlowspecV14v0Group,
           tmnxVRtrCreation12v0Group,
           tmnxVRtrEntropyLabelGroup,
           tmnxVRtrExportBgpVpnV11v0Group,
           tmnxVRtrFibStatsV14v0Group,
           tmnxVRtrFibStatsV8v0Group,
           tmnxVRtrFlowSpecV11v0Group,
           tmnxVRtrFpeV14v0Group,
           tmnxVRtrGenerateICMPV12v0Group,
           tmnxVRtrGlobalV10v0Group,
           tmnxVRtrGlobalV6v0Group,
           tmnxVRtrGrtLocalMgmtV10v0Group,
           tmnxVRtrHoldDownTimeV12v0Group,
           tmnxVRtrIPsecStatGroup,
           tmnxVRtrIPv6IPsecStatGroup,
           tmnxVRtrIPv6IfV4v0Group,
           tmnxVRtrIPv6IpV5v0Group,
-- EXCLUDE tmnxVRtrIPv6MgtIfV7v0Group
           tmnxVRtrIPv6V4v0Group,
           tmnxVRtrIcmpTunnelingGroup,
           tmnxVRtrIcmpV4ParamV14v0Group,
           tmnxVRtrIcmpV4StatsV14v0Group,
           tmnxVRtrIfArpNbrLimitGroup,
           tmnxVRtrIfArpNbrNotifGroup,
-- EXCLUDE tmnxVRtrIfCpmProtectGroup
           tmnxVRtrIfDHCP6V10v0Group,
           tmnxVRtrIfDHCP6V11v0Group,
           tmnxVRtrIfDHCP6V12v0Group,
           tmnxVRtrIfDHCP6V9v0Group,
           tmnxVRtrIfDHCPRelayV11v0Group,
           tmnxVRtrIfDHCPRelayV13v0Group,
           tmnxVRtrIfDHCPRelayV14v0Group,
           tmnxVRtrIfDHCPRelayV6v1Group,
           tmnxVRtrIfDHCPRelayV9v0Group,
           tmnxVRtrIfDhcpServerGroup,
           tmnxVRtrIfExtIfArpRetryTimerGrp,
           tmnxVRtrIfExtV12v0Group,
           tmnxVRtrIfExtV13v0Group,
           tmnxVRtrIfExtV14v0Group,
           tmnxVRtrIfIpReasV9v0Group,
           tmnxVRtrIfIpcpV6v0Group,
           tmnxVRtrIfLagPerLinkHashGroup,
           tmnxVRtrIfMacStatsV11v0Group,
           tmnxVRtrIfSendV12v0Group,
           tmnxVRtrIfStatsV11v0Group,
           tmnxVRtrIfStatsV9v0Group,
           tmnxVRtrIfSubscrAuthV3v0Group,
           tmnxVRtrIfV10v0Group,
           tmnxVRtrIfV14v0Group,
           tmnxVRtrInetAllCidrRouteV7v0Group,
           tmnxVRtrInetSRIndirectV13v0Group,
           tmnxVRtrInetSRIndirectV14v0Group,
           tmnxVRtrInetStaticRouteV7v0Group,
           tmnxVRtrIpPoolGroup,
           tmnxVRtrIpV13v0Group,
           tmnxVRtrIpV13v0ObsoletedGroup,
           tmnxVRtrIpv6RtrAdvertV11v0Group,
           tmnxVRtrLagEgrLoadBal12v0Group,
           tmnxVRtrLagHashLoadBal12v0Group,
           tmnxVRtrLdpIpv613v0Group,
           tmnxVRtrLoadBalEnhV13v0Group,
           tmnxVRtrLoopbackNotifGroup,
           tmnxVRtrLspBfdGroup,
           tmnxVRtrMSPwV9v0Group,
           tmnxVRtrMcastSpmsiEnhV13v0Group,
           tmnxVRtrMcastV11v0Group,
           tmnxVRtrMvpnPmsiV8v0Group,
           tmnxVRtrMvpnSrcRedV9v0R4Group,
           tmnxVRtrNatRedGroup,
           tmnxVRtrNetDomainGroup,
           tmnxVRtrNotificationNHRvplsArpGr,
           tmnxVRtrNotificationV10v0Group,
           tmnxVRtrNotificationV14v0Group,
           tmnxVRtrNotifyObjsNHRvplsArpGrp,
           tmnxVRtrPlcyAcctTempl12v0Group,
           tmnxVRtrPolicyGroup,
           tmnxVRtrQPPBV9v0R4Group,
           tmnxVRtrQosQGrplV10v0Group,
           tmnxVRtrRAV12v0Group,
           tmnxVRtrSrTeV14v0Group,
           tmnxVRtrStatV10v0Group,
           tmnxVRtrStatV11v0Group,
           tmnxVRtrStatV9v0Group,
           tmnxVRtrStaticRoutePrefixGroup,
           tmnxVRtrStaticRteCPEChkV6v0Group,
           tmnxVRtrStickyHashEcmp12v0Group,
           tmnxVRtrTunIntV8v0Group,
           tmnxVRtrTunnelExtTableV13v0Group,
           tmnxVRtrTunnelTableCBFV13v0Group,
           tmnxVRtrTunnelTableLSCV14v0Group,
           tmnxVRtrTunnelTableNhTV14v0Group,
           tmnxVRtrTunnelTableStatGroup,
           tmnxVRtrUniqueIfIndexGroup,
           tmnxVRtrV12v0Group,
           tmnxVRtrV13v0GenObsoletedGroup,
           tmnxVRtrV13v0IfStatsGroup,
           tmnxVRtrV14v0Group,
           tmnxVRtrV14v0NotifyObjsGroup,
           tmnxVRtrV6TunnelTableStatGroup,
           tmnxVRtrV6v1Group,
           tmnxVRtrV9v0Group,
           tmnxVRtrVccvBfd12v0Group,
           tmnxVRtrVirtualCPE12v0Group,
           tmnxVRtruRPFV10v0Group,
           tmnxVRtruRPFV7v0Group,
           tmnxVrtrDcpNotifyObjsV11v0Group,
           tmnxVrtrIfDCpuProtV11v0Group,
           tmnxVrtrIfDHCP6ProxyDuidGroup,
           tmnxVrtrIfDcpNotifyV11v0Group,
           tmnxvRtrIfAttributeGroup
        }

        VARIATION   vRtrFibStatMobileHostRoutes
            ACCESS  not-implemented
            DESCRIPTION
                 "vRtrFibStatMobileHostRoutes is not implemented on Nokia 7710
                  in release 14.0."

        VARIATION   vRtrFibStatV6MobileHostRoutes
            ACCESS  not-implemented
            DESCRIPTION
                 "vRtrFibStatV6MobileHostRoutes is not implemented on Nokia 7710
                  in release 14.0."

        VARIATION   vRtrIPv6RouteThresholdSoakTime
            ACCESS  read-only
            DESCRIPTION
                 "vRtrIPv6RouteThresholdSoakTime is implemented as read-only on
                  Nokia 7710 in release 14.0."

        VARIATION   vRtrIfAlias
            ACCESS  read-only
            DESCRIPTION
                 "vRtrIfAlias is implemented as read-only on Nokia 7710 in
                  release 14.0."

        VARIATION   vRtrIfBfdType
            SYNTAX  INTEGER {
                    -- cpmNp(1)
                       auto(2)
                    }
            DESCRIPTION
                 "cpmNp(1) is not supported on Nokia 7710."

        VARIATION   vRtrIfDHCP6ProxyDuidEnIdDataType
            SYNTAX  INTEGER {
                    -- ipv4(1)
                       ascii(2),
                       hex(3)
                    -- ipv6(4)
                    -- domain(5)
                    }
            DESCRIPTION
                 "The only allowed values for this object are 'ascii(2)' and
                  'hex(3)'."

        VARIATION   vRtrIfDHCPLeasePopulate
            DESCRIPTION
                 "The default value of vRtrIfDHCPLeasePopulate is '1', not '0',
                  when the interface running DHCP has vRtrIfType
                  'serviceIesGroup'."

        VARIATION   vRtrIfDHCPRelaySiaddrOvrAddr
            SYNTAX  InetAddress (SIZE (0|4))
            DESCRIPTION
                 "vRtrIfDHCPRelaySiaddrOvrAddr supports only InetAddressType
                  values 'unknown (0)' and 'ipv4 (1)'."

        VARIATION   vRtrIfDHCPRelaySiaddrOvrAddrType
            SYNTAX  InetAddressType {
                       unknown              (0),
                       ipv4                 (1)
                    -- ipv6                 (2)
                    -- ipv4z                (3)
                    -- ipv6z                (4)
                    -- dns                  (16)
                    }
            DESCRIPTION
                 "vRtrIfDHCPRelaySiaddrOvrAddrType supports only the
                  InetAddressType values 'unknown (0)' and 'ipv4 (1)'."

        VARIATION   vRtrIfIpReasBytesRx
            ACCESS  not-implemented
            DESCRIPTION
                 "vRtrIfIpReasBytesRx is not implemented on Nokia 7710 in
                  release 14.0."

        VARIATION   vRtrIfIpReasBytesRxHigh32
            ACCESS  not-implemented
            DESCRIPTION
                 "vRtrIfIpReasBytesRxHigh32 is not implemented on Nokia 7710 in
                  release 14.0."

        VARIATION   vRtrIfIpReasBytesRxLow32
            ACCESS  not-implemented
            DESCRIPTION
                 "vRtrIfIpReasBytesRxLow32 is not implemented on Nokia 7710 in
                  release 14.0."

        VARIATION   vRtrIfIpReasBytesTx
            ACCESS  not-implemented
            DESCRIPTION
                 "vRtrIfIpReasBytesTx is not implemented on Nokia 7710 in
                  release 14.0."

        VARIATION   vRtrIfIpReasBytesTxHigh32
            ACCESS  not-implemented
            DESCRIPTION
                 "vRtrIfIpReasBytesTxHigh32 is not implemented on Nokia 7710 in
                  release 14.0."

        VARIATION   vRtrIfIpReasBytesTxLow32
            ACCESS  not-implemented
            DESCRIPTION
                 "vRtrIfIpReasBytesTxLow32 is not implemented on Nokia 7710 in
                  release 14.0."

        VARIATION   vRtrIfIpReasContextValue
            ACCESS  not-implemented
            DESCRIPTION
                 "vRtrIfIpReasContextValue is not implemented on Nokia 7710 in
                  release 14.0."

        VARIATION   vRtrIfIpReasFragBytesRcvd
            ACCESS  not-implemented
            DESCRIPTION
                 "vRtrIfIpReasFragBytesRcvd is not implemented on Nokia 7710 in
                  release 14.0."

        VARIATION   vRtrIfIpReasFragBytesRcvdHigh32
            ACCESS  not-implemented
            DESCRIPTION
                 "vRtrIfIpReasFragBytesRcvdHigh32 is not implemented on Nokia
                  7710 in release 14.0."

        VARIATION   vRtrIfIpReasFragBytesRcvdLow32
            ACCESS  not-implemented
            DESCRIPTION
                 "vRtrIfIpReasFragBytesRcvdLow32 is not implemented on Nokia
                  7710 in release 14.0."

        VARIATION   vRtrIfIpReasFragBytesReas
            ACCESS  not-implemented
            DESCRIPTION
                 "vRtrIfIpReasFragBytesReas is not implemented on Nokia 7710 in
                  release 14.0."

        VARIATION   vRtrIfIpReasFragBytesReasHigh32
            ACCESS  not-implemented
            DESCRIPTION
                 "vRtrIfIpReasFragBytesReasHigh32 is not implemented on Nokia
                  7710 in release 14.0."

        VARIATION   vRtrIfIpReasFragBytesReasLow32
            ACCESS  not-implemented
            DESCRIPTION
                 "vRtrIfIpReasFragBytesReasLow32 is not implemented on Nokia
                  7710 in release 14.0."

        VARIATION   vRtrIfIpReasFragDisc
            ACCESS  not-implemented
            DESCRIPTION
                 "vRtrIfIpReasFragDisc is not implemented on Nokia 7710 in
                  release 14.0."

        VARIATION   vRtrIfIpReasFragDiscHigh32
            ACCESS  not-implemented
            DESCRIPTION
                 "vRtrIfIpReasFragDiscHigh32 is not implemented on Nokia 7710 in
                  release 14.0."

        VARIATION   vRtrIfIpReasFragDiscLow32
            ACCESS  not-implemented
            DESCRIPTION
                 "vRtrIfIpReasFragDiscLow32 is not implemented on Nokia 7710 in
                  release 14.0."

        VARIATION   vRtrIfIpReasFragPktsRcvd
            ACCESS  not-implemented
            DESCRIPTION
                 "vRtrIfIpReasFragPktsRcvd is not implemented on Nokia 7710 in
                  release 14.0."

        VARIATION   vRtrIfIpReasFragPktsRcvdHigh32
            ACCESS  not-implemented
            DESCRIPTION
                 "vRtrIfIpReasFragPktsRcvdHigh32 is not implemented on Nokia
                  7710 in release 14.0."

        VARIATION   vRtrIfIpReasFragPktsRcvdLow32
            ACCESS  not-implemented
            DESCRIPTION
                 "vRtrIfIpReasFragPktsRcvdLow32 is not implemented on Nokia 7710
                  in release 14.0."

        VARIATION   vRtrIfIpReasFragPktsReas
            ACCESS  not-implemented
            DESCRIPTION
                 "vRtrIfIpReasFragPktsReas is not implemented on Nokia 7710 in
                  release 14.0."

        VARIATION   vRtrIfIpReasFragPktsReasHigh32
            ACCESS  not-implemented
            DESCRIPTION
                 "vRtrIfIpReasFragPktsReasHigh32 is not implemented on Nokia
                  7710 in release 14.0."

        VARIATION   vRtrIfIpReasFragPktsReasLow32
            ACCESS  not-implemented
            DESCRIPTION
                 "vRtrIfIpReasFragPktsReasLow32 is not implemented on Nokia 7710
                  in release 14.0."

        VARIATION   vRtrIfIpReasFragReasErrors
            ACCESS  not-implemented
            DESCRIPTION
                 "vRtrIfIpReasFragReasErrors is not implemented on Nokia 7710 in
                  release 14.0."

        VARIATION   vRtrIfIpReasFragReasErrorsHigh32
            ACCESS  not-implemented
            DESCRIPTION
                 "vRtrIfIpReasFragReasErrorsHigh32 is not implemented on Nokia
                  7710 in release 14.0."

        VARIATION   vRtrIfIpReasFragReasErrorsLow32
            ACCESS  not-implemented
            DESCRIPTION
                 "vRtrIfIpReasFragReasErrorsLow32 is not implemented on Nokia
                  7710 in release 14.0."

        VARIATION   vRtrIfIpReasOutBufRes
            ACCESS  not-implemented
            DESCRIPTION
                 "vRtrIfIpReasOutBufRes is not implemented on Nokia 7710 in
                  release 14.0."

        VARIATION   vRtrIfIpReasOutBufResHigh32
            ACCESS  not-implemented
            DESCRIPTION
                 "vRtrIfIpReasOutBufResHigh32 is not implemented on Nokia 7710
                  in release 14.0."

        VARIATION   vRtrIfIpReasOutBufResLow32
            ACCESS  not-implemented
            DESCRIPTION
                 "vRtrIfIpReasOutBufResLow32 is not implemented on Nokia 7710 in
                  release 14.0."

        VARIATION   vRtrIfIpReasPktsRx
            ACCESS  not-implemented
            DESCRIPTION
                 "vRtrIfIpReasPktsRx is not implemented on Nokia 7710 in release
                  14.0."

        VARIATION   vRtrIfIpReasPktsRxHigh32
            ACCESS  not-implemented
            DESCRIPTION
                 "vRtrIfIpReasPktsRxHigh32 is not implemented on Nokia 7710 in
                  release 14.0."

        VARIATION   vRtrIfIpReasPktsRxLow32
            ACCESS  not-implemented
            DESCRIPTION
                 "vRtrIfIpReasPktsRxLow32 is not implemented on Nokia 7710 in
                  release 14.0."

        VARIATION   vRtrIfIpReasPktsTx
            ACCESS  not-implemented
            DESCRIPTION
                 "vRtrIfIpReasPktsTx is not implemented on Nokia 7710 in release
                  14.0."

        VARIATION   vRtrIfIpReasPktsTxHigh32
            ACCESS  not-implemented
            DESCRIPTION
                 "vRtrIfIpReasPktsTxHigh32 is not implemented on Nokia 7710 in
                  release 14.0."

        VARIATION   vRtrIfIpReasPktsTxLow32
            ACCESS  not-implemented
            DESCRIPTION
                 "vRtrIfIpReasPktsTxLow32 is not implemented on Nokia 7710 in
                  release 14.0."

        VARIATION   vRtrIfIpReasPortID
            ACCESS  not-implemented
            DESCRIPTION
                 "vRtrIfIpReasPortID is not implemented on Nokia 7710 in release
                  14.0."

        VARIATION   vRtrIfIpReasV6BytesRx
            ACCESS  not-implemented
            DESCRIPTION
                 "vRtrIfIpReasV6BytesRx is not implemented on Nokia 7710 in
                  release 14.0."

        VARIATION   vRtrIfIpReasV6BytesRxHigh32
            ACCESS  not-implemented
            DESCRIPTION
                 "vRtrIfIpReasV6BytesRxHigh32 is not implemented on Nokia 7710
                  in release 14.0."

        VARIATION   vRtrIfIpReasV6BytesRxLow32
            ACCESS  not-implemented
            DESCRIPTION
                 "vRtrIfIpReasV6BytesRxLow32 is not implemented on Nokia 7710 in
                  release 14.0."

        VARIATION   vRtrIfIpReasV6BytesTx
            ACCESS  not-implemented
            DESCRIPTION
                 "vRtrIfIpReasV6BytesTx is not implemented on Nokia 7710 in
                  release 14.0."

        VARIATION   vRtrIfIpReasV6BytesTxHigh32
            ACCESS  not-implemented
            DESCRIPTION
                 "vRtrIfIpReasV6BytesTxHigh32 is not implemented on Nokia 7710
                  in release 14.0."

        VARIATION   vRtrIfIpReasV6BytesTxLow32
            ACCESS  not-implemented
            DESCRIPTION
                 "vRtrIfIpReasV6BytesTxLow32 is not implemented on Nokia 7710 in
                  release 14.0."

        VARIATION   vRtrIfIpReasV6FragBytesRcvd
            ACCESS  not-implemented
            DESCRIPTION
                 "vRtrIfIpReasV6FragBytesRcvd is not implemented on Nokia 7710
                  in release 14.0."

        VARIATION   vRtrIfIpReasV6FragBytesRcvdH32
            ACCESS  not-implemented
            DESCRIPTION
                 "vRtrIfIpReasV6FragBytesRcvdH32 is not implemented on Nokia
                  7710 in release 14.0."

        VARIATION   vRtrIfIpReasV6FragBytesRcvdL32
            ACCESS  not-implemented
            DESCRIPTION
                 "vRtrIfIpReasV6FragBytesRcvdL32 is not implemented on Nokia
                  7710 in release 14.0."

        VARIATION   vRtrIfIpReasV6FragBytesReas
            ACCESS  not-implemented
            DESCRIPTION
                 "vRtrIfIpReasV6FragBytesReas is not implemented on Nokia 7710
                  in release 14.0."

        VARIATION   vRtrIfIpReasV6FragBytesReasH32
            ACCESS  not-implemented
            DESCRIPTION
                 "vRtrIfIpReasV6FragBytesReasH32 is not implemented on Nokia
                  7710 in release 14.0."

        VARIATION   vRtrIfIpReasV6FragBytesReasL32
            ACCESS  not-implemented
            DESCRIPTION
                 "vRtrIfIpReasV6FragBytesReasL32 is not implemented on Nokia
                  7710 in release 14.0."

        VARIATION   vRtrIfIpReasV6FragDisc
            ACCESS  not-implemented
            DESCRIPTION
                 "vRtrIfIpReasV6FragDisc is not implemented on Nokia 7710 in
                  release 14.0."

        VARIATION   vRtrIfIpReasV6FragDiscHigh32
            ACCESS  not-implemented
            DESCRIPTION
                 "vRtrIfIpReasV6FragDiscHigh32 is not implemented on Nokia 7710
                  in release 14.0."

        VARIATION   vRtrIfIpReasV6FragDiscLow32
            ACCESS  not-implemented
            DESCRIPTION
                 "vRtrIfIpReasV6FragDiscLow32 is not implemented on Nokia 7710
                  in release 14.0."

        VARIATION   vRtrIfIpReasV6FragPktsRcvd
            ACCESS  not-implemented
            DESCRIPTION
                 "vRtrIfIpReasV6FragPktsRcvd is not implemented on Nokia 7710 in
                  release 14.0."

        VARIATION   vRtrIfIpReasV6FragPktsRcvdHigh32
            ACCESS  not-implemented
            DESCRIPTION
                 "vRtrIfIpReasV6FragPktsRcvdHigh32 is not implemented on Nokia
                  7710 in release 14.0."

        VARIATION   vRtrIfIpReasV6FragPktsRcvdLow32
            ACCESS  not-implemented
            DESCRIPTION
                 "vRtrIfIpReasV6FragPktsRcvdLow32 is not implemented on Nokia
                  7710 in release 14.0."

        VARIATION   vRtrIfIpReasV6FragPktsReas
            ACCESS  not-implemented
            DESCRIPTION
                 "vRtrIfIpReasV6FragPktsReas is not implemented on Nokia 7710 in
                  release 14.0."

        VARIATION   vRtrIfIpReasV6FragPktsReasHigh32
            ACCESS  not-implemented
            DESCRIPTION
                 "vRtrIfIpReasV6FragPktsReasHigh32 is not implemented on Nokia
                  7710 in release 14.0."

        VARIATION   vRtrIfIpReasV6FragPktsReasLow32
            ACCESS  not-implemented
            DESCRIPTION
                 "vRtrIfIpReasV6FragPktsReasLow32 is not implemented on Nokia
                  7710 in release 14.0."

        VARIATION   vRtrIfIpReasV6FragReasErrors
            ACCESS  not-implemented
            DESCRIPTION
                 "vRtrIfIpReasV6FragReasErrors is not implemented on Nokia 7710
                  in release 14.0."

        VARIATION   vRtrIfIpReasV6FragReasErrorsH32
            ACCESS  not-implemented
            DESCRIPTION
                 "vRtrIfIpReasV6FragReasErrorsH32 is not implemented on Nokia
                  7710 in release 14.0."

        VARIATION   vRtrIfIpReasV6FragReasErrorsL32
            ACCESS  not-implemented
            DESCRIPTION
                 "vRtrIfIpReasV6FragReasErrorsL32 is not implemented on Nokia
                  7710 in release 14.0."

        VARIATION   vRtrIfIpReasV6OutBufRes
            ACCESS  not-implemented
            DESCRIPTION
                 "vRtrIfIpReasV6OutBufRes is not implemented on Nokia 7710 in
                  release 14.0."

        VARIATION   vRtrIfIpReasV6OutBufResHigh32
            ACCESS  not-implemented
            DESCRIPTION
                 "vRtrIfIpReasV6OutBufResHigh32 is not implemented on Nokia 7710
                  in release 14.0."

        VARIATION   vRtrIfIpReasV6OutBufResLow32
            ACCESS  not-implemented
            DESCRIPTION
                 "vRtrIfIpReasV6OutBufResLow32 is not implemented on Nokia 7710
                  in release 14.0."

        VARIATION   vRtrIfIpReasV6PktsRx
            ACCESS  not-implemented
            DESCRIPTION
                 "vRtrIfIpReasV6PktsRx is not implemented on Nokia 7710 in
                  release 14.0."

        VARIATION   vRtrIfIpReasV6PktsRxHigh32
            ACCESS  not-implemented
            DESCRIPTION
                 "vRtrIfIpReasV6PktsRxHigh32 is not implemented on Nokia 7710 in
                  release 14.0."

        VARIATION   vRtrIfIpReasV6PktsRxLow32
            ACCESS  not-implemented
            DESCRIPTION
                 "vRtrIfIpReasV6PktsRxLow32 is not implemented on Nokia 7710 in
                  release 14.0."

        VARIATION   vRtrIfIpReasV6PktsTx
            ACCESS  not-implemented
            DESCRIPTION
                 "vRtrIfIpReasV6PktsTx is not implemented on Nokia 7710 in
                  release 14.0."

        VARIATION   vRtrIfIpReasV6PktsTxHigh32
            ACCESS  not-implemented
            DESCRIPTION
                 "vRtrIfIpReasV6PktsTxHigh32 is not implemented on Nokia 7710 in
                  release 14.0."

        VARIATION   vRtrIfIpReasV6PktsTxLow32
            ACCESS  not-implemented
            DESCRIPTION
                 "vRtrIfIpReasV6PktsTxLow32 is not implemented on Nokia 7710 in
                  release 14.0."

        VARIATION   vRtrIfIpcpPeerAddr
            SYNTAX  InetAddress (SIZE (0|4))
            DESCRIPTION
                 "vRtrIfIpcpPeerAddr supports only InetAddressType values
                  'unknown (0)' and 'ipv4 (1)'."

        VARIATION   vRtrIfIpcpPeerAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPeerAddrType supports only the InetAddressType
                  values 'unknown (0)' and 'ipv4 (1)'."

        VARIATION   vRtrIfIpcpPriDnsAddr
            SYNTAX  InetAddress (SIZE (0|4))
            DESCRIPTION
                 "vRtrIfIpcpPriDnsAddr supports only InetAddressType values
                  'unknown (0)' and 'ipv4 (1)'."

        VARIATION   vRtrIfIpcpPriDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpPriDnsAddrType supports only the InetAddressType
                  values 'unknown (0)' and 'ipv4 (1)'."

        VARIATION   vRtrIfIpcpSecDnsAddr
            SYNTAX  InetAddress (SIZE (0|4))
            DESCRIPTION
                 "vRtrIfIpcpSecDnsAddr supports only InetAddressType values
                  'unknown (0)' and 'ipv4 (1)'."

        VARIATION   vRtrIfIpcpSecDnsAddrType
            SYNTAX  InetAddressType {
                       unknown              (0),
                       ipv4                 (1)
                    -- ipv6                 (2)
                    -- ipv4z                (3)
                    -- ipv6z                (4)
                    -- dns                  (16)
                    }
            DESCRIPTION
                 "vRtrIfIpcpSecDnsAddrType supports only the InetAddressType
                  values 'unknown (0)' and 'ipv4 (1)'."

        VARIATION   vRtrIfIpv6TrackMobile
            ACCESS  not-implemented
            DESCRIPTION
                 "vRtrIfIpv6TrackMobile is not implemented on Nokia 7710 in
                  release 14.0."

        VARIATION   vRtrIfTrackMobile
            ACCESS  not-implemented
            DESCRIPTION
                 "vRtrIfTrackMobile is not implemented on Nokia 7710 in release
                  14.0."

        VARIATION   vRtrIfType
            SYNTAX  INTEGER {
                       network(1),
                       service(2),
                       serviceIes(3),
                    -- serviceRtdVpls(4)
                       serviceVprn(5),
                       serviceIesSubscriber(6),
                       serviceIesGroup(7),
                       serviceVprnSubscriber(8),
                       serviceVprnGroup(9),
                       serviceIesRedundant(10),
                       serviceVprnRedundant(11),
                       serviceVpls(12),
                       serviceIesCem(13),
                       serviceVprnCem(14),
                    -- serviceVprnIPsec(15)
                       serviceVprnIPMirror(16),
                       serviceVideo(17),
                       serviceVplsVideo(18),
                    -- multiHomingPrimary(19)
                    -- multiHomingSecondary(20)
                       serviceIesTunnel(21),
                    -- serviceIpReas(22)
                    -- networkIpReas(23)
                       networkVprn(24),
                       tmsService(25),
                       serviceIesAarp(26),
                       serviceVprnAarp(27),
                       serviceIesAa(28),
                       serviceVprnAa(29),
                       unnumMplsTp(30)
                    }
            DESCRIPTION
                 "The values - 'serviceRtdVpls (4)' (obsoleted) -
                  'serviceVprnIPsec (15)' (IPsec Tunneling) -
                  'multiHomingPrimary (19)' (obsoleted) - 'multiHomingSecondary
                  (20)' (obsoleted) - 'serviceIpReas (22)' (MG specific) -
                  'networkIpReas (23)' (MG specific) are not supported on Nokia
                  7710."

        VARIATION   vRtrIgnoreIcmpRedirect
            DESCRIPTION
                 "The default value of vRtrIgnoreIcmpRedirect is changed to
                  'true' from 'false' in release 4.0-R13 and 5.0-R3."

        VARIATION   vRtrInetSRIndirectEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetSRIndirectSrTeLspEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRouteIndexEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrInetStaticRoutePfxEntry
            DESCRIPTION
                 "The index vRtrInetStaticRouteDestType supports the values
                  'ipv4Mcast (128)' and 'ipv6Mcast (129)' in addition to those
                  defined by the InetAddressType textual convention. 'ipv4Mcast
                  (128)' and 'ipv6Mcast (129)' are implemented for 'ipv4'/'ipv6'
                  addresses for multicast extensions."

        VARIATION   vRtrIpCidrRoutePreference
            ACCESS  read-only
            DESCRIPTION
                 "vRtrIpCidrRoutePreference is implemented as read-only on Nokia
                  7710 in release 14.0."

        VARIATION   vRtrIpPoolIsRemote
            ACCESS  not-implemented
            DESCRIPTION
                 "vRtrIpPoolIsRemote is not implemented on Nokia 7710 in release
                  14.0."

        VARIATION   vRtrLdpShortcut
            SYNTAX  TmnxEnabledDisabled
            DESCRIPTION
                 "vRtrLdpShortcut is only supported in the default or base
                  routing instance."

        VARIATION   vRtrLdpTunIfSenderAddr
            SYNTAX  InetAddress (SIZE (4))
            DESCRIPTION
                 "vRtrRsvpTunIfSenderAddr supports only InetAddressType 'ipv4'."

        VARIATION   vRtrLdpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrLdpTunIfSenderAddrType supports only the InetAddressType
                  value 'ipv4 (1)'."

        VARIATION   vRtrMobileHostActiveRoutes
            ACCESS  not-implemented
            DESCRIPTION
                 "vRtrMobileHostActiveRoutes is not implemented on Nokia 7710 in
                  release 14.0."

        VARIATION   vRtrMobileHostRoutes
            ACCESS  not-implemented
            DESCRIPTION
                 "vRtrMobileHostRoutes is not implemented on Nokia 7710 in
                  release 14.0."

        VARIATION   vRtrMvpnIpmsiType
            SYNTAX  INTEGER {
                       none                 (0),
                    -- rsvp                 (1)
                       pim                  (2)
                    }
            DESCRIPTION
                 "The value 'rsvp(1)' is not supported in the release 8.0R1."

        VARIATION   vRtrMvpnSpmsiType
            SYNTAX  INTEGER {
                       none                 (0),
                    -- rsvp                 (1)
                       pim                  (2)
                    }
            DESCRIPTION
                 "The value 'rsvp(1)' is not supported in the release 8.0R1."

        VARIATION   vRtrNextVRtrID
            ACCESS  read-only
            DESCRIPTION
                 "vRtrNextVRtrID is implemented as read-only on Nokia 7710 in
                  release 14.0."

        VARIATION   vRtrRouteThresholdSoakTime
            ACCESS  read-only
            DESCRIPTION
                 "vRtrRouteThresholdSoakTime is implemented as read-only on
                  Nokia 7710 in release 14.0."

        VARIATION   vRtrRsvpTunIfSenderAddr
            SYNTAX  InetAddress (SIZE (4))
            DESCRIPTION
                 "vRtrRsvpTunIfSenderAddr supports only InetAddressType 'ipv4'."

        VARIATION   vRtrRsvpTunIfSenderAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSenderAddrType supports only the InetAddressType
                  value 'ipv4 (1)'."

        VARIATION   vRtrRsvpTunIfSrcAddr
            SYNTAX  InetAddress (SIZE (4))
            DESCRIPTION
                 "vRtrRsvpTunIfSenderAddr supports only InetAddressType 'ipv4'."

        VARIATION   vRtrRsvpTunIfSrcAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfSrcAddrType supports only the InetAddressType
                  value 'ipv4 (1)'."

        VARIATION   vRtrRsvpTunIfStandbyAddr
            SYNTAX  InetAddress (SIZE (4))
            DESCRIPTION
                 "vRtrRsvpTunIfSenderAddr supports only InetAddressType 'ipv4'."

        VARIATION   vRtrRsvpTunIfStandbyAddrType
            SYNTAX  InetAddressType {
                    -- unknown              (0)
                       ipv4                 (1)
                    -- ipv6                 (2)
                    -- ipv4z                (3)
                    -- ipv6z                (4)
                    -- dns                  (16)
                    }
            DESCRIPTION
                 "vRtrRsvpTunIfStandbyAddrType supports only the InetAddressType
                  value 'ipv4 (1)'."

        VARIATION   vRtrV6MobileHostActiveRoutes
            ACCESS  not-implemented
            DESCRIPTION
                 "vRtrV6MobileHostActiveRoutes is not implemented on Nokia 7710
                  in release 14.0."

        VARIATION   vRtrV6MobileHostRoutes
            ACCESS  not-implemented
            DESCRIPTION
                 "vRtrV6MobileHostRoutes is not implemented on Nokia 7710 in
                  release 14.0."

    ::= { tmnx7710AgentV14v0  45 }

--
-- 7750 WLAN_GW CAPABILITIES
--
tmnx7750WlanGwV14v0               AGENT-CAPABILITIES
    PRODUCT-RELEASE "Nokia SROS"
    STATUS          current
    DESCRIPTION
         "Implementation of the Wireless Local Area Network Gateway function on
          Nokia 7750 systems release 14.0."

    SUPPORTS        TIMETRA-WLAN-GW-MIB
        INCLUDES {
           tmnxWlanGwDsmGroup,
           tmnxWlanGwDsmV13v0Group,
           tmnxWlanGwDsmV14v0Group,
           tmnxWlanGwInterVlanMobGroup,
           tmnxWlanGwIsaGroup,
           tmnxWlanGwL2ApGroup,
           tmnxWlanGwL2tpv3Group,
           tmnxWlanGwMgwAmbrIeGroup,
           tmnxWlanGwMgwChargingCharGroup,
           tmnxWlanGwMgwGroup,
           tmnxWlanGwMgwQosIeGroup,
           tmnxWlanGwMgwSeHoldTimeGroup,
           tmnxWlanGwMgwV11v0Group,
           tmnxWlanGwMobilityGroup,
           tmnxWlanGwNotifyGroup,
           tmnxWlanGwObsoletedGroup,
           tmnxWlanGwRedGroup,
           tmnxWlanGwSoftGreV12v0Group,
           tmnxWlanGwUeQryGroup,
           tmnxWlanGwV12v0Group,
           tmnxWlanGwV14v0Group,
           tmnxWlanGwVsrGroup
        }

        VARIATION   tmnxWlanGwGrpAdminState
            SYNTAX  INTEGER {
                    -- noop                 (1)
                       inService            (2),
                       outOfService         (3)
                    }
            DESCRIPTION
                 "tmnxWlanGwGrpAdminState supports only the values 'inService
                  (2)' and 'outOfService (3)'."

        VARIATION   tmnxWlanGwGrpRowStatus
            SYNTAX  RowStatus {
                       active               (1),
                    -- notInService         (2)
                    -- notReady             (3)
                       createAndGo          (4),
                    -- createAndWait        (5)
                       destroy              (6)
                    }
            DESCRIPTION
                 "tmnxWlanGwGrpRowStatus supports only 'active (1)',
                  'createAndGo (4)', and 'destroy (6)'."

        VARIATION   tmnxWlanGwIomRowStatus
            SYNTAX  RowStatus {
                       active               (1),
                    -- notInService         (2)
                    -- notReady             (3)
                       createAndGo          (4),
                    -- createAndWait        (5)
                       destroy              (6)
                    }
            DESCRIPTION
                 "tmnxWlanGwIomRowStatus supports only 'active (1)',
                  'createAndGo (4)', and 'destroy (6)'."

        VARIATION   tmnxWlanGwSoftGreIfAdminState
            SYNTAX  INTEGER {
                    -- noop                 (1)
                       inService            (2),
                       outOfService         (3)
                    }
            DESCRIPTION
                 "tmnxWlanGwSoftGreIfAdminState supports only the values
                  'inService (2)' and 'outOfService (3)'."

        VARIATION   tmnxWlanGwSoftGreIfGwAddrType
            SYNTAX  InetAddressType {
                       unknown              (0),
                       ipv4                 (1)
                    -- ipv6                 (2)
                    -- ipv4z                (3)
                    -- ipv6z                (4)
                    -- dns                  (16)
                    }
            DESCRIPTION
                 "tmnxWlanGwSoftGreIfGwAddrType supports only the
                  InetAddressType values 'unknown (0)' and 'ipv4 (1)'."

        VARIATION   tmnxWlanGwSoftGreXtAddrType
            SYNTAX  InetAddressType {
                       unknown              (0),
                       ipv4                 (1)
                    -- ipv6                 (2)
                    -- ipv4z                (3)
                    -- ipv6z                (4)
                    -- dns                  (16)
                    }
            DESCRIPTION
                 "tmnxWlanGwSoftGreXtAddrType supports only the InetAddressType
                  values 'unknown (0)' and 'ipv4 (1)'."

        VARIATION   tmnxWlanGwSoftGreXtDns1AddrType
            SYNTAX  InetAddressType {
                       unknown              (0),
                       ipv4                 (1)
                    -- ipv6                 (2)
                    -- ipv4z                (3)
                    -- ipv6z                (4)
                    -- dns                  (16)
                    }
            DESCRIPTION
                 "tmnxWlanGwSoftGreXtDns1AddrType supports only the
                  InetAddressType values 'unknown (0)' and 'ipv4 (1)'."

        VARIATION   tmnxWlanGwSoftGreXtDns2AddrType
            SYNTAX  InetAddressType {
                       unknown              (0),
                       ipv4                 (1)
                    -- ipv6                 (2)
                    -- ipv4z                (3)
                    -- ipv6z                (4)
                    -- dns                  (16)
                    }
            DESCRIPTION
                 "tmnxWlanGwSoftGreXtDns2AddrType supports only the
                  InetAddressType values 'unknown (0)' and 'ipv4 (1)'."

        VARIATION   tmnxWlanGwSoftGreXtNb1AddrType
            SYNTAX  InetAddressType {
                       unknown              (0),
                       ipv4                 (1)
                    -- ipv6                 (2)
                    -- ipv4z                (3)
                    -- ipv6z                (4)
                    -- dns                  (16)
                    }
            DESCRIPTION
                 "tmnxWlanGwSoftGreXtNb1AddrType supports only the
                  InetAddressType values 'unknown (0)' and 'ipv4 (1)'."

        VARIATION   tmnxWlanGwSoftGreXtNb2AddrType
            SYNTAX  InetAddressType {
                       unknown              (0),
                       ipv4                 (1)
                    -- ipv6                 (2)
                    -- ipv4z                (3)
                    -- ipv6z                (4)
                    -- dns                  (16)
                    }
            DESCRIPTION
                 "tmnxWlanGwSoftGreXtNb2AddrType supports only the
                  InetAddressType values 'unknown (0)' and 'ipv4 (1)'."

        VARIATION   tmnxWlanGwVlanAddrType
            SYNTAX  InetAddressType {
                       unknown              (0),
                       ipv4                 (1)
                    -- ipv6                 (2)
                    -- ipv4z                (3)
                    -- ipv6z                (4)
                    -- dns                  (16)
                    }
            DESCRIPTION
                 "tmnxWlanGwVlanAddrType supports only the InetAddressType
                  values 'unknown (0)' and 'ipv4 (1)'."

        VARIATION   tmnxWlanGwVlanDns1AddrType
            SYNTAX  InetAddressType {
                       unknown              (0),
                       ipv4                 (1)
                    -- ipv6                 (2)
                    -- ipv4z                (3)
                    -- ipv6z                (4)
                    -- dns                  (16)
                    }
            DESCRIPTION
                 "tmnxWlanGwVlanDns1AddrType supports only the InetAddressType
                  values 'unknown (0)' and 'ipv4 (1)'."

        VARIATION   tmnxWlanGwVlanDns2AddrType
            SYNTAX  InetAddressType {
                       unknown              (0),
                       ipv4                 (1)
                    -- ipv6                 (2)
                    -- ipv4z                (3)
                    -- ipv6z                (4)
                    -- dns                  (16)
                    }
            DESCRIPTION
                 "tmnxWlanGwVlanDns2AddrType supports only the InetAddressType
                  values 'unknown (0)' and 'ipv4 (1)'."

        VARIATION   tmnxWlanGwVlanNb1AddrType
            SYNTAX  InetAddressType {
                       unknown              (0),
                       ipv4                 (1)
                    -- ipv6                 (2)
                    -- ipv4z                (3)
                    -- ipv6z                (4)
                    -- dns                  (16)
                    }
            DESCRIPTION
                 "tmnxWlanGwVlanNb1AddrType supports only the InetAddressType
                  values 'unknown (0)' and 'ipv4 (1)'."

        VARIATION   tmnxWlanGwVlanNb2AddrType
            SYNTAX  InetAddressType {
                       unknown              (0),
                       ipv4                 (1)
                    -- ipv6                 (2)
                    -- ipv4z                (3)
                    -- ipv6z                (4)
                    -- dns                  (16)
                    }
            DESCRIPTION
                 "tmnxWlanGwVlanNb2AddrType supports only the InetAddressType
                  values 'unknown (0)' and 'ipv4 (1)'."

    ::= { tmnx7750AgentV14v0  84 }

--
-- SROS WPP CAPABILITIES
--
tmnxSROSWppV14v0                  AGENT-CAPABILITIES
    PRODUCT-RELEASE "Nokia SROS"
    STATUS          current
    DESCRIPTION
         "Implementation of Web Portal Protocol on Nokia SROS systems release
          14.0."

    SUPPORTS        TIMETRA-WEB-PORTAL-PROTOCOL-MIB
        INCLUDES {
           tmnxWppGroup,
           tmnxWppNotifyGroup,
           tmnxWppNtfLogoutGroup,
           tmnxWppV12v0Group
        }

        VARIATION   tmnxWppAdminState
            SYNTAX  INTEGER {
                    -- noop                 (1)
                       inService            (2),
                       outOfService         (3)
                    }
            DESCRIPTION
                 "tmnxWppAdminState supports only the values 'inService (2)' and
                  'outOfService (3)'."

        VARIATION   tmnxWppIfAdminState
            SYNTAX  INTEGER {
                    -- noop                 (1)
                       inService            (2),
                       outOfService         (3)
                    }
            DESCRIPTION
                 "tmnxWppIfAdminState supports only the values 'inService (2)'
                  and 'outOfService (3)'."

        VARIATION   tmnxWppPortalAddrType
            SYNTAX  InetAddressType {
                    -- unknown              (0)
                       ipv4                 (1)
                    -- ipv6                 (2)
                    -- ipv4z                (3)
                    -- ipv6z                (4)
                    -- dns                  (16)
                    }
            DESCRIPTION
                 "tmnxWppPortalAddrType supports only the InetAddressType value
                  'ipv4 (1)'."

        VARIATION   tmnxWppPortalAdminState
            SYNTAX  INTEGER {
                    -- noop                 (1)
                       inService            (2),
                       outOfService         (3)
                    }
            DESCRIPTION
                 "tmnxWppPortalAdminState supports only the values 'inService
                  (2)' and 'outOfService (3)'."

        VARIATION   tmnxWppPortalRowStatus
            SYNTAX  RowStatus {
                       active               (1),
                    -- notInService         (2)
                    -- notReady             (3)
                       createAndGo          (4),
                    -- createAndWait        (5)
                       destroy              (6)
                    }
            DESCRIPTION
                 "tmnxWppPortalRowStatus supports only 'active (1)',
                  'createAndGo (4)', and 'destroy (6)'."

        VARIATION   tmnxWppRowStatus
            SYNTAX  RowStatus {
                       active               (1),
                    -- notInService         (2)
                    -- notReady             (3)
                       createAndGo          (4),
                    -- createAndWait        (5)
                       destroy              (6)
                    }
            DESCRIPTION
                 "tmnxWppRowStatus supports only 'active (1)', 'createAndGo
                  (4)', and 'destroy (6)'."

    ::= { tmnxSROSAgentV14v0  82 }

--
-- 7950 WPP CAPABILITIES
--
tmnx7950WppV14v0                  AGENT-CAPABILITIES
    PRODUCT-RELEASE "Nokia SROS"
    STATUS          current
    DESCRIPTION
         "Implementation of Web Portal Protocol on Nokia 7950 systems release
          14.0."

--    SUPPORTS        TIMETRA-WEB-PORTAL-PROTOCOL-MIB
--        INCLUDES {
--        }

    ::= { tmnx7950AgentV14v0  82 }

--
-- 7750 _CALLTRACE CAPABILITIES
--
tmnx7750CalltraceV14v0            AGENT-CAPABILITIES
    PRODUCT-RELEASE "Nokia SROS"
    STATUS          current
    DESCRIPTION
         "Implementation of call trace capabilities for Nokia 7750 systems
          release 14.0."

    SUPPORTS        TIMETRA-CALLTRACE-MIB
        INCLUDES {
           tmnxCallTraceFileGroup,
           tmnxCallTraceJobGroup,
           tmnxCallTraceLocStoreGroup,
           tmnxCallTraceNotifyGroup,
           tmnxCallTraceProfileGroup,
           tmnxCallTraceScalarCfgGroup,
           tmnxCallTraceScalarStatsGroup
        }

        VARIATION   tmnxCallTraceJobDstAddrType
            SYNTAX  InetAddressType {
                       unknown              (0),
                       ipv4                 (1),
                       ipv6                 (2),
                    -- ipv4z                (3)
                    -- ipv6z                (4)
                       dns                  (16)
                    }
            DESCRIPTION
                 "tmnxCallTraceJobDstAddrType supports only the InetAddressType
                  values 'unknown (0)', 'ipv4 (1)', 'ipv6 (2)' and 'dns (16)'."

        VARIATION   tmnxCallTraceProfileDstAddrType
            SYNTAX  InetAddressType {
                       unknown              (0),
                       ipv4                 (1),
                       ipv6                 (2),
                    -- ipv4z                (3)
                    -- ipv6z                (4)
                       dns                  (16)
                    }
            DESCRIPTION
                 "tmnxCallTraceProfileDstAddrType supports only the
                  InetAddressType values 'unknown (0)', 'ipv4 (1)', 'ipv6 (2)'
                  and 'dns (16)'."

        VARIATION   tmnxCallTraceProfileRowStatus
            SYNTAX  RowStatus {
                       active               (1),
                    -- notInService         (2)
                    -- notReady             (3)
                       createAndGo          (4),
                    -- createAndWait        (5)
                       destroy              (6)
                    }
            DESCRIPTION
                 "tmnxCallTraceProfileRowStatus supports only 'active (1)',
                  'createAndGo (4)', and 'destroy (6)'."

    ::= { tmnx7750AgentV14v0  94 }

END
